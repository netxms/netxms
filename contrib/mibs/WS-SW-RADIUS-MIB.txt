-- vim: syntax=mib
--
-- WS-SW-RADIUS-MIB.my
-- MIB generated by MG-SOFT Visual MIB Builder Version 6.0  Build 88
-- Wednesday, January 03, 2007 at 16:47:37
--

--  WS-SW-RADIUS-MIB.my
-- MIB generated by MG-SOFT Visual MIB Builder Version 6.0  Build 88
-- Sunday, August 06, 2006 at 05:41:40
-- 
--  WS-SW-RADIUS-MIB.my
-- MIB generated by MG-SOFT Visual MIB Builder Version 6.0  Build 88
-- Saturday, August 05, 2006 at 06:29:41
-- 
--  WS-SW-RADIUS-MIB.my
-- MIB generated by MG-SOFT Visual MIB Builder Version 6.0  Build 88
-- Sunday, July 23, 2006 at 00:22:35
-- 
--  WS-SW-RADIUS-MIB.my
-- MIB generated by MG-SOFT Visual MIB Builder Version 6.0  Build 88
-- Friday, July 21, 2006 at 06:17:42
-- 
--  WS-SW-RADIUS-MIB.my
-- MIB generated by MG-SOFT Visual MIB Builder Version 5.0  Build 250
-- Tuesday, June 20, 2006 at 17:38:13
-- 
--  WS-SW-DHCPSERVER-MIB.my
-- MIB generated by MG-SOFT Visual MIB Builder Version 6.0  Build 88
-- Wednesday, May 24, 2006 at 16:49:44
-- 

	WS-SW-RADIUS-MIB DEFINITIONS ::= BEGIN
 
		IMPORTS
			OBJECT-GROUP			
				FROM SNMPv2-CONF			
			IpAddress, Integer32, Unsigned32, OBJECT-TYPE, 
			MODULE-IDENTITY			
				FROM SNMPv2-SMI			
			DisplayString, TruthValue			
				FROM SNMPv2-TC			
			wsSw			
				FROM WS-SMI;
	
	
		-- 1.3.6.1.4.1.388.14.2.13.1
		wsSwRadiusModule MODULE-IDENTITY 
			LAST-UPDATED "200606131814Z"		-- June 13, 2006 at 18:14 GMT
			ORGANIZATION 
				"Symbol Technologies"
			CONTACT-INFO 
				"Contact-info."
			DESCRIPTION 
				"Description."
			REVISION "200606141825Z"		-- June 14, 2006 at 18:25 GMT
			DESCRIPTION 
				"Symbol Technologies, Inc.
				Customer Service
				Postal:
				One Symbol Plaza
				Holtsville, NY 11742-1300
				USA
				Tel: +1. 631.738.6213
				E-mail: support@symbol.com
				Web: http://www.symbol.com/support
				
				"
			::= { wsSwRadius 1 }

		
	
--
-- Type definitions
--
	
--  1.3.6.1.4.1.388.14.2.13.1
-- June 13, 2006 at 18:14 GMT
-- June 14, 2006 at 18:25 GMT
-- 
-- Type definitions
-- 
--  1.3.6.1.4.1.388.14.2.13.1
-- June 13, 2006 at 18:14 GMT
-- June 14, 2006 at 18:25 GMT
-- 
-- Type definitions
-- 
--  1.3.6.1.4.1.388.14.2.13.1
-- June 13, 2006 at 18:14 GMT
-- June 14, 2006 at 18:25 GMT
-- 
-- Type definitions
-- 
--  1.3.6.1.4.1.388.14.2.13.1
-- June 13, 2006 at 18:14 GMT
-- June 14, 2006 at 18:25 GMT
-- 
-- Type definitions
-- 
--  1.3.6.1.4.1.388.14.2.13.1
-- June 13, 2006 at 18:14 GMT
-- June 14, 2006 at 18:25 GMT
-- 
-- Type definitions
-- 
-- In order to make the switch's implementation of some
-- dynamic tables simpler, tables using this datatype
-- use an abbreviated form of RowStatus.
-- 
-- Only CreateAndGo and Destroy states are supported.
-- 
-- On row creation, a single SET-PDU must contain all
-- the required values, including this value set to
-- createAndGo.  (This greatly simplifies row validation
-- for the switch).
-- 
-- Setting this value to Destroy causes the corresponding
-- row to be deleted.
-- 
		AbbrevRowStatus ::= INTEGER
			{
			createAndGo(4),
			destroy(6)
			}

--      Values of this type are passwords.  They can be written,
-- but when read, they return a 0-length string.
-- 
		Password ::= OCTET STRING

	
	
--
-- Node definitions
--
	
--  Node definitions
-- 
-- Node definitions
-- 
-- Node definitions
-- 
-- Node definitions
-- 
-- Node definitions
-- 
-- 1.3.6.1.4.1.388.14.2.13
-- 1.3.6.1.4.1.388.14.2.13
-- 1.3.6.1.4.1.388.14.2.13
-- 1.3.6.1.4.1.388.14.2.13
-- 1.3.6.1.4.1.388.14.2.13
		-- 1.3.6.1.4.1.388.14.2.13
		wsSwRadius OBJECT IDENTIFIER ::= { wsSw 13 }

		
--      1.3.6.1.4.1.388.14.2.13.1.1
-- 1.3.6.1.4.1.388.14.2.13.1.1
-- 1.3.6.1.4.1.388.14.2.13.1.1
-- 1.3.6.1.4.1.388.14.2.13.1.1
-- 1.3.6.1.4.1.388.14.2.13.1.1
		-- 1.3.6.1.4.1.388.14.2.13.1.1
		wsSwRadiusGlobal OBJECT IDENTIFIER ::= { wsSwRadiusModule 1 }

		
--      1.3.6.1.4.1.388.14.2.13.1.1.1
-- 1.3.6.1.4.1.388.14.2.13.1.1.1
-- 1.3.6.1.4.1.388.14.2.13.1.1.1
-- 1.3.6.1.4.1.388.14.2.13.1.1.1
-- 1.3.6.1.4.1.388.14.2.13.1.1.1
		-- 1.3.6.1.4.1.388.14.2.13.1.1.1
		wsSwRadiusSaveStatus OBJECT-TYPE
			SYNTAX INTEGER
				{
				save(1),
				idle(2)
				}
			MAX-ACCESS read-write
			STATUS current
			DESCRIPTION
				"Save the configuration info for the radius server. This OID should only be used to set and the only valid value for set is save(1). Get on this OID will always return idle(2)"
			::= { wsSwRadiusGlobal 1 }

		
--      1.3.6.1.4.1.388.14.2.13.1.1.2
-- 1.3.6.1.4.1.388.14.2.13.1.1.2
-- 1.3.6.1.4.1.388.14.2.13.1.1.2
-- 1.3.6.1.4.1.388.14.2.13.1.1.2
-- 1.3.6.1.4.1.388.14.2.13.1.1.2
		-- 1.3.6.1.4.1.388.14.2.13.1.1.2
		wsSwRadiusServerEnable OBJECT-TYPE
			SYNTAX INTEGER
				{
				enable(0),
				disable(1)
				}
			MAX-ACCESS read-write
			STATUS current
			DESCRIPTION
				"Enable(0) or disable(1) the radius server."
			::= { wsSwRadiusGlobal 2 }

		
--      1.3.6.1.4.1.388.14.2.13.1.1.3
-- 1.3.6.1.4.1.388.14.2.13.1.1.3
-- 1.3.6.1.4.1.388.14.2.13.1.1.3
-- 1.3.6.1.4.1.388.14.2.13.1.1.3
-- 1.3.6.1.4.1.388.14.2.13.1.1.3
		-- 1.3.6.1.4.1.388.14.2.13.1.1.3
		wsSwRadiusCATrustPoint OBJECT-TYPE
			SYNTAX DisplayString
			MAX-ACCESS read-write
			STATUS current
			DESCRIPTION
				"CA certificate trustpoint. Setting this OID with blank string( zero length string ) removes the configured trustpoint"
			::= { wsSwRadiusGlobal 3 }

		
--      1.3.6.1.4.1.388.14.2.13.1.1.4
-- 1.3.6.1.4.1.388.14.2.13.1.1.4
-- 1.3.6.1.4.1.388.14.2.13.1.1.4
-- 1.3.6.1.4.1.388.14.2.13.1.1.4
-- 1.3.6.1.4.1.388.14.2.13.1.1.4
		-- 1.3.6.1.4.1.388.14.2.13.1.1.4
		wsSwRadiusServerTrustPoint OBJECT-TYPE
			SYNTAX DisplayString
			MAX-ACCESS read-write
			STATUS current
			DESCRIPTION
				"Server certificate trustpoint. Setting this OID with blank string( zero length string ) removes the configured trustpoint"
			::= { wsSwRadiusGlobal 4 }

		
--      1.3.6.1.4.1.388.14.2.13.1.1.5
-- 1.3.6.1.4.1.388.14.2.13.1.1.5
-- 1.3.6.1.4.1.388.14.2.13.1.1.5
-- 1.3.6.1.4.1.388.14.2.13.1.1.5
-- 1.3.6.1.4.1.388.14.2.13.1.1.5
		-- 1.3.6.1.4.1.388.14.2.13.1.1.5
		wsSwRadiusAuthType OBJECT-TYPE
			SYNTAX INTEGER
				{
				tls(0),
				ttlsAndMd5(1),
				ttlsAndPap(2),
				ttlsAndMschapV2(3),
				peapAndGtc(4),
				peapAndMschapV2(5),
				all(6)
				}
			MAX-ACCESS read-write
			STATUS current
			DESCRIPTION
				"Radius authentication type"
			::= { wsSwRadiusGlobal 5 }

		
--      1.3.6.1.4.1.388.14.2.13.1.1.8
-- 1.3.6.1.4.1.388.14.2.13.1.1.8
-- 1.3.6.1.4.1.388.14.2.13.1.1.8
-- 1.3.6.1.4.1.388.14.2.13.1.1.8
-- 1.3.6.1.4.1.388.14.2.13.1.1.8
		-- 1.3.6.1.4.1.388.14.2.13.1.1.8
		wsSwRadiusDataSource OBJECT-TYPE
			SYNTAX INTEGER
				{
				local(1),
				ldap(2)
				}
			MAX-ACCESS read-write
			STATUS current
			DESCRIPTION
				"Radius datasource which can be local or ldap"
			::= { wsSwRadiusGlobal 8 }

		
--      1.3.6.1.4.1.388.14.2.13.1.7.1
-- 1.3.6.1.4.1.388.14.2.13.1.1.9
-- 1.3.6.1.4.1.388.14.2.13.1.1.9
-- 1.3.6.1.4.1.388.14.2.13.1.1.9
-- 1.3.6.1.4.1.388.14.2.13.1.1.9
		-- 1.3.6.1.4.1.388.14.2.13.1.1.9
		wsSwRadiusProxyRetryCount OBJECT-TYPE
			SYNTAX INTEGER (3..6)
			MAX-ACCESS read-write
			STATUS current
			DESCRIPTION
				"Number of retries for sending messages to a proxy"
			::= { wsSwRadiusGlobal 9 }

		
--      1.3.6.1.4.1.388.14.2.13.1.7.2
-- 1.3.6.1.4.1.388.14.2.13.1.1.10
-- 1.3.6.1.4.1.388.14.2.13.1.1.10
-- 1.3.6.1.4.1.388.14.2.13.1.1.10
-- 1.3.6.1.4.1.388.14.2.13.1.1.10
		-- 1.3.6.1.4.1.388.14.2.13.1.1.10
		wsSwRadiusProxyTimeout OBJECT-TYPE
			SYNTAX INTEGER (5..10)
			UNITS "seconds"
			MAX-ACCESS read-write
			STATUS current
			DESCRIPTION
				"Timeout in seconds before retrying to a proxy"
			::= { wsSwRadiusGlobal 10 }

		
		-- 1.3.6.1.4.1.388.14.2.13.1.1.11
		wsSwRadiusCRL OBJECT-TYPE
			SYNTAX INTEGER
				{
				disable(0),
				enable(1)
				}
			MAX-ACCESS read-write
			STATUS current
			DESCRIPTION
				"Description."
			::= { wsSwRadiusGlobal 11 }

		
--     1.3.6.1.4.1.388.14.2.13.1.2
-- 1.3.6.1.4.1.388.14.2.13.1.2
-- 1.3.6.1.4.1.388.14.2.13.1.2
-- 1.3.6.1.4.1.388.14.2.13.1.2
		-- 1.3.6.1.4.1.388.14.2.13.1.2
		wsSwRadiusLdapTable OBJECT-TYPE
			SYNTAX SEQUENCE OF WsSwRadiusLdapEntry
			MAX-ACCESS not-accessible
			STATUS current
			DESCRIPTION
				"This table can have only 2 rows. One for primary ldap server and other for secondary ldap server."
			::= { wsSwRadiusModule 2 }

		
--     1.3.6.1.4.1.388.14.2.13.1.2.1
-- 1.3.6.1.4.1.388.14.2.13.1.2.1
-- 1.3.6.1.4.1.388.14.2.13.1.2.1
-- 1.3.6.1.4.1.388.14.2.13.1.2.1
		-- 1.3.6.1.4.1.388.14.2.13.1.2.1
		wsSwRadiusLdapEntry OBJECT-TYPE
			SYNTAX WsSwRadiusLdapEntry
			MAX-ACCESS not-accessible
			STATUS current
			DESCRIPTION
				"Description."
			INDEX { wsSwRadiusLdapServerType }
			::= { wsSwRadiusLdapTable 1 }

		
		WsSwRadiusLdapEntry ::=
			SEQUENCE { 
				wsSwRadiusLdapServerType
					INTEGER,
				wsSwRadiusLdapServerIp
					IpAddress,
				wsSwRadiusLdapServerPort
					Unsigned32,
				wsSwRadiusLdapLoginAttribute
					DisplayString,
				wsSwRadiusLdapPasswordAttribute
					DisplayString,
				wsSwRadiusLdapBindDistinguishedName
					DisplayString,
				wsSwRadiusLdapBindDistinguishedPassword
					DisplayString,
				wsSwRadiusLdapBaseDistinguishedName
					DisplayString,
				wsSwRadiusLdapGroupAttribute
					DisplayString,
				wsSwRadiusLdapGroupFilter
					DisplayString,
				wsSwRadiusLdapGroupMembershipAttribute
					DisplayString,
				wsSwRadiusLdapNetTimeout
					INTEGER,
				wsSwRadiusLdapRowStatus
					AbbrevRowStatus
			 }

--     1.3.6.1.4.1.388.14.2.13.1.2.1.1
-- 1.3.6.1.4.1.388.14.2.13.1.2.1.1
-- 1.3.6.1.4.1.388.14.2.13.1.2.1.1
-- 1.3.6.1.4.1.388.14.2.13.1.2.1.1
		-- 1.3.6.1.4.1.388.14.2.13.1.2.1.1
		wsSwRadiusLdapServerType OBJECT-TYPE
			SYNTAX INTEGER
				{
				primary(1),
				secondary(2)
				}
			MAX-ACCESS read-only
			STATUS current
			DESCRIPTION
				"Primary or secondary ldap server"
			::= { wsSwRadiusLdapEntry 1 }

		
--     1.3.6.1.4.1.388.14.2.13.1.2.1.2
-- 1.3.6.1.4.1.388.14.2.13.1.2.1.2
-- 1.3.6.1.4.1.388.14.2.13.1.2.1.2
-- 1.3.6.1.4.1.388.14.2.13.1.2.1.2
		-- 1.3.6.1.4.1.388.14.2.13.1.2.1.2
		wsSwRadiusLdapServerIp OBJECT-TYPE
			SYNTAX IpAddress
			MAX-ACCESS read-create
			STATUS current
			DESCRIPTION
				"IP Address of ldap server. The value for this OID can be set only while creating the row and cannot be modified later."
			::= { wsSwRadiusLdapEntry 2 }

		
--     1.3.6.1.4.1.388.14.2.13.1.2.1.3
-- 1.3.6.1.4.1.388.14.2.13.1.2.1.3
-- 1.3.6.1.4.1.388.14.2.13.1.2.1.3
-- 1.3.6.1.4.1.388.14.2.13.1.2.1.3
		-- 1.3.6.1.4.1.388.14.2.13.1.2.1.3
		wsSwRadiusLdapServerPort OBJECT-TYPE
			SYNTAX Unsigned32
			MAX-ACCESS read-create
			STATUS current
			DESCRIPTION
				"Port of LDAP server. The value for this OID can be set only while creating the row and cannot be modified later."
			::= { wsSwRadiusLdapEntry 3 }

		
--     1.3.6.1.4.1.388.14.2.13.1.2.1.4
-- 1.3.6.1.4.1.388.14.2.13.1.2.1.4
-- 1.3.6.1.4.1.388.14.2.13.1.2.1.4
-- 1.3.6.1.4.1.388.14.2.13.1.2.1.4
		-- 1.3.6.1.4.1.388.14.2.13.1.2.1.4
		wsSwRadiusLdapLoginAttribute OBJECT-TYPE
			SYNTAX DisplayString
			MAX-ACCESS read-create
			STATUS current
			DESCRIPTION
				"Ldap Login. The value for this OID can be set only while creating the row and cannot be modified later."
			::= { wsSwRadiusLdapEntry 4 }

		
--     1.3.6.1.4.1.388.14.2.13.1.2.1.5
-- 1.3.6.1.4.1.388.14.2.13.1.2.1.5
-- 1.3.6.1.4.1.388.14.2.13.1.2.1.5
-- 1.3.6.1.4.1.388.14.2.13.1.2.1.5
		-- 1.3.6.1.4.1.388.14.2.13.1.2.1.5
		wsSwRadiusLdapPasswordAttribute OBJECT-TYPE
			SYNTAX DisplayString
			MAX-ACCESS read-create
			STATUS current
			DESCRIPTION
				"Ldap Password. The value for this OID can be set only while creating the row and cannot be modified later."
			::= { wsSwRadiusLdapEntry 5 }

		
--     1.3.6.1.4.1.388.14.2.13.1.2.1.6
-- 1.3.6.1.4.1.388.14.2.13.1.2.1.6
-- 1.3.6.1.4.1.388.14.2.13.1.2.1.6
-- 1.3.6.1.4.1.388.14.2.13.1.2.1.6
		-- 1.3.6.1.4.1.388.14.2.13.1.2.1.6
		wsSwRadiusLdapBindDistinguishedName OBJECT-TYPE
			SYNTAX DisplayString
			MAX-ACCESS read-create
			STATUS current
			DESCRIPTION
				"Bind Distinguished Name. The value for this OID can be set only while creating the row and cannot be modified later."
			::= { wsSwRadiusLdapEntry 6 }

		
--     1.3.6.1.4.1.388.14.2.13.1.2.1.7
-- 1.3.6.1.4.1.388.14.2.13.1.2.1.7
-- 1.3.6.1.4.1.388.14.2.13.1.2.1.7
-- 1.3.6.1.4.1.388.14.2.13.1.2.1.7
		-- 1.3.6.1.4.1.388.14.2.13.1.2.1.7
		wsSwRadiusLdapBindDistinguishedPassword OBJECT-TYPE
			SYNTAX DisplayString
			MAX-ACCESS read-create
			STATUS current
			DESCRIPTION
				"Bind distinguished password. The value for this OID can be set only while creating the row and cannot be modified later."
			::= { wsSwRadiusLdapEntry 7 }

		
--     1.3.6.1.4.1.388.14.2.13.1.2.1.8
-- 1.3.6.1.4.1.388.14.2.13.1.2.1.8
-- 1.3.6.1.4.1.388.14.2.13.1.2.1.8
-- 1.3.6.1.4.1.388.14.2.13.1.2.1.8
		-- 1.3.6.1.4.1.388.14.2.13.1.2.1.8
		wsSwRadiusLdapBaseDistinguishedName OBJECT-TYPE
			SYNTAX DisplayString
			MAX-ACCESS read-create
			STATUS current
			DESCRIPTION
				"Base distinguished password. The value for this OID can be set only while creating the row and cannot be modified later."
			::= { wsSwRadiusLdapEntry 8 }

		
--     1.3.6.1.4.1.388.14.2.13.1.2.1.9
-- 1.3.6.1.4.1.388.14.2.13.1.2.1.9
-- 1.3.6.1.4.1.388.14.2.13.1.2.1.9
-- 1.3.6.1.4.1.388.14.2.13.1.2.1.9
		-- 1.3.6.1.4.1.388.14.2.13.1.2.1.9
		wsSwRadiusLdapGroupAttribute OBJECT-TYPE
			SYNTAX DisplayString
			MAX-ACCESS read-create
			STATUS current
			DESCRIPTION
				"Group Attribute. The value for this OID can be set only while creating the row and cannot be modified later."
			::= { wsSwRadiusLdapEntry 9 }

		
--     1.3.6.1.4.1.388.14.2.13.1.2.1.10
-- 1.3.6.1.4.1.388.14.2.13.1.2.1.10
-- 1.3.6.1.4.1.388.14.2.13.1.2.1.10
-- 1.3.6.1.4.1.388.14.2.13.1.2.1.10
		-- 1.3.6.1.4.1.388.14.2.13.1.2.1.10
		wsSwRadiusLdapGroupFilter OBJECT-TYPE
			SYNTAX DisplayString
			MAX-ACCESS read-create
			STATUS current
			DESCRIPTION
				"Group Filter. The value for this OID can be set only while creating the row and cannot be modified later."
			::= { wsSwRadiusLdapEntry 10 }

		
--     1.3.6.1.4.1.388.14.2.13.1.2.1.11
-- 1.3.6.1.4.1.388.14.2.13.1.2.1.11
-- 1.3.6.1.4.1.388.14.2.13.1.2.1.11
-- 1.3.6.1.4.1.388.14.2.13.1.2.1.11
		-- 1.3.6.1.4.1.388.14.2.13.1.2.1.11
		wsSwRadiusLdapGroupMembershipAttribute OBJECT-TYPE
			SYNTAX DisplayString
			MAX-ACCESS read-create
			STATUS current
			DESCRIPTION
				"Membership Attribute. The value for this OID can be set only while creating the row and cannot be modified later."
			::= { wsSwRadiusLdapEntry 11 }

		
		-- 1.3.6.1.4.1.388.14.2.13.1.2.1.12
		wsSwRadiusLdapNetTimeout OBJECT-TYPE
			SYNTAX INTEGER (1..10)
			MAX-ACCESS read-create
			STATUS current
			DESCRIPTION
				"Timeout value in the range of 1 to 10. If the user does not enter any value or if the value entered is 0, then the default value for net timeout will be used. The default value for net timeout is 1."
			::= { wsSwRadiusLdapEntry 12 }

		
--     1.3.6.1.4.1.388.14.2.13.1.2.1.12
-- 1.3.6.1.4.1.388.14.2.13.1.2.1.12
-- 1.3.6.1.4.1.388.14.2.13.1.2.1.12
-- 1.3.6.1.4.1.388.14.2.13.1.2.1.12
		-- 1.3.6.1.4.1.388.14.2.13.1.2.1.13
		wsSwRadiusLdapRowStatus OBJECT-TYPE
			SYNTAX AbbrevRowStatus
			MAX-ACCESS read-create
			STATUS current
			DESCRIPTION
				"Row Status for LDAP table."
			::= { wsSwRadiusLdapEntry 13 }

		
--      1.3.6.1.4.1.388.14.2.13.1.4.2
-- 1.3.6.1.4.1.388.14.2.13.1.3
-- 1.3.6.1.4.1.388.14.2.13.1.3
-- 1.3.6.1.4.1.388.14.2.13.1.3
-- 1.3.6.1.4.1.388.14.2.13.1.3
		-- 1.3.6.1.4.1.388.14.2.13.1.3
		wsSwRadiusUsersTable OBJECT-TYPE
			SYNTAX SEQUENCE OF WsSwRadiusUsersEntry
			MAX-ACCESS not-accessible
			STATUS current
			DESCRIPTION
				"Description."
			::= { wsSwRadiusModule 3 }

		
--      1.3.6.1.4.1.388.14.2.13.1.4.2.1
-- 1.3.6.1.4.1.388.14.2.13.1.3.1
-- 1.3.6.1.4.1.388.14.2.13.1.3.1
-- 1.3.6.1.4.1.388.14.2.13.1.3.1
-- 1.3.6.1.4.1.388.14.2.13.1.3.1
		-- 1.3.6.1.4.1.388.14.2.13.1.3.1
		wsSwRadiusUsersEntry OBJECT-TYPE
			SYNTAX WsSwRadiusUsersEntry
			MAX-ACCESS not-accessible
			STATUS current
			DESCRIPTION
				"Description."
			INDEX { wsSwRadiusUsersId }
			::= { wsSwRadiusUsersTable 1 }

		
		WsSwRadiusUsersEntry ::=
			SEQUENCE { 
				wsSwRadiusUsersId
					DisplayString,
				wsSwRadiusUsersPassword
					DisplayString,
				wsSwRadiusUsersIfGuestUser
					TruthValue,
				wsSwRadiusUsersGroups
					BITS,
				wsSwRadiusUsersExpiryDateAndTime
					OCTET STRING,
				wsSwRadiusUsersRowStatus
					AbbrevRowStatus,
				wsSwRadiusUsersStartDateAndTime
					OCTET STRING
			 }

--      1.3.6.1.4.1.388.14.2.13.1.4.2.1.1
-- 1.3.6.1.4.1.388.14.2.13.1.3.1.1
-- 1.3.6.1.4.1.388.14.2.13.1.3.1.1
-- 1.3.6.1.4.1.388.14.2.13.1.3.1.1
-- 1.3.6.1.4.1.388.14.2.13.1.3.1.1
		-- 1.3.6.1.4.1.388.14.2.13.1.3.1.1
		wsSwRadiusUsersId OBJECT-TYPE
			SYNTAX DisplayString
			MAX-ACCESS read-only
			STATUS current
			DESCRIPTION
				"This OID is used to add a user. The user name can not be
				greater 64 characters"
			::= { wsSwRadiusUsersEntry 1 }

		
--      1.3.6.1.4.1.388.14.2.13.1.4.2.1.2
-- 1.3.6.1.4.1.388.14.2.13.1.3.1.2
-- 1.3.6.1.4.1.388.14.2.13.1.3.1.2
-- 1.3.6.1.4.1.388.14.2.13.1.3.1.2
-- 1.3.6.1.4.1.388.14.2.13.1.3.1.2
		-- 1.3.6.1.4.1.388.14.2.13.1.3.1.2
		wsSwRadiusUsersPassword OBJECT-TYPE
			SYNTAX DisplayString
			MAX-ACCESS read-create
			STATUS current
			DESCRIPTION
				"Radius user password"
			::= { wsSwRadiusUsersEntry 2 }

		
--      1.3.6.1.4.1.388.14.2.13.1.4.2.1.3
-- 1.3.6.1.4.1.388.14.2.13.1.3.1.3
-- 1.3.6.1.4.1.388.14.2.13.1.3.1.3
-- 1.3.6.1.4.1.388.14.2.13.1.3.1.3
-- 1.3.6.1.4.1.388.14.2.13.1.3.1.3
		-- 1.3.6.1.4.1.388.14.2.13.1.3.1.3
		wsSwRadiusUsersIfGuestUser OBJECT-TYPE
			SYNTAX TruthValue
			MAX-ACCESS read-create
			STATUS current
			DESCRIPTION
				"Whether the user is guest user or not."
			::= { wsSwRadiusUsersEntry 3 }

		
--      1.3.6.1.4.1.388.14.2.13.1.4.2.1.4
-- 1.3.6.1.4.1.388.14.2.13.1.3.1.4
-- 1.3.6.1.4.1.388.14.2.13.1.3.1.4
-- 1.3.6.1.4.1.388.14.2.13.1.3.1.4
-- 1.3.6.1.4.1.388.14.2.13.1.3.1.4
		-- 1.3.6.1.4.1.388.14.2.13.1.3.1.4
		wsSwRadiusUsersGroups OBJECT-TYPE
			SYNTAX BITS
				{
				g8(0),
				g7(1),
				g6(2),
				g5(3),
				g4(4),
				g3(5),
				g2(6),
				g1(7),
				g16(8),
				g15(9),
				g14(10),
				g13(11),
				g12(12),
				g11(13),
				g10(14),
				g9(15),
				g24(16),
				g23(17),
				g22(18),
				g21(19),
				g20(20),
				g19(21),
				g18(22),
				g17(23),
				g32(24),
				g31(25),
				g30(26),
				g29(27),
				g28(28),
				g27(29),
				g26(30),
				g25(31),
				g40(32),
				g39(33),
				g38(34),
				g37(35),
				g36(36),
				g35(37),
				g34(38),
				g33(39),
				g48(40),
				g47(41),
				g46(42),
				g45(43),
				g44(44),
				g43(45),
				g42(46),
				g41(47),
				g56(48),
				g55(49),
				g54(50),
				g53(51),
				g52(52),
				g51(53),
				g50(54),
				g49(55),
				g64(56),
				g63(57),
				g62(58),
				g61(59),
				g60(60),
				g59(61),
				g58(62),
				g57(63),
				g72(64),
				g71(65),
				g70(66),
				g69(67),
				g68(68),
				g67(69),
				g66(70),
				g65(71),
				g80(72),
				g79(73),
				g78(74),
				g77(75),
				g76(76),
				g75(77),
				g74(78),
				g73(79),
				g88(80),
				g87(81),
				g86(82),
				g85(83),
				g84(84),
				g83(85),
				g82(86),
				g81(87),
				g96(88),
				g95(89),
				g94(90),
				g93(91),
				g92(92),
				g91(93),
				g90(94),
				g89(95),
				null(96),
				unused1(97),
				unused2(98),
				unused3(99),
				g100(100),
				g99(101),
				g98(102)
				}
			MAX-ACCESS read-create
			STATUS current
			DESCRIPTION
				"List of groups to which the user belongs. The g1, g2 ... in the list indicate the group numbers 1, 2 ...The group number to group name mapping can be found in wsSwRadiusGroupsTable table."
			::= { wsSwRadiusUsersEntry 4 }

		
--      1.3.6.1.4.1.388.14.2.13.1.4.2.1.5
-- 1.3.6.1.4.1.388.14.2.13.1.3.1.5
-- 1.3.6.1.4.1.388.14.2.13.1.3.1.5
-- 1.3.6.1.4.1.388.14.2.13.1.3.1.5
-- 1.3.6.1.4.1.388.14.2.13.1.3.1.5
		-- 1.3.6.1.4.1.388.14.2.13.1.3.1.5
		wsSwRadiusUsersExpiryDateAndTime OBJECT-TYPE
			SYNTAX OCTET STRING
			MAX-ACCESS read-create
			STATUS current
			DESCRIPTION
				"Expiry date and time should be of the format MM:DD:YYYY-HH:MM "
			::= { wsSwRadiusUsersEntry 5 }

		
--      1.3.6.1.4.1.388.14.2.13.1.4.2.1.7
-- 1.3.6.1.4.1.388.14.2.13.1.3.1.7
-- 1.3.6.1.4.1.388.14.2.13.1.3.1.7
-- 1.3.6.1.4.1.388.14.2.13.1.3.1.6
-- 1.3.6.1.4.1.388.14.2.13.1.3.1.6
		-- 1.3.6.1.4.1.388.14.2.13.1.3.1.6
		wsSwRadiusUsersRowStatus OBJECT-TYPE
			SYNTAX AbbrevRowStatus
			MAX-ACCESS read-create
			STATUS current
			DESCRIPTION
				"Row status of wsSwRadiusUsersTable"
			::= { wsSwRadiusUsersEntry 6 }

		
		-- 1.3.6.1.4.1.388.14.2.13.1.3.1.7
		wsSwRadiusUsersStartDateAndTime OBJECT-TYPE
			SYNTAX OCTET STRING
			MAX-ACCESS read-create
			STATUS current
			DESCRIPTION
				"Expiry date and time should be of the format MM:DD:YYYY-HH:MM "
			::= { wsSwRadiusUsersEntry 7 }

		
--      1.3.6.1.4.1.388.14.2.13.1.4.1
-- 1.3.6.1.4.1.388.14.2.13.1.4
-- 1.3.6.1.4.1.388.14.2.13.1.4
-- 1.3.6.1.4.1.388.14.2.13.1.4
-- 1.3.6.1.4.1.388.14.2.13.1.4
		-- 1.3.6.1.4.1.388.14.2.13.1.4
		wsSwRadiusGroupsTable OBJECT-TYPE
			SYNTAX SEQUENCE OF WsSwRadiusGroupsEntry
			MAX-ACCESS not-accessible
			STATUS current
			DESCRIPTION
				"Description."
			::= { wsSwRadiusModule 4 }

		
--      1.3.6.1.4.1.388.14.2.13.1.4.1.1
-- 1.3.6.1.4.1.388.14.2.13.1.4.1
-- 1.3.6.1.4.1.388.14.2.13.1.4.1
-- 1.3.6.1.4.1.388.14.2.13.1.4.1
-- 1.3.6.1.4.1.388.14.2.13.1.4.1
		-- 1.3.6.1.4.1.388.14.2.13.1.4.1
		wsSwRadiusGroupsEntry OBJECT-TYPE
			SYNTAX WsSwRadiusGroupsEntry
			MAX-ACCESS not-accessible
			STATUS current
			DESCRIPTION
				"Description."
			INDEX { wsSwRadiusGroupName }
			::= { wsSwRadiusGroupsTable 1 }

		
		WsSwRadiusGroupsEntry ::=
			SEQUENCE { 
				wsSwRadiusGroupName
					DisplayString,
				wsSwRadiusGroupNum
					Integer32,
				wsSwRadiusIfGuestGroup
					TruthValue,
				wsSwRadiusGroupRowStatus
					AbbrevRowStatus
			 }

--      1.3.6.1.4.1.388.14.2.13.1.4.1.1.1
-- 1.3.6.1.4.1.388.14.2.13.1.4.1.1
-- 1.3.6.1.4.1.388.14.2.13.1.4.1.1
-- 1.3.6.1.4.1.388.14.2.13.1.4.1.1
-- 1.3.6.1.4.1.388.14.2.13.1.4.1.1
		-- 1.3.6.1.4.1.388.14.2.13.1.4.1.1
		wsSwRadiusGroupName OBJECT-TYPE
			SYNTAX DisplayString
			MAX-ACCESS read-only
			STATUS current
			DESCRIPTION
				"Name of the group"
			::= { wsSwRadiusGroupsEntry 1 }

		
--     1.3.6.1.4.1.388.14.2.13.1.4.1.2
-- 1.3.6.1.4.1.388.14.2.13.1.4.1.2
-- 1.3.6.1.4.1.388.14.2.13.1.4.1.2
-- 1.3.6.1.4.1.388.14.2.13.1.4.1.2
		-- 1.3.6.1.4.1.388.14.2.13.1.4.1.2
		wsSwRadiusGroupNum OBJECT-TYPE
			SYNTAX Integer32
			MAX-ACCESS read-only
			STATUS current
			DESCRIPTION
				"A group number corresponding to group. g1, g2 ... are identifiers used while associating users to groups. The value g1 indicates group with group number 1, the value g2 indicates group with group number 2 and so on."
			::= { wsSwRadiusGroupsEntry 2 }

		
--      1.3.6.1.4.1.388.14.2.13.1.4.1.1.2
-- 1.3.6.1.4.1.388.14.2.13.1.4.1.3
-- 1.3.6.1.4.1.388.14.2.13.1.4.1.3
-- 1.3.6.1.4.1.388.14.2.13.1.4.1.3
-- 1.3.6.1.4.1.388.14.2.13.1.4.1.3
		-- 1.3.6.1.4.1.388.14.2.13.1.4.1.3
		wsSwRadiusIfGuestGroup OBJECT-TYPE
			SYNTAX TruthValue
			MAX-ACCESS read-create
			STATUS current
			DESCRIPTION
				"whether this group is guest group or not."
			::= { wsSwRadiusGroupsEntry 3 }

		
--      1.3.6.1.4.1.388.14.2.13.1.4.1.1.3
-- 1.3.6.1.4.1.388.14.2.13.1.4.1.4
-- 1.3.6.1.4.1.388.14.2.13.1.4.1.4
-- 1.3.6.1.4.1.388.14.2.13.1.4.1.4
-- 1.3.6.1.4.1.388.14.2.13.1.4.1.4
		-- 1.3.6.1.4.1.388.14.2.13.1.4.1.4
		wsSwRadiusGroupRowStatus OBJECT-TYPE
			SYNTAX AbbrevRowStatus
			MAX-ACCESS read-create
			STATUS current
			DESCRIPTION
				"Row status of wsSwRadiusGroupsTable"
			::= { wsSwRadiusGroupsEntry 4 }

		
--      1.3.6.1.4.1.388.14.2.13.1.2
-- 1.3.6.1.4.1.388.14.2.13.1.5
-- 1.3.6.1.4.1.388.14.2.13.1.5
-- 1.3.6.1.4.1.388.14.2.13.1.5
-- 1.3.6.1.4.1.388.14.2.13.1.5
		-- 1.3.6.1.4.1.388.14.2.13.1.5
		wsSwRadiusClientAuthTable OBJECT-TYPE
			SYNTAX SEQUENCE OF WsSwRadiusClientAuthEntry
			MAX-ACCESS not-accessible
			STATUS current
			DESCRIPTION
				"Description."
			::= { wsSwRadiusModule 5 }

		
--      1.3.6.1.4.1.388.14.2.13.1.2.1
-- 1.3.6.1.4.1.388.14.2.13.1.5.1
-- 1.3.6.1.4.1.388.14.2.13.1.5.1
-- 1.3.6.1.4.1.388.14.2.13.1.5.1
-- 1.3.6.1.4.1.388.14.2.13.1.5.1
		-- 1.3.6.1.4.1.388.14.2.13.1.5.1
		wsSwRadiusClientAuthEntry OBJECT-TYPE
			SYNTAX WsSwRadiusClientAuthEntry
			MAX-ACCESS not-accessible
			STATUS current
			DESCRIPTION
				"Description."
			INDEX { wsSwRadiusClientAuthIpAndMask }
			::= { wsSwRadiusClientAuthTable 1 }

		
		WsSwRadiusClientAuthEntry ::=
			SEQUENCE { 
				wsSwRadiusClientAuthIpAndMask
					DisplayString,
				wsSwRadiusClientAuthSharedSecret
					DisplayString,
				wsSwRadiusClientAuthRowStatus
					AbbrevRowStatus
			 }

--      1.3.6.1.4.1.388.14.2.13.1.2.1.4
-- 1.3.6.1.4.1.388.14.2.13.1.5.1.1
-- 1.3.6.1.4.1.388.14.2.13.1.5.1.1
-- 1.3.6.1.4.1.388.14.2.13.1.5.1.1
-- 1.3.6.1.4.1.388.14.2.13.1.5.1.1
		-- 1.3.6.1.4.1.388.14.2.13.1.5.1.1
		wsSwRadiusClientAuthIpAndMask OBJECT-TYPE
			SYNTAX DisplayString
			MAX-ACCESS read-only
			STATUS current
			DESCRIPTION
				"The client IP address with subnet mask"
			::= { wsSwRadiusClientAuthEntry 1 }

		
--      1.3.6.1.4.1.388.14.2.13.1.2.1.2
-- 1.3.6.1.4.1.388.14.2.13.1.5.1.2
-- 1.3.6.1.4.1.388.14.2.13.1.5.1.2
-- 1.3.6.1.4.1.388.14.2.13.1.5.1.2
-- 1.3.6.1.4.1.388.14.2.13.1.5.1.2
		-- 1.3.6.1.4.1.388.14.2.13.1.5.1.2
		wsSwRadiusClientAuthSharedSecret OBJECT-TYPE
			SYNTAX DisplayString
			MAX-ACCESS read-create
			STATUS current
			DESCRIPTION
				"Shared secret between the client and the radius server. The value for this OID can be set only while creating the row and cannot be modified later."
			::= { wsSwRadiusClientAuthEntry 2 }

		
--      1.3.6.1.4.1.388.14.2.13.1.2.1.1
-- 1.3.6.1.4.1.388.14.2.13.1.5.1.3
-- 1.3.6.1.4.1.388.14.2.13.1.5.1.3
-- 1.3.6.1.4.1.388.14.2.13.1.5.1.3
-- 1.3.6.1.4.1.388.14.2.13.1.5.1.3
		-- 1.3.6.1.4.1.388.14.2.13.1.5.1.3
		wsSwRadiusClientAuthRowStatus OBJECT-TYPE
			SYNTAX AbbrevRowStatus
			MAX-ACCESS read-create
			STATUS current
			DESCRIPTION
				"Row status of Client Auth Table."
			::= { wsSwRadiusClientAuthEntry 3 }

		
--      1.3.6.1.4.1.388.14.2.13.1.5
-- 1.3.6.1.4.1.388.14.2.13.1.6
-- 1.3.6.1.4.1.388.14.2.13.1.6
-- 1.3.6.1.4.1.388.14.2.13.1.6
-- 1.3.6.1.4.1.388.14.2.13.1.6
		-- 1.3.6.1.4.1.388.14.2.13.1.6
		wsSwRadiusAccessTable OBJECT-TYPE
			SYNTAX SEQUENCE OF WsSwRadiusAccessEntry
			MAX-ACCESS not-accessible
			STATUS current
			DESCRIPTION
				"Description."
			::= { wsSwRadiusModule 6 }

		
--      1.3.6.1.4.1.388.14.2.13.1.5.1
-- 1.3.6.1.4.1.388.14.2.13.1.6.1
-- 1.3.6.1.4.1.388.14.2.13.1.6.1
-- 1.3.6.1.4.1.388.14.2.13.1.6.1
-- 1.3.6.1.4.1.388.14.2.13.1.6.1
		-- 1.3.6.1.4.1.388.14.2.13.1.6.1
		wsSwRadiusAccessEntry OBJECT-TYPE
			SYNTAX WsSwRadiusAccessEntry
			MAX-ACCESS not-accessible
			STATUS current
			DESCRIPTION
				"Description."
			INDEX { wsSwRadiusAccessGroupId }
			::= { wsSwRadiusAccessTable 1 }

		
		WsSwRadiusAccessEntry ::=
			SEQUENCE { 
				wsSwRadiusAccessGroupId
					DisplayString,
				wsSwRadiusAccessVlanPtrs
					Integer32,
				wsSwRadiusTimeofAccessStart
					DisplayString,
				wsSwRadiusTimeofAccessEnd
					DisplayString,
				wsSwRadiusTimeofAccessDays
					BITS,
				wsSwRadiusAccessWlanPtrs
					BITS
			 }

--      1.3.6.1.4.1.388.14.2.13.1.5.1.1
-- 1.3.6.1.4.1.388.14.2.13.1.6.1.1
-- 1.3.6.1.4.1.388.14.2.13.1.6.1.1
-- 1.3.6.1.4.1.388.14.2.13.1.6.1.1
-- 1.3.6.1.4.1.388.14.2.13.1.6.1.1
		-- 1.3.6.1.4.1.388.14.2.13.1.6.1.1
		wsSwRadiusAccessGroupId OBJECT-TYPE
			SYNTAX DisplayString
			MAX-ACCESS read-only
			STATUS current
			DESCRIPTION
				"Displays the GroupId for which coressponding
				WLAN mapping is being dispalyed."
			::= { wsSwRadiusAccessEntry 1 }

		
--     1.3.6.1.4.1.388.14.2.13.1.6.1.3
-- 1.3.6.1.4.1.388.14.2.13.1.6.1.3
-- 1.3.6.1.4.1.388.14.2.13.1.6.1.3
-- 1.3.6.1.4.1.388.14.2.13.1.6.1.3
		-- 1.3.6.1.4.1.388.14.2.13.1.6.1.2
		wsSwRadiusAccessVlanPtrs OBJECT-TYPE
			SYNTAX Integer32 (0..4096)
			MAX-ACCESS read-write
			STATUS current
			DESCRIPTION
				"Vlan with which the group is associated. Values 1 to 4096 indicate the configured vlans.
				Value 0 indicates that No VLAN is configured."
			::= { wsSwRadiusAccessEntry 2 }

		
--      1.3.6.1.4.1.388.14.2.13.1.5.1.3
-- 1.3.6.1.4.1.388.14.2.13.1.6.1.4
-- 1.3.6.1.4.1.388.14.2.13.1.6.1.4
-- 1.3.6.1.4.1.388.14.2.13.1.6.1.4
-- 1.3.6.1.4.1.388.14.2.13.1.6.1.4
		-- 1.3.6.1.4.1.388.14.2.13.1.6.1.3
		wsSwRadiusTimeofAccessStart OBJECT-TYPE
			SYNTAX DisplayString
			MAX-ACCESS read-write
			STATUS current
			DESCRIPTION
				"Radius Access Policy Start time. Format is HHMM"
			::= { wsSwRadiusAccessEntry 3 }

		
--      1.3.6.1.4.1.388.14.2.13.1.5.1.4
-- 1.3.6.1.4.1.388.14.2.13.1.6.1.5
-- 1.3.6.1.4.1.388.14.2.13.1.6.1.5
-- 1.3.6.1.4.1.388.14.2.13.1.6.1.5
-- 1.3.6.1.4.1.388.14.2.13.1.6.1.5
		-- 1.3.6.1.4.1.388.14.2.13.1.6.1.4
		wsSwRadiusTimeofAccessEnd OBJECT-TYPE
			SYNTAX DisplayString
			MAX-ACCESS read-write
			STATUS current
			DESCRIPTION
				"Radius Access Policy End time. Format is HHMM"
			::= { wsSwRadiusAccessEntry 4 }

		
--      1.3.6.1.4.1.388.14.2.13.1.5.1.5
-- 1.3.6.1.4.1.388.14.2.13.1.6.1.6
-- 1.3.6.1.4.1.388.14.2.13.1.6.1.6
-- 1.3.6.1.4.1.388.14.2.13.1.6.1.6
-- 1.3.6.1.4.1.388.14.2.13.1.6.1.6
		-- 1.3.6.1.4.1.388.14.2.13.1.6.1.5
		wsSwRadiusTimeofAccessDays OBJECT-TYPE
			SYNTAX BITS
				{
				unused(0),
				sunday(1),
				saturday(2),
				friday(3),
				thursday(4),
				wednesday(5),
				tuesday(6),
				monday(7)
				}
			MAX-ACCESS read-write
			STATUS current
			DESCRIPTION
				"Radius Time Restriction in Days."
			::= { wsSwRadiusAccessEntry 5 }

		
--      1.3.6.1.4.1.388.14.2.13.1.5.1.2
-- 1.3.6.1.4.1.388.14.2.13.1.6.1.2
-- 1.3.6.1.4.1.388.14.2.13.1.6.1.2
-- 1.3.6.1.4.1.388.14.2.13.1.6.1.2
-- 1.3.6.1.4.1.388.14.2.13.1.6.1.2
		-- 1.3.6.1.4.1.388.14.2.13.1.6.1.6
		wsSwRadiusAccessWlanPtrs OBJECT-TYPE
			SYNTAX BITS
				{
				wlan8(0),
				wlan7(1),
				wlan6(2),
				wlan5(3),
				wlan4(4),
				wlan3(5),
				wlan2(6),
				wlan1(7),
				wlan16(8),
				wlan15(9),
				wlan14(10),
				wlan13(11),
				wlan12(12),
				wlan11(13),
				wlan10(14),
				wlan9(15),
				wlan24(16),
				wlan23(17),
				wlan22(18),
				wlan21(19),
				wlan20(20),
				wlan19(21),
				wlan18(22),
				wlan17(23),
				wlan32(24),
				wlan31(25),
				wlan30(26),
				wlan29(27),
				wlan28(28),
				wlan27(29),
				wlan26(30),
				wlan25(31)
				}
			MAX-ACCESS read-write
			STATUS current
			DESCRIPTION
				"List of Wlans to which the current group is associated.
				"
			::= { wsSwRadiusAccessEntry 6 }

		
--      1.3.6.1.4.1.388.14.2.13.1.7.3
-- 1.3.6.1.4.1.388.14.2.13.1.9
-- 1.3.6.1.4.1.388.14.2.13.1.9
-- 1.3.6.1.4.1.388.14.2.13.1.9
-- 1.3.6.1.4.1.388.14.2.13.1.9
		-- 1.3.6.1.4.1.388.14.2.13.1.9
		wsSwRadiusProxyServerTable OBJECT-TYPE
			SYNTAX SEQUENCE OF WsSwRadiusProxyServerEntry
			MAX-ACCESS not-accessible
			STATUS current
			DESCRIPTION
				"Description."
			::= { wsSwRadiusModule 9 }

		
--      1.3.6.1.4.1.388.14.2.13.1.7.3.1
-- 1.3.6.1.4.1.388.14.2.13.1.9.1
-- 1.3.6.1.4.1.388.14.2.13.1.9.1
-- 1.3.6.1.4.1.388.14.2.13.1.9.1
-- 1.3.6.1.4.1.388.14.2.13.1.9.1
		-- 1.3.6.1.4.1.388.14.2.13.1.9.1
		wsSwRadiusProxyServerEntry OBJECT-TYPE
			SYNTAX WsSwRadiusProxyServerEntry
			MAX-ACCESS not-accessible
			STATUS current
			DESCRIPTION
				"Description."
			INDEX { wsSwRadiusProxyServerRealm }
			::= { wsSwRadiusProxyServerTable 1 }

		
		WsSwRadiusProxyServerEntry ::=
			SEQUENCE { 
				wsSwRadiusProxyServerRealm
					DisplayString,
				wsSwRadiusProxyServerIp
					IpAddress,
				wsSwRadiusProxyServerPort
					Integer32,
				wsSwRadiusProxyServerSharedSecret
					DisplayString,
				wsSwRadiusProxyServerRowStatus
					AbbrevRowStatus
			 }

--      1.3.6.1.4.1.388.14.2.13.1.7.3.1.2
-- 1.3.6.1.4.1.388.14.2.13.1.9.1.2
-- 1.3.6.1.4.1.388.14.2.13.1.9.1.2
-- 1.3.6.1.4.1.388.14.2.13.1.9.1.1
-- 1.3.6.1.4.1.388.14.2.13.1.9.1.1
		-- 1.3.6.1.4.1.388.14.2.13.1.9.1.1
		wsSwRadiusProxyServerRealm OBJECT-TYPE
			SYNTAX DisplayString
			MAX-ACCESS read-only
			STATUS current
			DESCRIPTION
				"Realm of proxy server."
			::= { wsSwRadiusProxyServerEntry 1 }

		
--      1.3.6.1.4.1.388.14.2.13.1.7.3.1.3
-- 1.3.6.1.4.1.388.14.2.13.1.9.1.3
-- 1.3.6.1.4.1.388.14.2.13.1.9.1.3
-- 1.3.6.1.4.1.388.14.2.13.1.9.1.2
-- 1.3.6.1.4.1.388.14.2.13.1.9.1.2
		-- 1.3.6.1.4.1.388.14.2.13.1.9.1.2
		wsSwRadiusProxyServerIp OBJECT-TYPE
			SYNTAX IpAddress
			MAX-ACCESS read-create
			STATUS current
			DESCRIPTION
				"IP address of the proxy server. The value for this OID can be set only while creating the row and cannot be modified later."
			::= { wsSwRadiusProxyServerEntry 2 }

		
--      1.3.6.1.4.1.388.14.2.13.1.7.3.1.4
-- 1.3.6.1.4.1.388.14.2.13.1.9.1.4
-- 1.3.6.1.4.1.388.14.2.13.1.9.1.4
-- 1.3.6.1.4.1.388.14.2.13.1.9.1.3
-- 1.3.6.1.4.1.388.14.2.13.1.9.1.3
		-- 1.3.6.1.4.1.388.14.2.13.1.9.1.3
		wsSwRadiusProxyServerPort OBJECT-TYPE
			SYNTAX Integer32 (1..65535)
			MAX-ACCESS read-create
			STATUS current
			DESCRIPTION
				"Port of proxy server. The value for this OID can be set only while creating the row and cannot be modified later."
			::= { wsSwRadiusProxyServerEntry 3 }

		
--      1.3.6.1.4.1.388.14.2.13.1.7.3.1.5
-- 1.3.6.1.4.1.388.14.2.13.1.9.1.5
-- 1.3.6.1.4.1.388.14.2.13.1.9.1.5
-- 1.3.6.1.4.1.388.14.2.13.1.9.1.4
-- 1.3.6.1.4.1.388.14.2.13.1.9.1.4
		-- 1.3.6.1.4.1.388.14.2.13.1.9.1.4
		wsSwRadiusProxyServerSharedSecret OBJECT-TYPE
			SYNTAX DisplayString
			MAX-ACCESS read-create
			STATUS current
			DESCRIPTION
				"Shared secret between radius server and proxy server. The value for this OID can be set only while creating the row and cannot be modified later."
			::= { wsSwRadiusProxyServerEntry 4 }

		
--      1.3.6.1.4.1.388.14.2.13.1.7.3.1.6
-- 1.3.6.1.4.1.388.14.2.13.1.9.1.6
-- 1.3.6.1.4.1.388.14.2.13.1.9.1.6
-- 1.3.6.1.4.1.388.14.2.13.1.9.1.5
-- 1.3.6.1.4.1.388.14.2.13.1.9.1.5
		-- 1.3.6.1.4.1.388.14.2.13.1.9.1.5
		wsSwRadiusProxyServerRowStatus OBJECT-TYPE
			SYNTAX AbbrevRowStatus
			MAX-ACCESS read-create
			STATUS current
			DESCRIPTION
				"Row status of wsSwRadiusProxyServerTable"
			::= { wsSwRadiusProxyServerEntry 5 }

		
--      1.3.6.1.4.1.388.14.2.13.1.8
-- 1.3.6.1.4.1.388.14.2.13.1.10
-- 1.3.6.1.4.1.388.14.2.13.1.10
-- 1.3.6.1.4.1.388.14.2.13.1.10
-- 1.3.6.1.4.1.388.14.2.13.1.10
		-- 1.3.6.1.4.1.388.14.2.13.1.10
		wsSwRadiusObjectGroup OBJECT IDENTIFIER ::= { wsSwRadiusModule 10 }

		
--      1.3.6.1.4.1.388.14.2.13.1.8.1
-- 1.3.6.1.4.1.388.14.2.13.1.10.1
-- 1.3.6.1.4.1.388.14.2.13.1.10.1
-- 1.3.6.1.4.1.388.14.2.13.1.10.1
-- 1.3.6.1.4.1.388.14.2.13.1.10.1
		-- 1.3.6.1.4.1.388.14.2.13.1.10.1
		wsSwRadiusObjectGroupAll OBJECT-GROUP
			OBJECTS { wsSwRadiusDataSource, wsSwRadiusServerTrustPoint, wsSwRadiusCATrustPoint, wsSwRadiusClientAuthSharedSecret, wsSwRadiusClientAuthRowStatus, 
				wsSwRadiusServerEnable, wsSwRadiusSaveStatus, wsSwRadiusProxyRetryCount, wsSwRadiusProxyTimeout, wsSwRadiusProxyServerIp, 
				wsSwRadiusProxyServerPort, wsSwRadiusProxyServerSharedSecret, wsSwRadiusProxyServerRowStatus, wsSwRadiusGroupRowStatus, wsSwRadiusUsersId, 
				wsSwRadiusUsersPassword, wsSwRadiusUsersGroups, wsSwRadiusUsersRowStatus, wsSwRadiusAccessGroupId, wsSwRadiusAccessWlanPtrs, 
				wsSwRadiusIfGuestGroup, wsSwRadiusUsersIfGuestUser, wsSwRadiusAuthType, wsSwRadiusLdapServerIp, wsSwRadiusLdapServerType, 
				wsSwRadiusLdapServerPort, wsSwRadiusLdapLoginAttribute, wsSwRadiusLdapBindDistinguishedName, wsSwRadiusLdapPasswordAttribute, wsSwRadiusLdapBaseDistinguishedName, 
				wsSwRadiusLdapBindDistinguishedPassword, wsSwRadiusLdapGroupFilter, wsSwRadiusLdapGroupAttribute, wsSwRadiusProxyServerRealm, wsSwRadiusAccessVlanPtrs, 
				wsSwRadiusGroupNum, wsSwRadiusClientAuthIpAndMask, wsSwRadiusGroupName, wsSwRadiusLdapRowStatus, wsSwRadiusLdapGroupMembershipAttribute, 
				wsSwRadiusUsersExpiryDateAndTime, wsSwRadiusTimeofAccessDays, wsSwRadiusLdapNetTimeout, wsSwRadiusCRL, wsSwRadiusUsersStartDateAndTime, 
				wsSwRadiusTimeofAccessEnd, wsSwRadiusTimeofAccessStart }
			STATUS current
			DESCRIPTION 
				"Description."
			::= { wsSwRadiusObjectGroup 1 }

		
	
	END

--
-- WS-SW-RADIUS-MIB.my
--
