-- =====================================================================
-- Copyright (c) 2004-2012 Hangzhou H3C Tech. Co., Ltd. All rights reserved.
--
-- Description: LACP extend MIB
-- Reference:
-- Version: V1.7
-- History:
--   V1.0 Initial version
--   V1.1 2004-10-12 updated by gaolong
--        Remove OID comments.
--        Change MAX-ACCESS clause value of hh3cAggLinkNumber to accessible-for-notify
--        because this index object is used when sending notification.
--        Fix a default value error of hh3cAggResourceAllocationValue.
--   V1.2 2004-10-25 updated by fuzhenyu
--        Change the range of hh3cAggLinkNumber from (1..256) to (1..728)
--        Change the size of hh3cAggPortNotAttachedString from (1..50) to (1..255)
--   V1.3 2006-03-05 updated by zhangjian
--        Edit the description of hh3cAggPortNotAttachedReason.
--        Change value range of hh3cAggLinkNumber.
--   V1.4 2006-11-15 updated by zhangjian
--        Change MAX-ACCESS clause of hh3cAggPortIndex to accessible-for-notify.
--        Add hh3cAggPortInactiveNotification2 and hh3cAggPortActiveNotification.
--   V1.5 2009-10-09 updated by songjianyong
--        Change value range of hh3cAggPortNotAttachedReason.
--   V1.6 2010-03-26 updated by songjianyong
--        Change value range of hh3cAggPortNotAttachedReason.
--   V1.7 2011-10-12 updated by liyugang
--        Change some descriptions.
-- =====================================================================
HH3C-LAG-MIB DEFINITIONS ::= BEGIN

    IMPORTS
        OBJECT-GROUP, MODULE-COMPLIANCE, NOTIFICATION-GROUP
            FROM SNMPv2-CONF
        Integer32, Gauge32, OBJECT-TYPE, MODULE-IDENTITY, NOTIFICATION-TYPE
            FROM SNMPv2-SMI
        DisplayString, RowStatus,TruthValue,TEXTUAL-CONVENTION
            FROM SNMPv2-TC
        hh3cRhw
            FROM HH3C-OID-MIB
        PortList
            FROM Q-BRIDGE-MIB;

    hh3cLAG MODULE-IDENTITY
        LAST-UPDATED "200310091942Z"    -- October 09, 2003 at 19:42 GMT
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "LACP extend MIB."
        ::= { hh3cRhw 25 }

--
-- Node definitions
--

    hh3cLAGMibObjects OBJECT IDENTIFIER ::= { hh3cLAG 1 }


    hh3cAggLinkTable OBJECT-TYPE
        SYNTAX SEQUENCE OF Hh3cAggLinkEntry
        MAX-ACCESS not-accessible
        STATUS current
        DESCRIPTION
            "A table of aggregate link objects."
        ::= { hh3cLAGMibObjects 1 }


    hh3cAggLinkEntry OBJECT-TYPE
        SYNTAX Hh3cAggLinkEntry
        MAX-ACCESS not-accessible
        STATUS current
        DESCRIPTION
            "Entry of table."
        INDEX { hh3cAggLinkNumber }
        ::= { hh3cAggLinkTable 1 }


    Hh3cAggLinkEntry ::=
        SEQUENCE {
            hh3cAggLinkNumber
                Integer32,
            hh3cAggLinkName
                DisplayString,
            hh3cAggLinkMode
                INTEGER,
            hh3cAggLinkPortList
                PortList,
            hh3cAggLinkState
                RowStatus,
            hh3cAggPortListSelectedPorts
                PortList,
            hh3cAggPortListSamePartnerPorts
                PortList
         }

    hh3cAggLinkNumber OBJECT-TYPE
        SYNTAX Integer32
        MAX-ACCESS accessible-for-notify
        STATUS current
        DESCRIPTION
            "The serial number of aggregation group."
        ::= { hh3cAggLinkEntry 1 }


    hh3cAggLinkName OBJECT-TYPE
        SYNTAX DisplayString (SIZE (0..32))
        MAX-ACCESS read-create
        STATUS current
        DESCRIPTION
            "Aggregation name."
        ::= { hh3cAggLinkEntry 2 }


    hh3cAggLinkMode OBJECT-TYPE
        SYNTAX INTEGER
            {
            manual(1),
            static(2),
            dynamic(3)
            }
        MAX-ACCESS read-create
        STATUS current
        DESCRIPTION
            "Type of aggregation.
             manual: Manual aggregation, no LACP.
             static: Membership specified by user, LACP is
                     used to validate.
             dynamic: Completely dynamic aggregation detected
                      by LACP."
        ::= { hh3cAggLinkEntry 3 }


    hh3cAggLinkPortList OBJECT-TYPE
        SYNTAX PortList
        MAX-ACCESS read-create
        STATUS current
        DESCRIPTION
            "List of ports in this link aggregation group, by bridge port
             number. If the mode of the link aggregation group is manual
             or static, you can update this list to your
             hearts content. However, if the link aggregation group is
             dynamic, the system will maintain it. You are not
             permitted to set the value of this to
             all zeroes."
        ::= { hh3cAggLinkEntry 4 }


    hh3cAggLinkState OBJECT-TYPE
        SYNTAX RowStatus
        MAX-ACCESS read-create
        STATUS current
        DESCRIPTION
            "RowStatus, now support three states:
            createAndGo, active, destroy."
        ::= { hh3cAggLinkEntry 5 }


    hh3cAggPortListSelectedPorts OBJECT-TYPE
        SYNTAX PortList
        MAX-ACCESS read-only
        STATUS current
        DESCRIPTION
            "A PortList of physical ports that have been
             selected but not attached to this aggregator.
             When the bit is set to 1,it means the
             corresponding port is in the portlist."
        ::= { hh3cAggLinkEntry 6 }


    hh3cAggPortListSamePartnerPorts OBJECT-TYPE
        SYNTAX PortList
        MAX-ACCESS read-only
        STATUS current
        DESCRIPTION
            "PortList of physical ports that have the
             same Actor SystemID and partner systemID as
             this aggregator, but have different actor
             and partner keys of aggregator."
        ::= { hh3cAggLinkEntry 7 }


    hh3cAggPortTable OBJECT-TYPE
        SYNTAX SEQUENCE OF Hh3cAggPortEntry
        MAX-ACCESS not-accessible
        STATUS current
        DESCRIPTION
            "A table of aggregate port objects."
        ::= { hh3cLAGMibObjects 2 }


    hh3cAggPortEntry OBJECT-TYPE
        SYNTAX Hh3cAggPortEntry
        MAX-ACCESS not-accessible
        STATUS current
        DESCRIPTION
            "Entry of table."
        INDEX { hh3cAggPortIndex }
        ::= { hh3cAggPortTable 1 }


    Hh3cAggPortEntry ::=
        SEQUENCE {
            hh3cAggPortIndex
                Gauge32,
            hh3cAggPortNotAttachedReason
                Integer32,
            hh3cAggPortLacpState
                TruthValue,
            hh3cAggPortNotAttachedString
                DisplayString
        }

    hh3cAggPortIndex OBJECT-TYPE
        SYNTAX Gauge32
        MAX-ACCESS accessible-for-notify
        STATUS current
        DESCRIPTION
            "Port ifindex which is according to RFC1213 MIB."
        ::= { hh3cAggPortEntry 1 }


    hh3cAggPortNotAttachedReason OBJECT-TYPE
        SYNTAX Integer32 (0..10)
        MAX-ACCESS read-write
        STATUS current
        DESCRIPTION
            "Reason why this port is selected for an
             aggregator but not attached,
             0: The port is attached to this aggregator.
             1: The current number of active ports has
                reached the upper limit.
             2: All aggregation resources are already in-use.
             3: The port's configuration is improper
                for being attached.
             4: The port's partner is improper for being attached.
             5: The number of current active ports
                has not reached the lower limit.
             6: The port's physical state (down) is
                improper for being attached.
             7: The port is not selected for an aggregator.
             8: The port's hardware restriction is
                improper for being attached.
             9: The port's speed is improper for being attached.
             10: The port's duplex mode is improper for being attached."
        ::= { hh3cAggPortEntry 2 }

    hh3cAggPortLacpState OBJECT-TYPE
        SYNTAX TruthValue
        MAX-ACCESS read-write
        STATUS current
        DESCRIPTION
            "Control ports' lacp enble or disable."
        ::= { hh3cAggPortEntry 3 }

    hh3cAggPortNotAttachedString OBJECT-TYPE
        SYNTAX DisplayString (SIZE (0..255))
        MAX-ACCESS read-write
        STATUS current
        DESCRIPTION
            "The string which interprets this
             port is selected for an aggregator
             but not attached."
        ::= { hh3cAggPortEntry 4 }


    hh3cAggResourceAllocationValue OBJECT-TYPE
        SYNTAX PortList
        MAX-ACCESS read-only
        STATUS current
        DESCRIPTION
            "The priority value calculated to decide which
             aggregations have first call on the load-sharing
             aggregation resources in the hardware. It
             depends on the aggregation type and total
             speed."
        DEFVAL { "0" }
        ::= { hh3cLAGMibObjects 3 }


    hh3cLAGMibNotifications OBJECT IDENTIFIER ::= { hh3cLAG 2 }


    hh3cAggSpeedChangedNotification NOTIFICATION-TYPE
        OBJECTS { hh3cAggLinkNumber }
        STATUS current
        DESCRIPTION
            "This event will be triggered whenever an
             aggregation changes its speed."
        ::= { hh3cLAGMibNotifications 1 }


    hh3cAggPortInactiveNotification NOTIFICATION-TYPE
        OBJECTS { hh3cAggLinkNumber }
        STATUS current
        DESCRIPTION
            "This event will be triggered whenever any port
             in aggregator is made inactive."
        ::= { hh3cLAGMibNotifications 2 }


    hh3cAggPortInactiveNotification2 NOTIFICATION-TYPE
        OBJECTS { hh3cAggLinkNumber,
                  hh3cAggPortIndex }
        STATUS current
        DESCRIPTION
            "This event will be triggered whenever the port
             in aggregator is made inactive."
        ::= { hh3cLAGMibNotifications 3 }


    hh3cAggPortActiveNotification NOTIFICATION-TYPE
        OBJECTS { hh3cAggLinkNumber,
                  hh3cAggPortIndex }
        STATUS current
        DESCRIPTION
            "This event will be triggered whenever the port
             in aggregator is made active."
        ::= { hh3cLAGMibNotifications 4 }


    hh3cLAGMibConformance OBJECT IDENTIFIER ::= { hh3cLAG 3 }


    hh3cLAGMibCompliances OBJECT IDENTIFIER ::= { hh3cLAGMibConformance 1 }


    hh3cLAGMibCompliance MODULE-COMPLIANCE
        STATUS current
        DESCRIPTION
            "The compliance statement for SNMP entities
             which implement the Lag MIB."
        MODULE -- this module
            MANDATORY-GROUPS
                { hh3cLAGMibObjectGroup, hh3cLAGMibNotificationGroup }
        ::= { hh3cLAGMibCompliances 1 }


    hh3cLAGMibGroup OBJECT IDENTIFIER ::= { hh3cLAGMibConformance 2 }


    hh3cLAGMibObjectGroup OBJECT-GROUP
        OBJECTS { hh3cAggLinkName, hh3cAggLinkMode, hh3cAggLinkPortList,
                hh3cAggLinkState, hh3cAggPortListSelectedPorts,
                hh3cAggPortListSamePartnerPorts,
                hh3cAggPortNotAttachedReason, hh3cAggPortLacpState,
                hh3cAggPortNotAttachedString,
                hh3cAggResourceAllocationValue }
        STATUS current
        DESCRIPTION
            "The collection of objects which are used to
             represent LAG objects."
        ::= { hh3cLAGMibGroup 1 }


    hh3cLAGMibNotificationGroup NOTIFICATION-GROUP
        NOTIFICATIONS { hh3cAggSpeedChangedNotification,
                        hh3cAggPortInactiveNotification,
                        hh3cAggPortInactiveNotification2,
                        hh3cAggPortActiveNotification }
        STATUS current
        DESCRIPTION
            "The collection of objects which are used to
             represent notifications."
        ::= { hh3cLAGMibGroup 2 }

END
