-- -----------------------------------------------------------------------------
-- MIB NAME : PORTGROUP-MIB
-- FILE NAME: PortGroup.MIB
-- DATE     : 2010/01/11
-- VERSION  : 1.00
-- PURPOSE  : To construct the MIB structure of port group information for
--            proprietary enterprise
-- -----------------------------------------------------------------------------
-- MODIFICTION HISTORY:
-- -----------------------------------------------------------------------------
-- Version, Date, Author
-- Description:
-- [New Object]
-- [Modification]
-- Notes: (Requested by who and which project)
--
-- Version 1.00, 2010/01/11, Peterson Zhou
-- This is the first formal version for universal MIB definition.
-- Notes:Requested by Peterson Zhou for project DGS3120
-- -----------------------------------------------------------------------------

PORTGROUP-MIB DEFINITIONS ::= BEGIN

     IMPORTS
         MODULE-IDENTITY, OBJECT-TYPE     FROM SNMPv2-SMI
         RowStatus, DisplayString
                                          FROM SNMPv2-TC
         PortList                         FROM Q-BRIDGE-MIB
         dlink-common-mgmt                FROM DLINK-ID-REC-MIB;

     swPortGroupMIB MODULE-IDENTITY
         LAST-UPDATED "1001110000Z"
         ORGANIZATION "D-Link Corp."
         CONTACT-INFO
             "http://support.dlink.com"
         DESCRIPTION
             "The structure of port group for the proprietary enterprise."
         ::= { dlink-common-mgmt 88 }

	 swPortGroupMIBObjects	OBJECT IDENTIFIER ::= { swPortGroupMIB 1 }
-- -----------------------------------------------------------------------------
-- swPortGroupMgmtTable	::= { swPortGroupMIBObjects 1 }
-- -----------------------------------------------------------------------------

       swPortGroupTable OBJECT-TYPE
           SYNTAX      SEQUENCE OF SwPortGroupEntry
           MAX-ACCESS  not-accessible
           STATUS      current
           DESCRIPTION
               "A table that contains the information of port group."
           ::= { swPortGroupMIBObjects 1 }

       swPortGroupEntry OBJECT-TYPE
           SYNTAX      SwPortGroupEntry
           MAX-ACCESS  not-accessible
           STATUS      current
           DESCRIPTION
               "A list of information of each port group."
           INDEX { swPortGroupID }
           ::= { swPortGroupTable 1 }

       SwPortGroupEntry ::=
           SEQUENCE {
               swPortGroupID
               	   INTEGER,
               swPortGroupRowStatus
                   RowStatus,
               swPortGroupName
                   DisplayString,
               swPortGroupPorts
                   PortList
           }

       swPortGroupID           OBJECT-TYPE
           SYNTAX      INTEGER
           MAX-ACCESS  not-accessible
           STATUS      current
           DESCRIPTION
               "The ID of the port group.
               Note: The maximum entry range is (1..N), the value N means the maximum number.
               Entry range is project dependent"
           ::= { swPortGroupEntry 1 }

       swPortGroupRowStatus OBJECT-TYPE
           SYNTAX      RowStatus
           MAX-ACCESS  read-create
           STATUS      current
           DESCRIPTION
               "This object indicates the RowStatus of the entry."
           ::= { swPortGroupEntry  2 }

       swPortGroupName           OBJECT-TYPE
           SYNTAX      DisplayString (SIZE (1..16))
           MAX-ACCESS  read-create
           STATUS      current
           DESCRIPTION
               "The name of the port group."
           ::= { swPortGroupEntry 3 }

       swPortGroupPorts         OBJECT-TYPE
           SYNTAX      PortList
           MAX-ACCESS  read-create
           STATUS      current
           DESCRIPTION
               "Configure the port list in this port group."
           ::= { swPortGroupEntry 4 }

END
