FOUNDRY-SN-WIRELESS-GROUP-MIB DEFINITIONS ::= BEGIN
-- Foundry SN WIRELESS GROUP MIB Release 1.0.0
-- Revision 0 04/15/04

-- Copyright 1996-2004 Foundry Networks, Inc.
-- All rights reserved.
-- This Foundry Networks SNMP Management Information Base Specification
-- (Specification) embodies Foundry Networks' confidential and
-- proprietary intellectual property. Foundry Networks retains all
-- title and ownership in the Specification, including any
-- revisions.

-- This Specification is supplied "AS IS," and Foundry Networks makes
-- no warranty, either express or implied, as to the use,
-- operation, condition, or performance of the Specification.

-- SECTION 1: Top Level Definitions

IMPORTS
	MODULE-IDENTITY, OBJECT-TYPE, IpAddress,Integer32
		FROM SNMPv2-SMI
	MacAddress
		FROM FOUNDRY-SN-AGENT-MIB
	snSwitch
		FROM FOUNDRY-SN-SWITCH-GROUP-MIB
	TEXTUAL-CONVENTION
		FROM SNMPv2-TC;

snWireless MODULE-IDENTITY
	LAST-UPDATED "200909300000Z" -- September 30, 2009
	ORGANIZATION "Foundry Networks, Inc"
	CONTACT-INFO
			"Technical Support Center, Foundry Networks,
			4980 Great America Parkway,
			Santa Clara, CA 95054
			Email: support@foundrynet.com
			Phone: 1-877-TURBO-CALL"
	DESCRIPTION
			""
	REVISION     "200909300000Z" -- September 30, 2009
	DESCRIPTION
			"convert from SMIv1 to SMIv2"
   ::= {snSwitch  23}

-- textual conventions

	IfIndexList ::= TEXTUAL-CONVENTION
		STATUS      current
		DESCRIPTION
			"Each octet within this value specifies a set of eight
			interfaces by their ifIndex values, with the first octet
			specifying interfaces 1 through 8, the second octet
			specifying interfaces 9 through 16, etc.  Within each
			octet, the most significant bit represents the lowest
			numbered interface, and the least significant bit
			represents the highest numbered interface.  Thus, each
			interface of the device is represented by a single bit
			within the value of this object.  If that bit has a value
			of '1' then that interface is included in the set of
			interfaces; the interface is not included if its bit has a
			value of '0'."
		SYNTAX      OCTET STRING

-- iso(1).org(3).dod(6).internet(1).private(4).enterprises(1).foundry(1991)

wgGroup     OBJECT IDENTIFIER ::= { snWireless 1 }

wgMobilityId OBJECT-TYPE
	SYNTAX  Integer32
	MAX-ACCESS  read-write
	STATUS  current
	DESCRIPTION
		"Unique Identifier used to specify the mobility doamin.
		 Valid range is <1 - 65535>. Use <0> to remove the domain."
	::= { wgGroup 1 }

wgVpnPTDeletePolicy OBJECT-TYPE
	SYNTAX  Integer32
	MAX-ACCESS  read-write
	STATUS  current
	DESCRIPTION
		"Write a valid VPN pass through policy ID to remove the policy.
		Return zero when reading this object."
	::= { wgGroup 2 }


--
-- WiFi Interface Table
--

wgIfTable OBJECT-TYPE
	SYNTAX SEQUENCE OF WgIfEntry
	MAX-ACCESS not-accessible
	STATUS current
	DESCRIPTION
		"WiFi Interface Table."
	::= { snWireless 2 }

wgIfEntry OBJECT-TYPE
	SYNTAX WgIfEntry
	MAX-ACCESS not-accessible
	STATUS current
	DESCRIPTION
		"An entry of the WiFi Interface Table."
	INDEX { wgIfIndex }
	::= { wgIfTable 1 }

WgIfEntry ::= SEQUENCE {
	wgIfIndex                 Integer32,
	wgIfWirelessEnable        INTEGER,
	wgIfPnPLearnNewAP         INTEGER,
	wgIfAutoPortDisable       INTEGER,
	wgIfVpnPTPolicyId         Integer32,
	wgIfFullCompRoamingEnable INTEGER
}

wgIfIndex OBJECT-TYPE
	SYNTAX  Integer32
	MAX-ACCESS  read-only
	STATUS  current
	DESCRIPTION
		"ifIndex value of the switch interface."
	::= { wgIfEntry 1 }

wgIfWirelessEnable OBJECT-TYPE
	SYNTAX  INTEGER {
		other(1),
		enable(2),
		disable(3)
		}
	MAX-ACCESS  read-write
	STATUS  current
	DESCRIPTION
		"Control wireless function of the switch interface."
	DEFVAL { disable }
	::= { wgIfEntry 2 }

wgIfPnPLearnNewAP OBJECT-TYPE
	SYNTAX  INTEGER {
		other(1),
		enable(2),
		disable(3)
		}
	MAX-ACCESS  read-write
	STATUS  current
	DESCRIPTION
		"Control the interface to learn new AP."
	::= { wgIfEntry 3 }

wgIfAutoPortDisable  OBJECT-TYPE
	SYNTAX  INTEGER {
		other(1),
		enable(2),
		disable(3)
		}
	MAX-ACCESS  read-write
	STATUS  current
	DESCRIPTION
		"Disable the interface if the interface link status change."
	::= { wgIfEntry 4 }

wgIfVpnPTPolicyId OBJECT-TYPE
	SYNTAX Integer32
	MAX-ACCESS  read-write
	STATUS  current
	DESCRIPTION
		"To bind an interface to a VPN pass through policy, write
		a valid policy number which is larger than zero. To unbind
		an interface to a VPN pass through policy, write a zero."
	::= { wgIfEntry 5 }

wgIfFullCompRoamingEnable OBJECT-TYPE
	SYNTAX  INTEGER {
		other(1),
		enable(2),
		disable(3)
		}
	MAX-ACCESS  read-write
	STATUS  current
	DESCRIPTION
		"Control full compatibility roaming of an interface."
	DEFVAL { disable }
	::= { wgIfEntry 6 }


--
-- Roaming Peer table
--

wgRoamingPeerTable OBJECT-TYPE
	SYNTAX  SEQUENCE OF WgRoamingPeerEntry
	MAX-ACCESS  not-accessible
	STATUS  current
	DESCRIPTION
		"Roaming Peer table contains information of peers."
	::= { snWireless 3 }

wgRoamingPeerEntry OBJECT-TYPE
	SYNTAX  WgRoamingPeerEntry
	MAX-ACCESS  not-accessible
	STATUS  current
	DESCRIPTION
		"An entry of the roaming peer table."
	INDEX   { wgRoamingPeerIpAddress }
	::= { wgRoamingPeerTable 1 }

WgRoamingPeerEntry ::= SEQUENCE {
	wgRoamingPeerIpAddress
		IpAddress,
	wgRoamingPeerConnectionStatus
		INTEGER,
	wgRoamingPeerRowStatus
		INTEGER
	}

wgRoamingPeerIpAddress OBJECT-TYPE
	SYNTAX  IpAddress
	MAX-ACCESS  read-only
	STATUS  current
	DESCRIPTION
		"IP Address of the ISRP peer."
	::= { wgRoamingPeerEntry 1 }

wgRoamingPeerConnectionStatus OBJECT-TYPE
	SYNTAX  INTEGER {
		other(1),
		configured(2),
		established(3)
		}
	MAX-ACCESS  read-only
	STATUS  current
	DESCRIPTION
		"Shows the state of the ISRP Connection."
	::= { wgRoamingPeerEntry 2 }

wgRoamingPeerRowStatus OBJECT-TYPE
	SYNTAX  INTEGER {
		other(1),
		valid(2),
		delete(3),
		create(4)
		}
	MAX-ACCESS  read-write
	STATUS  current
	DESCRIPTION
		"Shows the state of the row in the PeerRow Table."
	::= { wgRoamingPeerEntry 3 }


--
-- AP Plug and Play Table
--

wgPnPTable OBJECT-TYPE
	SYNTAX SEQUENCE OF WgPnPEntry
	MAX-ACCESS not-accessible
	STATUS current
	DESCRIPTION
		"AP Plug and Play Table."
	::= { snWireless 4 }

wgPnPEntry OBJECT-TYPE
	SYNTAX WgPnPEntry
	MAX-ACCESS not-accessible
	STATUS current
	DESCRIPTION
		"An entry of the AP Plug and Play Table."
	INDEX { wgPnPIfIndex, wgPnPMacAddress }
	::= { wgPnPTable 1 }

WgPnPEntry ::= SEQUENCE {
	wgPnPIfIndex             Integer32,
	wgPnPMacAddress          MacAddress,
	wgPnPIpAddress           IpAddress,
	wgPnPIpMask              IpAddress,
	wgPnPIpDefaultGw         IpAddress,
	wgPnPStatus              INTEGER,
	wgPnPRowStatus           INTEGER
}

wgPnPIfIndex OBJECT-TYPE
	SYNTAX  Integer32
	MAX-ACCESS  read-only
	STATUS  current
	DESCRIPTION
		"ifIndex value of the switch interface."
	::= { wgPnPEntry 1 }

wgPnPMacAddress OBJECT-TYPE
	SYNTAX  MacAddress
	MAX-ACCESS  read-only
	STATUS  current
	DESCRIPTION
		"MAC address of the attached AP."
	::= { wgPnPEntry 2 }

wgPnPIpAddress OBJECT-TYPE
	SYNTAX  IpAddress
	MAX-ACCESS  read-write
	STATUS  current
	DESCRIPTION
		"IP address of the attached AP."
	::= { wgPnPEntry 3 }

wgPnPIpMask OBJECT-TYPE
	SYNTAX  IpAddress
	MAX-ACCESS  read-write
	STATUS  current
	DESCRIPTION
		"Subnet mask of the attached AP."
	::= { wgPnPEntry 4 }

wgPnPIpDefaultGw OBJECT-TYPE
	SYNTAX  IpAddress
	MAX-ACCESS  read-write
	STATUS  current
	DESCRIPTION
		"Default gateway of the attached AP."
	::= { wgPnPEntry 5 }

wgPnPStatus OBJECT-TYPE
	SYNTAX  INTEGER {
		other(1),
		discovered(2),
		configured(3),
		operational(4)
		}
	MAX-ACCESS  read-only
	STATUS  current
	DESCRIPTION
		"AP device status. If the switch diecovered a new AP which
		had not been configured, the 'discovered' state will return.
		If the AP's IP address, subnet mask and default gateway were
		configured to the switch port but the AP with the matching
		MAC address had not attached to the switch port, 'configured'
		state will return. If the AP's IP address, subnet mask and
		default gateway were configured to the switch port and the
		AP with the matching MAC address had attached to the switch
		port and was operating, 'operational' state will return."
	::= { wgPnPEntry 6 }

wgPnPRowStatus OBJECT-TYPE
	SYNTAX  INTEGER {
		other(1),
		valid(2),
		delete(3),
		create(4),
		modify(5)
		}
	MAX-ACCESS  read-write
	STATUS  current
	DESCRIPTION
		"Create, delete or modify a row of AP Plug and Play Table."
	::= { wgPnPEntry 7 }

--
-- VPN Pass Through Server Table
--

wgVpnPTServerTable OBJECT-TYPE
	SYNTAX SEQUENCE OF WgVpnPTServerEntry
	MAX-ACCESS not-accessible
	STATUS current
	DESCRIPTION
		"VPN pass through server table"
	::= { snWireless 5 }

wgVpnPTServerEntry OBJECT-TYPE
	SYNTAX WgVpnPTServerEntry
	MAX-ACCESS not-accessible
	STATUS current
	DESCRIPTION
		"An entry of the VPN pass through server table."
	INDEX { wgVpnPTServerPolicyId, wgVpnPTServerIpAddress }
	::= { wgVpnPTServerTable 1 }

WgVpnPTServerEntry ::= SEQUENCE {
	wgVpnPTServerPolicyId       Integer32,
	wgVpnPTServerIpAddress      IpAddress,
	wgVpnPTServerRowStatus      INTEGER
}

wgVpnPTServerPolicyId OBJECT-TYPE
	SYNTAX  Integer32
	MAX-ACCESS  read-only
	STATUS  current
	DESCRIPTION
		"VPN pass through policy identifier. It must be greater than zero."
	::= { wgVpnPTServerEntry 1 }

wgVpnPTServerIpAddress OBJECT-TYPE
	SYNTAX  IpAddress
	MAX-ACCESS  read-only
	STATUS  current
	DESCRIPTION
		"VPN server IP address."
	::= { wgVpnPTServerEntry 2 }

wgVpnPTServerRowStatus OBJECT-TYPE
	SYNTAX  INTEGER {
		other(1),
		valid(2),
		delete(3),
		create(4)
		}
	MAX-ACCESS  read-write
	STATUS  current
	DESCRIPTION
		"Create or delete a row of VPN pass through server table."
	::= { wgVpnPTServerEntry 3 }


--
-- VPN Pass Through Filter Table
--

wgVpnPTFilterTable OBJECT-TYPE
	SYNTAX SEQUENCE OF WgVpnPTFilterEntry
	MAX-ACCESS not-accessible
	STATUS current
	DESCRIPTION
		"VPN pass through filter table"
	::= { snWireless 6 }

wgVpnPTFilterEntry OBJECT-TYPE
	SYNTAX WgVpnPTFilterEntry
	MAX-ACCESS not-accessible
	STATUS current
	DESCRIPTION
		"An entry of the VPN pass through filter table."
	INDEX { wgVpnPTFilterPolicyId, wgVpnPTFilterProtocol, wgVpnPTFilterPort }
	::= { wgVpnPTFilterTable 1 }

WgVpnPTFilterEntry ::= SEQUENCE {
	wgVpnPTFilterPolicyId       Integer32,
	wgVpnPTFilterProtocol       INTEGER,
	wgVpnPTFilterPort           Integer32,
	wgVpnPTFilterRowStatus      INTEGER
}

wgVpnPTFilterPolicyId OBJECT-TYPE
	SYNTAX  Integer32
	MAX-ACCESS  read-only
	STATUS  current
	DESCRIPTION
		"VPN pass through policy identifier. It must be greater than zero."
	::= { wgVpnPTFilterEntry 1 }

wgVpnPTFilterProtocol OBJECT-TYPE
	SYNTAX  INTEGER {
		other(1),
		udp(2),
		tcp(3)
		}
	MAX-ACCESS  read-only
	STATUS  current
	DESCRIPTION
		"Allow this type of protocol to pass through."
	::= { wgVpnPTFilterEntry 2 }

wgVpnPTFilterPort OBJECT-TYPE
	SYNTAX  Integer32
	MAX-ACCESS  read-only
	STATUS  current
	DESCRIPTION
		"Allow this protocol port to pass through."
	::= { wgVpnPTFilterEntry 3 }

wgVpnPTFilterRowStatus OBJECT-TYPE
	SYNTAX  INTEGER {
		other(1),
		valid(2),
		delete(3),
		create(4)
		}
	MAX-ACCESS  read-write
	STATUS  current
	DESCRIPTION
		"Create or delete a row of VPN pass through filter table."
	::= { wgVpnPTFilterEntry 4 }

--
-- VPN Pass Through Policy Table
--

wgVpnPTPolicyTable OBJECT-TYPE
	SYNTAX SEQUENCE OF WgVpnPTPolicyEntry
	MAX-ACCESS not-accessible
	STATUS current
	DESCRIPTION
		"VPN pass through policy table"
	::= { snWireless 7 }

wgVpnPTPolicyEntry OBJECT-TYPE
	SYNTAX WgVpnPTPolicyEntry
	MAX-ACCESS not-accessible
	STATUS current
	DESCRIPTION
		"An entry of the VPN pass through policy table."
	INDEX { wgVpnPTPolicyId }
	::= { wgVpnPTPolicyTable 1 }

WgVpnPTPolicyEntry ::= SEQUENCE {
	wgVpnPTPolicyId        Integer32,
	wgVpnPTPolicyPortList  IfIndexList
}

wgVpnPTPolicyId OBJECT-TYPE
	SYNTAX  Integer32
	MAX-ACCESS  read-only
	STATUS  current
	DESCRIPTION
		"VPN pass through policy identifier. It must be greater than zero."
	::= { wgVpnPTPolicyEntry 1 }

wgVpnPTPolicyPortList OBJECT-TYPE
	SYNTAX  IfIndexList
	MAX-ACCESS  read-only
	STATUS  current
	DESCRIPTION
		"A list of ports bound to this VPN pass through policy."
	::= { wgVpnPTPolicyEntry 2 }

END
