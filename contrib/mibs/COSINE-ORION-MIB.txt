COSINE-ORION-MIB DEFINITIONS ::= BEGIN

   IMPORTS
	MODULE-IDENTITY, OBJECT-TYPE, Counter32, Gauge32, 
	Unsigned32, Integer32, TimeTicks, IpAddress,
	NOTIFICATION-TYPE		 FROM SNMPv2-SMI
	TEXTUAL-CONVENTION, DisplayString,
	PhysAddress, MacAddress, RowStatus, 
	TestAndIncr, TimeStamp, TruthValue, TimeInterval    FROM SNMPv2-TC
	csModules, csOrionMIB  			    FROM COSINE-GLOBAL-REG;
 


   cosineOrionMod MODULE-IDENTITY
	LAST-UPDATED "0008240252Z"
	ORGANIZATION "CoSine Communications, Inc."
	CONTACT-INFO
		"   CoSine Communications, Inc.
		    1200 Bridge Parkway
		    Redwood City, California 94065
		    USA

		    650-637-4777
		    info@cosinecom.com
		    www.cosinecom.com"
	DESCRIPTION
		"The MIB module to describe generic objects for
		IPNOS system. "
	REVISION "0102280332Z"
	DESCRIPTION
		"Revised for IPNOS version 2.1 ."
	REVISION "9909071355Z"
	DESCRIPTION
		"Initial revision."
	::= { csModules 2 }


    LongDisplayString ::= TEXTUAL-CONVENTION
	STATUS	current
	DESCRIPTION   
		"Use this instead of DisplayString for ASCII string
		that is longer than 255."
	SYNTAX	OCTET STRING (SIZE(0..1024))

    OperStatus ::= TEXTUAL-CONVENTION
	STATUS	current
	DESCRIPTION   
		"Available operational states for the object (e.g. VPN, 
		Virtual Router, Virtual Interface, etc.).  This is used
		to provide additional granularity beyond that provided
		by RowStatus."
	SYNTAX	INTEGER {
		       operationallyDown	(1),
		       initializing 		(2),
		       operationallyUp 		(3),
		       faultRecovery 		(4),
			   testing				(5),
			   unknown				(6)
	}


      OperState ::= TEXTUAL-CONVENTION
           STATUS       current
           DESCRIPTION
                 "Type used in enabling and disabling a row."
           SYNTAX       INTEGER
                         {
                          off(1),
                          on(2)
                         }

	PerfCurrentCount ::= TEXTUAL-CONVENTION
	STATUS  current
	DESCRIPTION
			  "A counter associated with a performance 
			   measurement in a current 15
               minute measurement interval. The value
               of this counter starts from zero and is
               increased when associated events occur,
               until the end of the 15 minute interval.
               At that time the value of the counter is
               stored in the first 15 minute history
               interval, and the CurrentCount is
               restarted at zero. In the
               case where the agent has no valid data
               available for the current interval the
               corresponding object instance is not
               available and upon a retrieval request
               a corresponding error message shall be
               returned to indicate that this instance
               does not exist (for example, a noSuchName
               error for SNMPv1 and a noSuchInstance for
               SNMPv2 GET operation)."
	SYNTAX  Gauge32


    PerfIntervalCount ::= TEXTUAL-CONVENTION
    STATUS  current
    DESCRIPTION
              "A counter associated with a
               performance measurement in a previous
               15 minute measurement interval. In the
               case where the agent has no valid data
               available for a particular interval the
               corresponding object instance is not
               available and upon a retrieval request
               a corresponding error message shall be
               returned to indicate that this instance
               does not exist (for example, a noSuchName
               error for SNMPv1 and a noSuchInstance for
               SNMPv2 GET operation).
               In a system supporting
               a history of n intervals with
               IntervalCount(1) and IntervalCount(n) the
               most and least recent intervals
               respectively, the following applies at
               the end of a 15 minute interval:
               - discard the value of IntervalCount(n)
               - the value of IntervalCount(i) becomes that
                 of IntervalCount(i-1) for n >= i > 1
               - the value of IntervalCount(1) becomes that
                 of CurrentCount
               - the TotalCount, if supported, is adjusted."
    SYNTAX  Gauge32


    PerfTotalCount ::= TEXTUAL-CONVENTION
    STATUS  current
    DESCRIPTION
              "A counter associated with a
               performance measurements aggregating the
               previous valid 15 minute measurement
               intervals. (Intervals for which no valid
               data was available are not counted)"
    SYNTAX  Gauge32

	
	OrionIfIndex ::= TEXTUAL-CONVENTION
	STATUS	current
	DESCRIPTION
			"ifIndex for the interface table of the mib-2 is redefined here. The 32-bit integer is
			organized as below to easily locate an interface in an Orion box.
			+---------+----------+-------------+-----------------+----------------------+
			|Reserved |          |	           |                 |                      |
			|(always0)| slot #   |port #       |    channel #    |       subif #        |
			|1-bit    | 5-bits   |6-bits       |     8-bits      |       12-bits        |
			+---------+----------+-------------+-----------------+----------------------+
			In the case of channelized and un-channelized DS3 blades, subif #4095, refers to
			the PPP/CiscoHDLC interfaces encapsulted on a channel/port. If the encpsulation is
			Frame Relay, subif 16-4094 refers to Dlcis' an the subid #4095 refers to the Dlcmi
			on a channel. Whereever one of those components of ifIndex(slot/port/chan/subif) doesn't
			make sense, it should be Zero. For example, in the case of an ethernet blade, only the
			slot and port are the valid fields. Other will be zero.
			So, the interfeaces in an Orion box are sorted in their order of presence with respect 
			to the slot,port,channel and subif compoinents."
	SYNTAX	Integer32
	
	AtmVcIdentifier ::= TEXTUAL-CONVENTION
        STATUS  current
        DESCRIPTION
            "The VCI value for a VCL. The maximum VCI value
            cannot exceed the value allowable by
            atmInterfaceMaxVciBits defined in ATM-MIB."
        SYNTAX   INTEGER (0..65535)


	AtmVpIdentifier ::= TEXTUAL-CONVENTION
        STATUS  current
        DESCRIPTION
            "The VPI value for a VPL or VCL. The value VPI=0
            is only allowed for a VCL. For ATM UNIs supporting
            VPCs the VPI value ranges from 0 to 255.  The VPI
            value 0 is supported for ATM UNIs conforming to
            the ATM Forum UNI 4.0 Annex 8 (Virtual UNIs)
            specification. For ATM UNIs supporting VCCs the
            VPI value ranges from 0 to 255.  For ATM NNIs the
            VPI value ranges from 0 to 4095.  The maximum VPI
            value cannot exceed the value allowable by
            atmInterfaceMaxVpiBits defined in ATM-MIB."
        SYNTAX    INTEGER (0..4095)


	AtmServiceCategory ::= TEXTUAL-CONVENTION
        STATUS  current
        DESCRIPTION
            "The service category for a connection."
        REFERENCE
            "ATM Forum Traffic Management Specification,
            Version 4.0, af-tm-0056.000, June 1996."
        SYNTAX   INTEGER {
           other(1),   -- none of the following
           cbr(2),     -- constant bit rate
           rtVbr(3),   -- real-time variable bit rate
           nrtVbr(4),  -- non real-time variable bit rate
           abr(5),     -- available bit rate
           ubr(6)      -- unspecified bit rate
           }


    SPPBaudRate ::= TEXTUAL-CONVENTION
        STATUS  current
        DESCRIPTION
            "The baud rate of a Status Panel port."
        REFERENCE
            "None"
        SYNTAX   INTEGER {
           baud50(1),        -- 50 baud
           baud75(2),        -- 75 baud
           baud110(3),       -- 110 baud
           baud134Dot5(4),   -- 134.5 baud
           baud150(5),       -- 150 baud
           baud300(6),       -- 300 baud
           baud600(7),       -- 600 baud
           baud1200(8),      -- 1200 baud
           baud1800(9),      -- 1800 baud
           baud2000(10),     -- 2000 baud
           baud2400(11),     -- 2400 baud
           baud3600(12),     -- 3600 baud
           baud3800(13),     -- 3800 baud
           baud7200(14),     -- 7200 baud
           baud9600(15),     -- 9600 baud
           baud19200(16),    -- 19200 baud
           baud38400(17),    -- 38400 baud
           baud56000(18),    -- 57600 baud
           baud128000(19)    -- 128000 baud
        }



    SPPLoopbackStatus ::= TEXTUAL-CONVENTION
        STATUS  current
        DESCRIPTION
            "The loopback status of a Status Panel port."
        REFERENCE
            "None"
        SYNTAX   INTEGER {
           noLoop(1),     -- no loopback
           ccmLoop(2),    -- on blade loopback in CCM
           spLoop(3)      -- loopback at Status Panel
        }


    SPPModemStatus ::= TEXTUAL-CONVENTION
        STATUS  current
        DESCRIPTION
            "Indicates whether a modem is connected to a Service Panel port." 
        REFERENCE
            "None"
        SYNTAX   INTEGER {
           modemConnected(1),      -- modem connected
           modemNotConnected(2)   -- modem not connected
        }


    SPPRedundantStatus ::= TEXTUAL-CONVENTION
        STATUS  current
        DESCRIPTION
            "???? Ask Bev ????" 
        REFERENCE
            "None"
        SYNTAX   INTEGER {
           master(1),      -- master
           standby(2)      -- standby
        }




    EvLogLevel ::= TEXTUAL-CONVENTION
    STATUS  current
    DESCRIPTION
              "This specifies the level of detail for the
               event log."
    SYNTAX  INTEGER {
        none(0),                -- no event is logged
        critical(100),          -- unrecoverable service affecting event
        major(200),             -- service affecting event
        minor(300),             -- gross configuration errors etc.
        informational(400),     -- debug configuration errors
        debug(500)              -- general debugging messages
        }

    EvLogArea ::= TEXTUAL-CONVENTION
    STATUS  current
    DESCRIPTION
              "This is a bitmap where each bit represents the area that
               the event log belongs to.

                        area                    bit
                ------------------------------------------------------
                        trap                    0
                        emergency               1
                        system                  2
                        authentication          3
                        application             4
                        protocol                5
                        ipsec/ike               6
                        link                    7
                        configuration           8
               "
    SYNTAX  Integer32

-- An MPLS label.
    MplsLabel ::= TEXTUAL-CONVENTION
       STATUS        current
       DESCRIPTION
     	  "Represents an MPLS label.  Note that the contents of
      	  a  label  field are interpreted in an interface-type
      	  specific fashion.  For example, the label carried in
      	  the MPLS shim header is 20 bits wide and the top  12
      	  bits  must  be zero.  The frame relay label  can  be
      	  either 10, 17 or 23 bits wide depending on the  size
      	  of the DLCI field size and the top 22, 15, or 9 bits
      	  must  be  zero, respectively.  For an ATM interface,
      	  the  lowermost 16 bits are interpreted as  the  VCI,
      	  the  next  8 bits as the VPI and the remaining  bits
      	  must  be  zero.   Also  note the  permissible  label
       	  values  are  also a function of the interface  type.
          For  example,  the value 3 has special semantics  in
          the  control plane for an MPLS shim header label and
          is not a valid label value in the datapath."
      REFERENCE
          "1.  MPLS  Label Stack Encoding, Rosen et al,  draft-
           ietf-mpls-label-encaps-04.txt, April 1999.
           2.  Use  of  Label Switching on Frame Relay Networks,
           Conta et al, draft-ietf-mpls-fr-03.txt, Nov. 1998."
      SYNTAX Integer32


------------------------------------------------------------------------------
--
--	      	Groups in the ORION Private MIB  
--
------------------------------------------------------------------------------

    csOrionEvents		OBJECT IDENTIFIER ::= { csOrionMIB 1 }
    csOrionSystem		OBJECT IDENTIFIER ::= { csOrionMIB 2 }
	csOrionGeneralSys	OBJECT IDENTIFIER ::= { csOrionSystem 1 }
	csOrionBoot		OBJECT IDENTIFIER ::= { csOrionSystem 2 }
	csOrionLogin		OBJECT IDENTIFIER ::= { csOrionSystem 3 }
	csOrionModem		OBJECT IDENTIFIER ::= { csOrionSystem 4 }
	csOrionConfig		OBJECT IDENTIFIER ::= { csOrionSystem 5 }
	csOrionConfigSave	OBJECT IDENTIFIER ::= { csOrionConfig 1 }
	csOrionConfigLoad	OBJECT IDENTIFIER ::= { csOrionConfig 2 }
	csOrionFileSys		OBJECT IDENTIFIER ::= { csOrionSystem 6 }
	csOrionChassisInfo	OBJECT IDENTIFIER ::= { csOrionSystem 7 }
    csOrionPortInfo		OBJECT IDENTIFIER ::= { csOrionMIB 3 }
	csOrionEthInfo		OBJECT IDENTIFIER ::= { csOrionPortInfo 1 }
	csOrionDs3Info		OBJECT IDENTIFIER ::= { csOrionPortInfo 2 }
	csOrionOc3Info		OBJECT IDENTIFIER ::= { csOrionPortInfo 3 }
	csOrionFrInfo		OBJECT IDENTIFIER ::= { csOrionPortInfo 4 }
	csAtmInfo			OBJECT IDENTIFIER ::= { csOrionPortInfo 5 }
	csPOSInfo			OBJECT IDENTIFIER ::= { csOrionPortInfo 6 }
    csOrionVPNInfo		OBJECT IDENTIFIER ::= { csOrionMIB 4 }
    csOrionBladeInfo 		OBJECT IDENTIFIER ::= { csOrionMIB 5 }
    csOrionServiceInfo		OBJECT IDENTIFIER ::= { csOrionMIB 6 }
	csOrionAccessListInfo	OBJECT IDENTIFIER ::= { csOrionServiceInfo 1 }
	csOrionFWInfo		OBJECT IDENTIFIER ::= { csOrionServiceInfo 2 }
	csOrionPktFilterInfo	OBJECT IDENTIFIER ::= { csOrionServiceInfo 3 }
	csOrionNatInfo		OBJECT IDENTIFIER ::= { csOrionServiceInfo 4 }
	csOrionEncryptInfo	OBJECT IDENTIFIER ::= { csOrionServiceInfo 5 }
	csOrionQueueInfo	OBJECT IDENTIFIER ::= { csOrionServiceInfo 6 }
	csOrionPppInfo		OBJECT IDENTIFIER ::= { csOrionServiceInfo 7 }
	csOrionPptpInfo		OBJECT IDENTIFIER ::= { csOrionServiceInfo 8 }
	csOrionRadiusInfo	OBJECT IDENTIFIER ::= { csOrionServiceInfo 9 }
	csOrionDNSInfo		OBJECT IDENTIFIER ::= { csOrionServiceInfo 10 }
	csOrionCiscoHdlcInfo	OBJECT IDENTIFIER ::= { csOrionServiceInfo 11 }
	csOrionFRoIPInfo	OBJECT IDENTIFIER ::= { csOrionServiceInfo 12 }
	csOrionL2tpInfo		OBJECT IDENTIFIER ::= { csOrionServiceInfo 13 }
	csOrionQosInfo		OBJECT IDENTIFIER ::= { csOrionServiceInfo 14 }
    csOrionDHCPInfo    OBJECT IDENTIFIER ::= { csOrionServiceInfo 15 }
	csOrionDHCPRelayInfo    OBJECT IDENTIFIER ::= { csOrionDHCPInfo 1}
	csOrionMlpppInfo        OBJECT IDENTIFIER ::= { csOrionServiceInfo 16 }
	csOrionPppoeInfo	OBJECT IDENTIFIER ::= { csOrionServiceInfo 17 }
	csOrionServiceSelectionInfo    OBJECT IDENTIFIER ::= { csOrionServiceInfo 18 }
	csOrionNBNSInfo		OBJECT IDENTIFIER ::= { csOrionServiceInfo 19 }
        csOrionHWControlInfo	OBJECT IDENTIFIER ::= { csOrionMIB 7 }
	csOrionPowerSupplyControlInfo	OBJECT IDENTIFIER ::= { csOrionHWControlInfo 3 }
	csOrionStatusPanelControlInfo	OBJECT IDENTIFIER ::= { csOrionHWControlInfo 6 }
        csOrionTemperatureAirFlowCardInfo    OBJECT IDENTIFIER ::= { csOrionHWControlInfo 7 }
    csOrionBackplaneInfo	OBJECT IDENTIFIER ::= { csOrionMIB 8 }
    csOrionSnmpInfo		OBJECT IDENTIFIER ::= { csOrionMIB 9 }
	csOrionGenSnmp		OBJECT IDENTIFIER ::=	{ csOrionSnmpInfo 1 }
	csOrionTrapInfo		OBJECT IDENTIFIER ::=	{ csOrionSnmpInfo 2 }
    csOrionAcctInfo		OBJECT IDENTIFIER ::= { csOrionMIB 10 }
	csOrionStaticConn	OBJECT IDENTIFIER ::=	{ csOrionAcctInfo 1 }
	csOrionDynamicConn	OBJECT IDENTIFIER ::=	{ csOrionAcctInfo 2 }
    csTelnetSvrInfo		OBJECT IDENTIFIER ::= { csOrionMIB 11 }
    csOrionSyslogd  	       	OBJECT IDENTIFIER ::= { csOrionMIB 12 }
    csOrionHWNotifyInfo         OBJECT IDENTIFIER ::= { csOrionMIB 13 }
    csOrionStatusPanelInfo	OBJECT IDENTIFIER ::= { csOrionMIB 14}


------------------------------------------------------------------------------
--
-- 		The System group contains information about the entity.
--
------------------------------------------------------------------------------

    csOrionSystemIpAddress OBJECT-TYPE
 	SYNTAX	IpAddress 
 	MAX-ACCESS  read-write
	STATUS	current
	DESCRIPTION
		"A system Ip address."
	::= { csOrionGeneralSys 1 }

    csOrionSystemNetMask OBJECT-TYPE
 	SYNTAX	IpAddress 
 	MAX-ACCESS  read-write
	STATUS	current
	DESCRIPTION
		"A system network mask."
	::= { csOrionGeneralSys 2 }

    csOrionSystemGatewayAddress OBJECT-TYPE
	SYNTAX	IpAddress 
	MAX-ACCESS  read-write
	STATUS	current
	DESCRIPTION
		"A system default gateway address."
	::= { csOrionGeneralSys 3 }

    csOrionSystemFwVer OBJECT-TYPE
	SYNTAX	DisplayString 
	MAX-ACCESS read-only
	STATUS 	 current
	DESCRIPTION  " The fw version used by Orion"
	::= { csOrionGeneralSys 4}

    csOrionSystemMajorVer OBJECT-TYPE
	SYNTAX	DisplayString 
	MAX-ACCESS read-only
	STATUS 	 current
	DESCRIPTION  " The version for a Orion as a system."
	::= { csOrionGeneralSys 5}

    csOrionSystemNumberOfBlades OBJECT-TYPE
	SYNTAX 	Integer32 (0..26)
	MAX-ACCESS read-only
	STATUS 	current
	DESCRIPTION  ""
	::= { csOrionGeneralSys 6}

    csOrionSystemTempStatus OBJECT-TYPE
	SYNTAX INTEGER {
		normal (1),
		hot    (2)
	}
	MAX-ACCESS read-only
	STATUS current
	DESCRIPTION
		"This object identifies the current temperature status
		within the Orion system.  If this object has the value
		normal(1), the temperature is within the normal range.
		If the status is hot(2), the temperature is above the
		normal range and measures should be taken to bring the
		temperature down."
	::= { csOrionGeneralSys 7}

	csOrionSystemReset OBJECT-TYPE
	SYNTAX 	INTEGER {
		none	(1),
		reset	(2)
	}
	MAX-ACCESS read-write
	STATUS 	current
	DESCRIPTION  "The software reset. It is an action object such 
		that when set to 'reset' will reset all the blades. 
		Setting it to 'none' has no effect, and when it is retrieved 
		the value will always be 'none' . "
	::= { csOrionGeneralSys 8}

	csOrionSystemTime OBJECT-TYPE
         SYNTAX  DisplayString (SIZE (0..50)) 
         MAX-ACCESS   read-write
         STATUS   current
         DESCRIPTION
            "To set the system date & time with the standard format 
             specified by RFC 2579. Below is the date-time specification. 
		     (Display Format: YYYY-MM-DD,HH:MM:SS.ss,+/-:HH:MM) 
				

            field    contents                  range
            -----    --------                  -----
              1       year*                     1999..2098
              2       month                     1..12
              3       day                       1..31
              4       hour                      0..23
              5       minutes                   0..59
              6       seconds                   0..60
                      (use 60 for leap-second)
              7       deci-seconds              0..9
              8       direction from UTC        '+' / '-'
              9       hours from UTC*           0..13
             10       minutes from UTC          0..59

            * Notes:
            - the value of year is in network-byte order
            - daylight saving time in New Zealand is +13

            For example, Tuesday May 26, 2000 at 1:30:15 PM EDT would be

            displayed as: 2000-5-26,13:30:15.0,-4:0
		Note that if only local time is known, then timezone
            	information (fields 8-10) is not present.
	
            "
         ::= { csOrionGeneralSys 9}


   csOrionSystemVersionNum OBJECT-TYPE
       SYNTAX  DisplayString
       MAX-ACCESS read-only
       STATUS   current
       DESCRIPTION
           "The system version number applies to the IPSX system
            as a whole.  This number has the format:

                a.b.c.d

            where 'a.b' is major release number, 'c' is the patch
            nubmer, and 'd' is the internal release number."
       ::= { csOrionGeneralSys 10}

	csOrionSystemShutdown OBJECT-TYPE
	SYNTAX 	INTEGER {
		none	(1),
		shutdown	(2)
	}
	MAX-ACCESS read-write
	STATUS 	current
	DESCRIPTION  "The software shutdown. It is an action object such 
		that when set to 'shutdown' will stop the file-system of all the blades.
		that when set to 'shutdown' will stop the file-system of all the blades. 
		Setting it to 'none' has no effect, and when it is retrieved 
		the value will always be 'none' . "
	::= { csOrionGeneralSys 11}

	csOrionSystemControlBladeFailOver OBJECT-TYPE
	SYNTAX 	INTEGER {
		none		(1),
		failover	(2)
	}
	MAX-ACCESS read-write
	STATUS 	current
	DESCRIPTION  "When set to 'failover', the master control blade 
		switches over to stand-by control blade.  
		Setting it to 'none' has no effect, and when it is retrieved 
		the value will always be 'none' . "
	::= { csOrionGeneralSys 12}

------------------------------------------------------------------------------
--
-- 		The Orion Boot Table
--
------------------------------------------------------------------------------

    csOrionSystemBootTable OBJECT-TYPE
	SYNTAX	SEQUENCE OF CsOrionSystemBootEntry
	MAX-ACCESS  not-accessible
	STATUS	current
	DESCRIPTION
		"A list of Sources from which this Orion will boot."
	::= { csOrionBoot 1 }

    csOrionSystemBootEntry OBJECT-TYPE
	SYNTAX 	 CsOrionSystemBootEntry
	MAX-ACCESS  not-accessible
	STATUS	current
	DESCRIPTION
		"An entry containing Boot information applicable
		to this Orion System.  Note, currently there is only
		one entry in this table.  More entries may be added
		in future releases."
	INDEX   { csOrionSystemBootIndex }

	::= { csOrionSystemBootTable 1 }

    CsOrionSystemBootEntry ::=
	SEQUENCE {
	csOrionSystemBootIndex	
		Integer32,
	csOrionSystemBootImageName1 
		DisplayString,
	csOrionSystemBootImageName2
		DisplayString,
	csOrionSystemBootImageName3 
		DisplayString,
	csOrionSystemBootImageName4 
		DisplayString,
	csOrionSystemBootImageName5 
		DisplayString,
	csOrionSystemBootImageName6 
		DisplayString,
	csOrionSystemBootPort
		Integer32,
	csOrionSystemBootServerAddress     
		IpAddress,
	csOrionSystemBootLocalIpAddr
		IpAddress,
	csOrionSystemBootLocalIpMask
		IpAddress,
	csOrionSystemBootDefGw
		IpAddress,
	csOrionSystemBootConfig 
		DisplayString,
	csOrionSystemBootSaveImage
		INTEGER
	}

    csOrionSystemBootIndex OBJECT-TYPE
	SYNTAX	Integer32 (1..2147483647)
	MAX-ACCESS  not-accessible
	STATUS	current
	DESCRIPTION
	    "A  unique value, greater than zero, for each
	    boot record."
	::= { csOrionSystemBootEntry 1 }

    csOrionSystemBootImageName1 OBJECT-TYPE
	SYNTAX	DisplayString (SIZE (0..50))
	MAX-ACCESS	read-write
	STATUS		current
	DESCRIPTION  "The absolute path and file name for the boot image.
		     If this string is prefaced with 'FLSH', tftp will
		     be used to boot over the network.  This applies to
		     all 6 images."
	::= { csOrionSystemBootEntry 2}

    csOrionSystemBootImageName2 OBJECT-TYPE
	SYNTAX	DisplayString (SIZE (0..50))
	MAX-ACCESS	read-write
	STATUS		current
	DESCRIPTION  " The 2nd absolute path and file name for the boot image.
		     This will be used only if the previous boot images fail."
	::= { csOrionSystemBootEntry 3}

    csOrionSystemBootImageName3 OBJECT-TYPE
	SYNTAX	DisplayString (SIZE (0..50))
	MAX-ACCESS	read-write
	STATUS		current
	DESCRIPTION  " The 3rd absolute path and file name for the boot image.
		     This will be used only if the previous boot images fail."
	::= { csOrionSystemBootEntry 4}

    csOrionSystemBootImageName4 OBJECT-TYPE
	SYNTAX	DisplayString (SIZE (0..50))
	MAX-ACCESS	read-write
	STATUS		current
	DESCRIPTION  " The 4th absolute path and file name for the boot image.
		     This will be used only if the previous boot images fail."
	::= { csOrionSystemBootEntry 5}

    csOrionSystemBootImageName5 OBJECT-TYPE
	SYNTAX	DisplayString (SIZE (0..50))
	MAX-ACCESS	read-write
	STATUS		current
	DESCRIPTION  " The 5th absolute path and file name for the boot image.
		     This will be used only if the previous boot images fail."
	::= { csOrionSystemBootEntry 6}

    csOrionSystemBootImageName6 OBJECT-TYPE
	SYNTAX	DisplayString (SIZE (0..50))
	MAX-ACCESS	read-write
	STATUS		current
	DESCRIPTION  " The 6th absolute path and file name for the boot image.
		     This will be used only if the previous boot images fail."
	::= { csOrionSystemBootEntry 7}

    csOrionSystemBootPort OBJECT-TYPE
	SYNTAX Integer32 (1..8)
	MAX-ACCESS  read-write
	STATUS 	current
	DESCRIPTION  
	    "When booting over the network, the port used to load the image"
	::= { csOrionSystemBootEntry 8}

    csOrionSystemBootServerAddress OBJECT-TYPE
	SYNTAX		IpAddress
	MAX-ACCESS	read-write
	STATUS		current
	DESCRIPTION  " A boot server Ip Address.  Note, this only applies if
	    this entry specifies booting over the network."
	::= { csOrionSystemBootEntry 9}

    csOrionSystemBootLocalIpAddr OBJECT-TYPE
	SYNTAX		IpAddress
	MAX-ACCESS	read-write
	STATUS		current
	DESCRIPTION  " When booting over the network using a boot protocol 
	    that does not supply a source IP address, This object 
	    specifies the local IP address to use when booting via the network."
	::= { csOrionSystemBootEntry 10}

    csOrionSystemBootLocalIpMask OBJECT-TYPE
	SYNTAX		IpAddress
	MAX-ACCESS	read-write
	STATUS		current
	DESCRIPTION  " When booting over the network using a boot protocol 
	    that does not supply a source IP address, This object 
	    specifies the local IP address mask to use when booting via the network."
	::= { csOrionSystemBootEntry 11}


    csOrionSystemBootDefGw OBJECT-TYPE
	SYNTAX		IpAddress
	MAX-ACCESS	read-write
	STATUS		current
	DESCRIPTION  " When booting over the network, this object is used
	    to identify the gateway to use in communicating with
	    the boot server."
	::= { csOrionSystemBootEntry 12}


    csOrionSystemBootConfig OBJECT-TYPE
	SYNTAX	DisplayString (SIZE (0..30))
	MAX-ACCESS	read-write
	STATUS		current
	DESCRIPTION  
	    "The absolute path and file name for the configuration
	    file.  Note, the configuration file must be on the local flash."
	::= { csOrionSystemBootEntry 13}

    csOrionSystemBootSaveImage OBJECT-TYPE
	SYNTAX		INTEGER {
		enabled		(1),
		disabled 	(2)
	}
	MAX-ACCESS	read-write
	STATUS		current
	DESCRIPTION  
	    "This object specifies whether the IPSX system will
	    save the boot image in local flash.  Note this applies
	    only if the csOrionSystemBootProtocol is tftp(2)."
	::= { csOrionSystemBootEntry 14}

------------------------------------------------------------------------------
--
-- 		The Orion Login Table
--
------------------------------------------------------------------------------

    csOrionSystemLoginTable OBJECT-TYPE
	SYNTAX	SEQUENCE OF CsOrionSystemLoginEntry
	MAX-ACCESS  not-accessible
	STATUS	current
	DESCRIPTION
		"A login information for Orion, using console or telnet."
	::= { csOrionLogin 1 }

    csOrionSystemLoginEntry OBJECT-TYPE
	SYNTAX 	 CsOrionSystemLoginEntry
	MAX-ACCESS  not-accessible
	STATUS	current
	DESCRIPTION
		"An entry containing management information applicable
		to a particular interface or management Blade."
	INDEX   { csOrionSystemLoginIndex }
	::= { csOrionSystemLoginTable 1 }

    CsOrionSystemLoginEntry ::=
	SEQUENCE {
	csOrionSystemLoginIndex	
		Integer32,
	csOrionSystemLoginName     
		DisplayString,
	csOrionSystemLoginPassword    
		DisplayString,
	csOrionSystemLoginIdleTimeout    
		Integer32,
	csOrionSystemLoginRowStatus
		RowStatus,
	csOrionSystemLoginOperStatus
		OperStatus
	}

    csOrionSystemLoginIndex OBJECT-TYPE
	SYNTAX	Integer32 (1..2147483647)
	MAX-ACCESS  not-accessible
	STATUS	current
	DESCRIPTION
		"A  unique value, greater than zero, for each
		login record."
	::= { csOrionSystemLoginEntry 1 }

    csOrionSystemLoginName OBJECT-TYPE
	SYNTAX	DisplayString 
	MAX-ACCESS  read-create
	STATUS 	current
	DESCRIPTION  " "
	::= { csOrionSystemLoginEntry 2}

    csOrionSystemLoginPassword OBJECT-TYPE
	SYNTAX	DisplayString (SIZE (8..80))
	MAX-ACCESS  read-create
	STATUS 	    current
	DESCRIPTION  
		"A sequence of alphabetical and numerical characters,
		 MUST not be less than 8 characters."
	    ::= { csOrionSystemLoginEntry 3}

    csOrionSystemLoginIdleTimeout OBJECT-TYPE
	SYNTAX	Integer32 (0..600)
	MAX-ACCESS  read-create
	STATUS 	current
	DESCRIPTION  " An idle timeout after which system logs current user out."
	::= { csOrionSystemLoginEntry 4}

    csOrionSystemLoginRowStatus OBJECT-TYPE
	SYNTAX		RowStatus 
	MAX-ACCESS	read-create
	STATUS		current
	DESCRIPTION
		"A row status type for the table entry."
	::= {csOrionSystemLoginEntry 5 }

    csOrionSystemLoginOperStatus OBJECT-TYPE
	SYNTAX		OperStatus
	MAX-ACCESS	read-only
	STATUS		current
	DESCRIPTION
		"A operational status for this table entry."
	::= { csOrionSystemLoginEntry 6 }

------------------------------------------------------------------------------
--
-- 		The Orion Modem Group
--
------------------------------------------------------------------------------

    csOrionModemControl OBJECT-TYPE
	SYNTAX		INTEGER {
		enable  (1),
		disable (2)
	}
	MAX-ACCESS	read-write
	STATUS		current
	DESCRIPTION
	       "This object controls access to this device via Dial In modem."
	::= { csOrionModem 1 }

    csOrionModemBaud OBJECT-TYPE
	SYNTAX		Integer32
	MAX-ACCESS	read-write
	STATUS		current
	DESCRIPTION
	       "This object sets the target baud rate of the modem connection."
	::= { csOrionModem 2 }

    csOrionModemFlowCtl OBJECT-TYPE
	SYNTAX		INTEGER {
		hardware (1),
		software (2)
	}
	MAX-ACCESS	read-write
	STATUS		current
	DESCRIPTION
	       "This object specifies the type of flow control used by the
	       modem."
	::= { csOrionModem 3 }

    csOrionModemConnectWait OBJECT-TYPE
	SYNTAX		Integer32
	MAX-ACCESS	read-write
	STATUS		current
	DESCRIPTION
	       "This object sets the length of time, in seconds, the modem will 
	       wait for a connection."
	::= { csOrionModem 4 }


------------------------------------------------------------------------------
--
--		Orion Config group
--
------------------------------------------------------------------------------

-- Saving Configuration to a File

    csOrionConfigSaveFileName OBJECT-TYPE
	SYNTAX		DisplayString (SIZE(0..20))
	MAX-ACCESS	read-write
	STATUS		current
	DESCRIPTION
	       "This object is used when the save configuration is launched on an Orion 
		   box by setting the csOrionConfigSave object. The device handle the default
		   value for this object. When this object is not set, the device look for 
		   the csOrionSystemBootConfig of the csOrionSystemBootTable. If that is not
		   NULL, that name is used as the file name. Otherwise the default filename of
		   config.dat is used."
	::= { csOrionConfigSave 1 }

    csOrionConfigSaveStart OBJECT-TYPE
	SYNTAX		INTEGER {
		save  (1),
		none (2)
	}
	MAX-ACCESS	read-write
	STATUS		current
	DESCRIPTION
	       "This object triggers the configuration saving on the divice. The result of this
		   action is stored in csOrionConfigSaveStatus."
	::= { csOrionConfigSave 2 }

    csOrionConfigSaveStatus OBJECT-TYPE
	SYNTAX		INTEGER {
		none  (1),
		saveInProgress (2),
		saveSuccess (3),
		saveFailed (4)
	}
	MAX-ACCESS	read-only
	STATUS		current
	DESCRIPTION
	       "This object triggers the configuration saving on the divice. The result of this
		   action is stored in csOrionConfigSaveStatus."
	::= { csOrionConfigSave 3 }

    csOrionConfigLoadOutputEnable OBJECT-TYPE
	SYNTAX INTEGER {
		enable  (1),
		disable (2)
	}
	MAX-ACCESS	read-write
	STATUS		current
	DESCRIPTION
	       "This object controls whether output from loading configuration
		file should be printed out to the console.

		Loading configuration will be quicker if this object is
		disabled."
	DEFVAL  { enable }
	::= { csOrionConfigLoad 1 }


----------------------------------------------------------------------------
-- File System Operation
----------------------------------------------------------------------------

	csOrionFileSysReqTable OBJECT-TYPE
	SYNTAX  SEQUENCE OF CsOrionFileSysReqEntry
	MAX-ACCESS  not-accessible
	STATUS  current
	DESCRIPTION
		"File System Request Table."
	::= { csOrionFileSys 1 }

    csOrionFileSysReqEntry  OBJECT-TYPE
	SYNTAX  CsOrionFileSysReqEntry
	MAX-ACCESS  not-accessible
	STATUS  current
	DESCRIPTION
		"An entry of File System Request Table."
	INDEX   { csOrionFileSysReqIndex }
	::= { csOrionFileSysReqTable 1 }

    CsOrionFileSysReqEntry ::=
	SEQUENCE {
	csOrionFileSysReqIndex
		Integer32,
	csOrionFileSysReqType
		INTEGER,
	csOrionFileSysReqSrcFile 
		DisplayString,
	csOrionFileSysReqDestFile 
		DisplayString,
	csOrionFileSysReqStatus
		INTEGER,
	csOrionFileSysReqRowStatus
		RowStatus
	}

	csOrionFileSysReqIndex OBJECT-TYPE
	SYNTAX Integer32 (1..2147483647)
	MAX-ACCESS  not-accessible
	STATUS  current
	DESCRIPTION
		"This object identifies a specific File System request entry.
		NMSs are expected to come up with a unique ID each request.
		This ID will also be used to index the File System result entry."
	::= { csOrionFileSysReqEntry 1 }

    csOrionFileSysReqType OBJECT-TYPE
	SYNTAX		INTEGER {
		none (1),
		dir  (2),
		delete (3),
		copy (4),
		rename (5),
		load (6)
	}
	MAX-ACCESS	read-create
	STATUS		current
	DESCRIPTION
	       "This object specifies the filesystem operation stated in the
		   enumeration above. We will add entries as we support additional
		   filesystem commands. Objects that hold the parameters must also
		   be set for commands that requires some arguments."
	::= { csOrionFileSysReqEntry 2 }

	csOrionFileSysReqSrcFile OBJECT-TYPE
	SYNTAX		DisplayString (SIZE(0..80))
	MAX-ACCESS	read-create
	STATUS		current
	DESCRIPTION
	       "This object is used to hold the source file for the file system
		    operation. Must be set for 'delete', 'copy' and 'rename' requests.
			For 'load' request, the file to be loaded should be set using this
			object. If not set, the default file defined in
			csOrionSystemBootConfig will be loaded."
	::= { csOrionFileSysReqEntry 3 }

	csOrionFileSysReqDestFile OBJECT-TYPE
	SYNTAX		DisplayString (SIZE(0..80))
	MAX-ACCESS	read-create
	STATUS		current
	DESCRIPTION
	       "This object is used to hold the source file for the file system
		    operation. Must be set for copy and rename requests."
	::= { csOrionFileSysReqEntry 4 }

    csOrionFileSysReqStatus OBJECT-TYPE
	SYNTAX		INTEGER {
		none  (1),
		opInProgress (2),
		opSuccess (3),
		opFailed (4)
	}
	MAX-ACCESS	read-only
	STATUS		current
	DESCRIPTION
	       "This object is used to store the status of the File System request.
		   operation. For 'dir' operation, csOrionFileSysResultTable should
		   only be evaluated after this object yields opSuccess(3)."
	::= { csOrionFileSysReqEntry 5 }

	csOrionFileSysReqRowStatus OBJECT-TYPE
	SYNTAX  RowStatus
	MAX-ACCESS  read-create
	STATUS  current
	DESCRIPTION
		"The RowStatus object for this table.  This is used to
		add/delete rows from this table."
	::= { csOrionFileSysReqEntry 6 }

	csOrionFileSysResultTable OBJECT-TYPE
	SYNTAX  SEQUENCE OF CsOrionFileSysResultEntry
	MAX-ACCESS  not-accessible
	STATUS  current
	DESCRIPTION
		"File System Result Table. The object csOrionFileSysReqStatus should
		 be evaluated before acquiring the results from this table."
	::= { csOrionFileSys 2 }

    csOrionFileSysResultEntry  OBJECT-TYPE
	SYNTAX  CsOrionFileSysResultEntry
	MAX-ACCESS  not-accessible
	STATUS  current
	DESCRIPTION
		"An entry of File System Result Table. Each file returned from 'dir'
		request corresponds to an entry in csOrionFileSysResultEntry.
		Additional 'getnext' is expected to obtain the succeeding files.
		We will add objects in this table as we expose more file attributes."
	INDEX   { csOrionFileSysResultIndex, csOrionFileSysResultFilename }
	::= { csOrionFileSysResultTable 1 }

    CsOrionFileSysResultEntry ::=
	SEQUENCE {
	csOrionFileSysResultIndex
		Integer32,
	csOrionFileSysResultFilename 
		DisplayString,
	csOrionFileSysResultFilesize
		Integer32
	}

	csOrionFileSysResultIndex OBJECT-TYPE
	SYNTAX Integer32 (1..2147483647)
	MAX-ACCESS  not-accessible
	STATUS  current
	DESCRIPTION
		"This object identifies a specific File System result entry.
		This index corresponds to the ID provided by NMSs on File System
		request."
	::= { csOrionFileSysResultEntry 1 }

	csOrionFileSysResultFilename OBJECT-TYPE
	SYNTAX		DisplayString (SIZE(0..80))
	MAX-ACCESS	not-accessible
	STATUS		current
	DESCRIPTION
	       "This object is used to hold the filename from the 'dir' request."
	::= { csOrionFileSysResultEntry 2 }

	csOrionFileSysResultFilesize OBJECT-TYPE
	SYNTAX Integer32 (0..2147483647)
	MAX-ACCESS  read-only
	STATUS  current
	DESCRIPTION
		"This object is used to hold the filesize from the 'dir' request."
	::= { csOrionFileSysResultEntry 3 }


----------------------------------------------------------------------------
-- IPSX Chassis Info
----------------------------------------------------------------------------

    csOrionChassisMidplaneID	OBJECT-TYPE
        SYNTAX   OCTET STRING (SIZE(7))
 	MAX-ACCESS  read-only
	STATUS	current
	DESCRIPTION
		"Midplane laser ID for this chassis."
	::= { csOrionChassisInfo 1 }

    csOrionChassisType	OBJECT-TYPE
 	SYNTAX	INTEGER {
		ipsx3500(1),
		ipsx9000(2),
		ipsx9500(3),
                unknown(4)
	}
 	MAX-ACCESS  read-only
	STATUS	current
	DESCRIPTION
		"Chassis type."
	::= { csOrionChassisInfo 2 }

    csOrionChassisPacketRingStatus OBJECT-TYPE
 	SYNTAX	INTEGER {
		noProtection(1),
		onProtection(2)
	}
 	MAX-ACCESS  read-only
	STATUS	current
	DESCRIPTION
		"Status of the packet ring.
		noProtection means protection ring is inactive.
		onProtection means protection ring is active."
	::= { csOrionChassisInfo 3 }

    csOrionChassisPacketRingPrimToProtEndpoint OBJECT-TYPE
 	SYNTAX	Integer32 (1..26)
 	MAX-ACCESS  read-only
	STATUS	current
	DESCRIPTION
		"Slot number of the primary to protection endpoint.
		If csOrionChassisPacketRingStatus is noProtection,
		this object will have a value of 0."
	::= { csOrionChassisInfo 4 }

    csOrionChassisPacketRingProtToPrimEndpoint OBJECT-TYPE
 	SYNTAX	Integer32 (1..26)
 	MAX-ACCESS  read-only
	STATUS	current
	DESCRIPTION
		"Slot number of the protection to primary endpoint.
		If csOrionChassisPacketRingStatus is noProtection,
		this object will have a value of 0."
	::= { csOrionChassisInfo 5 }

    csOrionChassisPacketRingPrimaryCRC OBJECT-TYPE
 	SYNTAX	Integer32
 	MAX-ACCESS  read-only
	STATUS	current
	DESCRIPTION
		"CRC count on the primary packet ring."
	::= { csOrionChassisInfo 6 }

    csOrionChassisPacketRingProtectionCRC OBJECT-TYPE
 	SYNTAX	Integer32
 	MAX-ACCESS  read-only
	STATUS	current
	DESCRIPTION
		"CRC count on the protection packet ring."
	::= { csOrionChassisInfo 7 }

------------------------------------------------------------------------------
--
-- 		The Orion Port Info
--
--			This section contains information about Orion
--			ports (generally info that can't be 
--			obtained from std mibs)
--
--			The first table is used to configure parameters
--			on a 10/100 Ethernet port.
--
--			The next table defines individual channels used
--			on channelized T3 ports.  It also configures
--			the DS1 parameters used on each channel.
--
------------------------------------------------------------------------------
    --
    -- csEthTable.  This table configures parameters for the 10/100 Mbps 
    -- Ethernet ports.

    csEthTable OBJECT-TYPE
	SYNTAX  SEQUENCE OF CsEthEntry
	MAX-ACCESS  not-accessible
	STATUS  current
	DESCRIPTION
		"The Orion Ethernet Table."
	::= { csOrionEthInfo 1 }

    csEthEntry  OBJECT-TYPE
	SYNTAX  CsEthEntry
	MAX-ACCESS  not-accessible
	STATUS  current
	DESCRIPTION
		"An entry in the Ethernet Table."
	INDEX   { csEthSlotIndex, csEthPortIndex }
	::= { csEthTable 1 }

    CsEthEntry ::=
	SEQUENCE {
	csEthSlotIndex
		Integer32,
	csEthPortIndex
		Integer32,
	csEthEncapType
		INTEGER,
	csEthAutoneg
		INTEGER,
	csEthDuplex
		INTEGER,
	csEthSpeed
		INTEGER,
	csEthLinkTestInterval
		Integer32,
	csEthAdminStatus
		INTEGER,
	csEthOperStatus
		OperStatus
	}

    csEthSlotIndex OBJECT-TYPE
	SYNTAX  Integer32 (1..'7fffffff'h)
	MAX-ACCESS  not-accessible
	STATUS	current
	DESCRIPTION
	       "This object identifies the slot in which the blade that supports
	       this port is installed."
	::= { csEthEntry 1 }
		
    csEthPortIndex OBJECT-TYPE
	SYNTAX  Integer32 (1..'7fffffff'h)
	MAX-ACCESS  not-accessible
	STATUS	current
	DESCRIPTION
	       "This object identifies a specific port on the blade installed in
	       csEthSlotIndex."
	::= { csEthEntry 2 }

    csEthEncapType OBJECT-TYPE
	SYNTAX  INTEGER {
		eth (1),
		ieee (2),
		snap (3)
	}
	MAX-ACCESS  read-write
	STATUS	current
	DESCRIPTION
	       "This object identifies the encapsulation method used on this
	       Ethernet port."
	DEFVAL { eth }
	::= { csEthEntry 3 }

    csEthAutoneg OBJECT-TYPE
	SYNTAX  INTEGER {
		enabled  (1),
		disabled (2)
	}
	MAX-ACCESS  read-write
	STATUS	current
	DESCRIPTION
	       "This object is used to enable or disable the autonegotiation 
	       feature of this Ethernet port.  This feature is used to 
	       automatically negotiate the Speed and Duplex mode for 10/100 
	       Mbps Ethernet ports."
	DEFVAL { enabled }
	::= { csEthEntry 4 }

    csEthDuplex OBJECT-TYPE
	SYNTAX  INTEGER {
		half  (1),
		full (2)
	}
	MAX-ACCESS  read-write
	STATUS	current
	DESCRIPTION
	       "This object is used to specify the Duplex mode of this Ethernet 
	       port.  This is used only if csEthAutoneg is disabled.
		   Note: The default value is removed because it is not fixed in the system
		   after reboot when autonegotiation enabled. It is hardware configuration 
		   dependent."
	::= { csEthEntry 5 }

    csEthSpeed OBJECT-TYPE
	SYNTAX  INTEGER {
		mbps10  (1),
		mbps100 (2)
	}
	MAX-ACCESS  read-write
	STATUS	current
	DESCRIPTION
	       "This object is used to specify the speed of this Ethernet port.
	       This is used only if csEthAutoneg is disabled.
		   Note: The default value is removed because it is not fixed in the system
		   after reboot when autonegotiation enabled. It is hardware configuration 
		   dependent."
	::= { csEthEntry 6 }

    csEthLinkTestInterval OBJECT-TYPE
	SYNTAX  Integer32 (0..20)
	MAX-ACCESS  read-write
	STATUS	current
	DESCRIPTION
	       "This object is used to specify the interval, in seconds, between
	       Link Test packet transmissions.  If this object is set to 0, no
	       Link Test packets are sent."
	DEFVAL { 15 }
	::= { csEthEntry 7 }

    csEthAdminStatus OBJECT-TYPE
	SYNTAX  INTEGER {
		enable  (1),
		disable (2)
	}
	MAX-ACCESS  read-write
	STATUS	current
	DESCRIPTION
	       "This object is used to enable/disable thie Ethernet port."
	DEFVAL { enable }
	::= { csEthEntry 8 }

    csEthOperStatus OBJECT-TYPE
	SYNTAX  OperStatus
	MAX-ACCESS  read-only
	STATUS	current
	DESCRIPTION
	       "This object indicates the current operational status of this 
	       Ethernet port."
	::= { csEthEntry 9 }

   --
   --		Ethernet Sub-Interface Configuration Table
   --
    csEthSubIfTable OBJECT-TYPE
	SYNTAX  SEQUENCE OF CsEthSubIfEntry
	MAX-ACCESS  not-accessible
	STATUS  current
	DESCRIPTION
		"The Orion Ethernet Sub-Interface Table."
	::= { csOrionEthInfo 2 }

    csEthSubIfEntry OBJECT-TYPE
    	SYNTAX CsEthSubIfEntry
    	MAX-ACCESS not-accessible
    	STATUS current
    	DESCRIPTION
	    "The Parameters for a VLAN Interface."
        INDEX { csEthSlotIndex, csEthPortIndex, csEthSubIfChannelIndex, csEthSubIfIndex }
        ::= { csEthSubIfTable 1 }

    CsEthSubIfEntry ::=
    	SEQUENCE {
	csEthSubIfChannelIndex	Integer32,
    	csEthSubIfIndex		Integer32,
    	csEthSubIfVlanId	Integer32,
   	csEthSubIfUserPriority	Integer32,
	csEthSubIfVlanName	DisplayString,
	csEthSubIfAdmStatus	INTEGER,
	csEthSubIfOpStatus 	OperStatus,
	csEthSubIfRowStatus	RowStatus
    }

    csEthSubIfChannelIndex OBJECT-TYPE
	SYNTAX	Integer32 (0..64)
	MAX-ACCESS  not-accessible
	STATUS	current
	DESCRIPTION
	       "Channel ID of this VLAN connection. Currently, it
		    will always be 0."
	::= { csEthSubIfEntry 1 }

    csEthSubIfIndex OBJECT-TYPE
    	SYNTAX	Integer32 (1..512)
    	MAX-ACCESS	not-accessible
    	STATUS	current
    	DESCRIPTION
	    "The Sub Interface Id of the Logical Interface."
        ::= { csEthSubIfEntry 2 }

    csEthSubIfVlanId OBJECT-TYPE
    	SYNTAX	   Integer32 (2..4094)
    	MAX-ACCESS read-create
    	STATUS	   current
    	DESCRIPTION
	    "The unipue number between 0 and 4095 that identifies 
	    a particular VLAN. The range of VLAN IDs supported
	    per port is from 2 to 4094. The null VLAN Id (0) 
	    indicates that the tag header  contains only user
	    priority information. The VLAN Id 1, 4095 is reserved
	    for implementation use."
    	::= { csEthSubIfEntry 3 }

    csEthSubIfUserPriority OBJECT-TYPE
    	SYNTAX	   Integer32 (0..7)
    	MAX-ACCESS read-create
    	STATUS	   current
    	DESCRIPTION
	    "The user priority for this VLAN"
	DEFVAL { 0 }
   	::= { csEthSubIfEntry 4 }

    csEthSubIfVlanName OBJECT-TYPE
    	SYNTAX	   DisplayString (SIZE(0..32))
    	MAX-ACCESS read-create
    	STATUS	   current
    	DESCRIPTION
	    "The name for this VLAN"
   	::= { csEthSubIfEntry 5 }

    csEthSubIfAdmStatus OBJECT-TYPE
    	SYNTAX	INTEGER {
		enable (1),
		disable (2)
	}
    	MAX-ACCESS read-create
    	STATUS	   current
    	DESCRIPTION
	    "This object is used to enable/disable this VLAN."
	DEFVAL { disable }
    	::= { csEthSubIfEntry 6 }

    csEthSubIfOpStatus OBJECT-TYPE
    	SYNTAX	   OperStatus
    	MAX-ACCESS read-only
    	STATUS	   current
    	DESCRIPTION
	    "The operational status for this VLAN."
    ::= { csEthSubIfEntry 7 }

     csEthSubIfRowStatus OBJECT-TYPE
         SYNTAX   	RowStatus
         MAX-ACCESS   	read-create
         STATUS   	current
         DESCRIPTION
            "This object is used to create a new row or modify or
            destroy an existing row in the manner described in the
            definition of the RowStatus textual convention.
            Writable objects in the table may be written in any
            RowStatus state."
         ::= { csEthSubIfEntry 8 }


	--
	-- csDs3ConfigTable.  This table is used to configure
	-- DS3 parameters.
	-- 

    csDs3ConfigTable OBJECT-TYPE
	SYNTAX  SEQUENCE OF CsDs3ConfigEntry
	MAX-ACCESS  not-accessible
	STATUS  current
	DESCRIPTION
	       "The DS3 configuration table."
	::= { csOrionDs3Info 1 }

    csDs3ConfigEntry OBJECT-TYPE
	SYNTAX  CsDs3ConfigEntry
	MAX-ACCESS  not-accessible
	STATUS  current
	DESCRIPTION
	       "An entry in the DS3 Configuration table."
	INDEX { csDs3ConfigSlotIndex, csDs3ConfigPortIndex }
	::= { csDs3ConfigTable 1 }

    CsDs3ConfigEntry ::=
	SEQUENCE {
	csDs3ConfigSlotIndex
		Integer32,
	csDs3ConfigPortIndex
		Integer32,
	csDs3ConfigCableLength
		Integer32,
	csDs3ConfigFraming
		INTEGER,
	csDs3ConfigMdlPath
		INTEGER,
	csDs3ConfigMdlIdleSig
		INTEGER,
	csDs3ConfigMdlTestSig
		INTEGER,
	csDs3ConfigMdlEic
		DisplayString,
	csDs3ConfigMdlLic
		DisplayString,
	csDs3ConfigMdlFic
		DisplayString,
	csDs3ConfigMdlUnit
		DisplayString,
	csDs3ConfigMdlPfi
		DisplayString,
	csDs3ConfigMdlPort
		DisplayString,
	csDs3ConfigMdlGenerator
		DisplayString,
	csDs3ConfigTestT1Id
		Integer32,
	csDs3ConfigAdminStatus
		INTEGER,
	csDs3ConfigOperStatus
		OperStatus,
	csDs3ConfigClockSource
		INTEGER,
	csDs3ConfigDeviceType
		INTEGER,
	csDs3ConfigSendCode
		INTEGER,
	csDs3ConfigLoopbackType
		INTEGER,
	csDs3ConfigLoopbackStatus
		INTEGER,
	csDs3ConfigLineStatus
		INTEGER,
	csDs3ConfigTimeElapsed
		INTEGER,
	csDs3ConfigValidInterval
		INTEGER,
	csDs3ConfigInvalidInterval
		INTEGER,
	csDs3ConfigLineCoding
		INTEGER,
	csDs3ConfigNationalBit
		INTEGER
	}

    csDs3ConfigSlotIndex OBJECT-TYPE
	SYNTAX	Integer32 (1..'7fffffff'h)
	MAX-ACCESS  not-accessible
	STATUS	current
	DESCRIPTION
	       "This object identifies the blade to which this Ds3 Port
	       is attached.  Together with csDs3ConfigPortIndex, it uniquely 
	       identifies a physical port."
	::= { csDs3ConfigEntry 1 }

    csDs3ConfigPortIndex OBJECT-TYPE
	SYNTAX	Integer32 (1..'7fffffff'h)
	MAX-ACCESS  not-accessible
	STATUS	current
	DESCRIPTION
	       "This object identifies the location of the Ds3 Port on the
	       blade identified by csChDs3SlotIndex.  Together with 
	       csDs3ConfigSlotIndex, it uniquely identifies a physical port."
	::= { csDs3ConfigEntry 2 }

    csDs3ConfigCableLength OBJECT-TYPE
	SYNTAX	Integer32 (0..450)
	MAX-ACCESS  read-write
	STATUS	current
	DESCRIPTION
	       "The length of the DS3 cable. 
		    NOTE: This is applicable only for DS3."
	DEFVAL { 200 }
	::= { csDs3ConfigEntry 3 }

    csDs3ConfigFraming OBJECT-TYPE
	SYNTAX	INTEGER {
		cbit (1),
		m23  (2),
		auto (3),
		e3Framed	(4)
	}
	MAX-ACCESS  read-write
	STATUS	current
	DESCRIPTION
	       "The framing format used on this Ds3 Interface.
		    The default value is cbit if the interface is DS3. 
		    If the interface is E3,	e3Framed will be used, 
			and cannot be configured to any other types."
	::= { csDs3ConfigEntry 4 }

    csDs3ConfigMdlPath OBJECT-TYPE
	SYNTAX	INTEGER {
		enable  (1),
		disable (2)
	}
	MAX-ACCESS  read-write
	STATUS	current
	DESCRIPTION
	       "This object controls the transmission of the MDL Path message.
		    NOTE: This is applicable only for DS3."
	DEFVAL { enable }
	::= { csDs3ConfigEntry 5 }

    csDs3ConfigMdlIdleSig OBJECT-TYPE
	SYNTAX	INTEGER {
		enable  (1),
		disable (2)
	}
	MAX-ACCESS  read-write
	STATUS	current
	DESCRIPTION
	       "This object controls the transmission of the MDL Idle Signal 
	       message. NOTE: This is applicable only for DS3."
	DEFVAL { enable }
	::= { csDs3ConfigEntry 6 }

    csDs3ConfigMdlTestSig OBJECT-TYPE
	SYNTAX	INTEGER {
		enable  (1),
		disable (2)
	}
	MAX-ACCESS  read-write
	STATUS	current
	DESCRIPTION
	       "This object controls the transmission of the MDL Test Signal 
	       message. NOTE: This is applicable only for DS3."
	DEFVAL { enable }
	::= { csDs3ConfigEntry 7 }

    csDs3ConfigMdlEic OBJECT-TYPE
	SYNTAX	DisplayString (SIZE(0..10))
	MAX-ACCESS  read-write
	STATUS	current
	DESCRIPTION
	       "This object specifies the Equipment Identification Code.
		   NOTE: This is applicable only for DS3."
	::= { csDs3ConfigEntry 8 }

    csDs3ConfigMdlLic OBJECT-TYPE
	SYNTAX	DisplayString (SIZE(0..11))
	MAX-ACCESS  read-write
	STATUS	current
	DESCRIPTION
	       "This object specifies the Location Identification Code.
		    NOTE: This is applicable only for DS3."
	::= { csDs3ConfigEntry 9 }

    csDs3ConfigMdlFic OBJECT-TYPE
	SYNTAX	DisplayString (SIZE(0..10))
	MAX-ACCESS  read-write
	STATUS	current
	DESCRIPTION
	       "This object specifies the Frame Identification Code.
		    NOTE: This is applicable only for DS3."
	::= { csDs3ConfigEntry 10 }

    csDs3ConfigMdlUnit OBJECT-TYPE
	SYNTAX	DisplayString (SIZE(0..6))
	MAX-ACCESS  read-write
	STATUS	current
	DESCRIPTION
	       "This object specifies the Unit Identification Code.
		    NOTE: This is applicable only for DS3."
	::= { csDs3ConfigEntry 11 }

    csDs3ConfigMdlPfi OBJECT-TYPE
	SYNTAX	DisplayString (SIZE(0..38))
	MAX-ACCESS  read-write
	STATUS	current
	DESCRIPTION
	       "This object specifies the Facility Identification Code
	       sent in the MDL Path message. NOTE: This is applicable only for DS3."
	::= { csDs3ConfigEntry 12 }

    csDs3ConfigMdlPort OBJECT-TYPE
	SYNTAX	DisplayString (SIZE(0..38))
	MAX-ACCESS  read-write
	STATUS	current
	DESCRIPTION
	       "This object specifies the Port number string sent in the
	       MDL Idle Signal message. NOTE: This is applicable only for DS3."
	::= { csDs3ConfigEntry 13}

    csDs3ConfigMdlGenerator OBJECT-TYPE
	SYNTAX	DisplayString (SIZE(0..38))
	MAX-ACCESS  read-write
	STATUS	current
	DESCRIPTION
	       "This object specifies the Generator number string sent in the
	       MDL Test Signal message. NOTE: This is applicable only for DS3."
	::= { csDs3ConfigEntry 14}

    csDs3ConfigTestT1Id OBJECT-TYPE
	SYNTAX  Integer32 (1..28)
	MAX-ACCESS read-write
	STATUS  current
	DESCRIPTION
		"This object identifies which of the 28 T1's within
		this DS3 are to be broken out into the Test T1 port.
		If none of the T1's are to be broken out, this object
		should be set to 0. NOTE: This is applicable only for DS3."
	::= { csDs3ConfigEntry 15}

    csDs3ConfigAdminStatus OBJECT-TYPE
	SYNTAX		INTEGER {
		enable  (1),
		disable (2)
	}
	MAX-ACCESS	read-write
	STATUS		current
	DESCRIPTION
	       "This object is used to enable/disable this Ds3 port."
	DEFVAL { enable }
	::= { csDs3ConfigEntry 16 }

    csDs3ConfigOperStatus OBJECT-TYPE
	SYNTAX  OperStatus
	MAX-ACCESS  read-only
	STATUS	current
	DESCRIPTION
	       "This object indicates the current operational status of this 
	       Ds3 port."
	::= { csDs3ConfigEntry 17 }

    csDs3ConfigClockSource OBJECT-TYPE
	SYNTAX INTEGER {
		internal (1),
		line     (2)
	}
	MAX-ACCESS  read-write
	STATUS  current
	DESCRIPTION
	       "This object specifies the source of the Transmit Clock
	       used on this (unchannelized) DS3.  If this
	       object is set to internal(1), a local clock source
	       is used.  If this object is set to line(2), the recovered
	       received clock is used as the transmit clock.
		   NOTE: This is applicable only for DS3."
	::= { csDs3ConfigEntry 18 }

	csDs3ConfigDeviceType OBJECT-TYPE
	SYNTAX INTEGER {
		ds3 (1),
		e3  (2)
	}
	MAX-ACCESS  read-only
	STATUS  current
	DESCRIPTION
	       "This object indicates whether the interface is DS3 or E3."
	::= { csDs3ConfigEntry 19 }

	csDs3ConfigSendCode OBJECT-TYPE
	SYNTAX INTEGER {
		ds3SendNoCode(1),
        ds3SendLineCode(2),
        ds3SendPayloadCode(3),
        ds3SendResetCode(4)
	}
	MAX-ACCESS  read-write
	STATUS  current
	DESCRIPTION
	       "This variable indicates what type of code is
            being sent across the DS3 interface by the
            device. Setting this variable causes the interface
			to begin sending the code requested.
            The values mean:

               sendNoCode
                   sending looped or normal data

               sendLineCode
                   sending a request for a line loopback

               sendPayloadCode
                   sending a request for a payload loopback
                        (i.e., all DS1/E1s in a DS3/E3 frame)

               sendResetCode
                   sending a loopback deactivation request 
			NOTE: This is applicable only for DS3."

	::= { csDs3ConfigEntry 20 }

	csDs3ConfigLoopbackType OBJECT-TYPE
	SYNTAX INTEGER {
		noLoop (1),
		payloadLoop (2),
		lineLoop (3),
		otherLoop (4),
		inwardLoop (5),
		dualLoop (6)
	}
	MAX-ACCESS  read-write
	STATUS  current
	DESCRIPTION
	       "This object represents the desired loopback configuration
		    of the DS3 interface. 

			The values mean:
               noLoop
                 Not in the loopback state.  A device that is
                 not capable of performing a loopback on
                 the interface shall always return this as
                 its value.

               payloadLoop
                 The received signal at this interface is looped
                 through the device.  Typically the received signal
                 is looped back for retransmission after it has
                 passed through the device's framing function.

               lineLoop
                 The received signal at this interface does not
                 go through the device (minimum penetration) but
                 is looped back out.

               otherLoop
                 Loopbacks that are not defined here. Currently
				 not used in the IPSX system.

               inwardLoop
                 The sent signal at this interface is looped back
                 through the device.

               dualLoop
                 Both lineLoop and inwardLoop will be active 
				 simultaneously."
	::= { csDs3ConfigEntry 21 }

	csDs3ConfigLoopbackStatus OBJECT-TYPE
	SYNTAX INTEGER (1..127)
	MAX-ACCESS  read-only
	STATUS  current
	DESCRIPTION
	       "This variable represents the current state of the
            loopback on the DS3 interface.  It contains
            information about loopbacks established by a
            manager and remotely from the far end.

            The csDs3ConfigLoopbackStatus is a bit map represented 
			as a sum, therefore is can represent multiple 
			loopbacks simultaneously.

            The various bit positions are:
                  1  ds3NoLoopback
                  2  ds3NearEndPayloadLoopback
                  4  ds3NearEndLineLoopback
                  8  ds3NearEndOtherLoopback
                 16  ds3NearEndInwardLoopback
                 32  ds3FarEndPayloadLoopback
                 64  ds3FarEndLineLoopback "
	::= { csDs3ConfigEntry 22 }

	csDs3ConfigLineStatus OBJECT-TYPE
    SYNTAX  INTEGER (1..4095)
    MAX-ACCESS  read-only
    STATUS  current
    DESCRIPTION
		"This variable indicates the Line Status of the interface.  
		 It contains loopback state information and failure state 
		 information.  The csDs3ConfigLineStatus is a bit map 
		 represented as a sum, therefore, it can represent multiple 
		 failures and a loopback (see csDs3ConfigLoopbackStatus object 
		 for the type of loopback) simultaneously.  
		 The ds3NoAlarm must be set if and only if no other flag is set. 
		 If the ds3LoopbackState bit is set, the loopback in effect
		 can be determined from the csDs3ConfigLoopbackStatus object.
       The various bit positions are:
        0     ds3NoAlarm         No alarm present
        1     ds3RcvRAIFailure   Receiving Yellow/Remote
                                  Alarm Indication
        2     ds3XmitRAIAlarm    Transmitting Yellow/Remote
                                  Alarm Indication
        3     ds3RcvAIS          Receiving AIS failure state
        4     ds3XmitAIS         Transmitting AIS
        5     ds3LOF             Receiving LOF failure state
        6     ds3LOS             Receiving LOS failure state
        7     ds3LoopbackState   Looping the received signal
        8     ds3RcvTestCode     Receiving a Test Pattern
        9     ds3OtherFailure    any line status not defined
                                  here
       10     ds3UnavailSigState Near End in Unavailable Signal
                                  State
       11     ds3NetEquipOOS     Carrier Equipment Out of Service"
    ::= { csDs3ConfigEntry 23 }

	csDs3ConfigTimeElapsed OBJECT-TYPE
    SYNTAX  INTEGER (0..899)
    MAX-ACCESS  read-only
    STATUS  current
    DESCRIPTION
		"The number of seconds that have elapsed since the beginning 
		 of the near end current error-measurement period.  If, for some
		 reason, such as an adjustment in the system's time-of-day clock,
         the current interval exceeds the maximum value, the agent will 
		 return the maximum value."
    ::= { csDs3ConfigEntry 24 }

	csDs3ConfigValidInterval OBJECT-TYPE
    SYNTAX  INTEGER (1..96)
    MAX-ACCESS  read-only
    STATUS  current
    DESCRIPTION
		"The number of previous near end intervals for which data was 
		 collected.  The value will be 96 unless the interface was 
		 brought online within the last 24 hours, in which case the 
		 value will be the number of complete 15 minute near end
         intervals since the interface has been online.  In the case
		 where the agent is a proxy, it is possible that some intervals 
		 are unavailable.  In this case, this interval is the maximum 
		 interval number for which data is available."
    ::= { csDs3ConfigEntry 25 }

	csDs3ConfigInvalidInterval OBJECT-TYPE
    SYNTAX  INTEGER (1..96)
    MAX-ACCESS  read-only
    STATUS  current
    DESCRIPTION
		"The number of intervals in the range from 0 to csDs3ConfigValidInterval
		 for which no data is available.  This object will typically be zero
         except in cases where the data for some intervals are not available 
		 (e.g., in proxy situations)."
    ::= { csDs3ConfigEntry 26 }

	csDs3ConfigLineCoding OBJECT-TYPE
    SYNTAX  INTEGER {
		ds3Other  (1),
		ds3B3ZS   (2),
		e3HDB3    (3),
		e3NRZ	  (4)
		}
    MAX-ACCESS  read-write
    STATUS  current
    DESCRIPTION
		"This variable describes the variety of Zero Code
                      Suppression used on this interface, which in turn
                      affects a number of its characteristics.

                      ds3B3ZS and e3HDB3 refer to the use of specified
                      patterns of normal bits and bipolar violations
                      which are used to replace sequences of zero bits
                      of a specified length. NOTE: This is applicable 
					  only for E3 for now."
    ::= { csDs3ConfigEntry 27 }

	csDs3ConfigNationalBit OBJECT-TYPE
    SYNTAX  INTEGER (0..1)
	MAX-ACCESS  read-write
    STATUS  current
    DESCRIPTION
		"Bit 12 of the E3 G.751 frame. NOTE: This is applicable only for E3."
    ::= { csDs3ConfigEntry 28 }

	--
	-- csDs3Ds1ConfigTable.  This table is used to configure
	-- parameters for each DS1 within a DS3 device.
	--

    csDs3Ds1ConfigTable OBJECT-TYPE
	SYNTAX  SEQUENCE OF CsDs3Ds1ConfigEntry
	MAX-ACCESS  not-accessible
	STATUS  current
	DESCRIPTION
	       "The DS3 DS1 configuration table.  This is used to
		configure each of the DS1 connections within a complete DS3."
	::= { csOrionDs3Info 2 }

    csDs3Ds1ConfigEntry OBJECT-TYPE
	SYNTAX  CsDs3Ds1ConfigEntry
	MAX-ACCESS  not-accessible
	STATUS  current
	DESCRIPTION
	       "An entry in the DS3 DS1 Configuration table."
	INDEX { csDs3ConfigSlotIndex, csDs3ConfigPortIndex, csDs3Ds1Id }
	::= { csDs3Ds1ConfigTable 1 }

    CsDs3Ds1ConfigEntry ::=
	SEQUENCE {
	csDs3Ds1Id
		Integer32,
	csDs3Ds1Framing
		INTEGER,
	csDs3Ds1YellowAlarmDetect
		INTEGER,
	csDs3Ds1YellowAlarmGen
		INTEGER,
	csDs3Ds1LineCode
		INTEGER,
	csDs3Ds1InvertData 
		INTEGER,
	csDs3Ds1ClockSource
		INTEGER,
	csDs3Ds1Fdl
		INTEGER,
	csDs3Ds1OperStatus
		OperStatus,
	csDs3Ds1SendCode
		INTEGER,
	csDs3Ds1LoopbackType
		INTEGER,
	csDs3Ds1LoopbackStatus
		INTEGER,
	csDs3Ds1LineConfig
		Integer32,
	csDs3Ds1LineStatus
		Integer32,
	csDs3E1NatBits
		INTEGER,
	csDs3E1IntBits
		INTEGER
	}

    csDs3Ds1Id OBJECT-TYPE
	SYNTAX Integer32 (1..28)
	MAX-ACCESS not-accessible
	STATUS current
	DESCRIPTION
		"This identifies a single DS1 within a complete DS3."
	::= { csDs3Ds1ConfigEntry 1 }

    csDs3Ds1Framing OBJECT-TYPE
	SYNTAX INTEGER {
		esf                    (1),
		sf                     (2),
        e1CrcMultiframe        (3),
        e1CrcMultiframeFebe    (4),
        e1FrameAlignSignal     (5),
		e1UnFramed			   (6)
	}
	MAX-ACCESS  read-write
	STATUS  current
	DESCRIPTION
	       "This object specifies the framing
	       used on the DS1 assigned to this channel."
	::= { csDs3Ds1ConfigEntry 2 }

    csDs3Ds1YellowAlarmDetect OBJECT-TYPE
	SYNTAX INTEGER {
		enable  (1),
		disable (2)
	}
	MAX-ACCESS  read-write
	STATUS  current
	DESCRIPTION
	       "This object specifies whether Yellow Alarm detection
	       is active on the DS1 assigned to this channel."
	DEFVAL { enable }
	::= { csDs3Ds1ConfigEntry 3 }

    csDs3Ds1YellowAlarmGen OBJECT-TYPE
	SYNTAX INTEGER {
		enable  (1),
		disable (2)
	}
	MAX-ACCESS  read-write
	STATUS  current
	DESCRIPTION
	       "This object specifies whether Yellow Alarm 
	       generation is active on the DS1 assigned to this 
	       channel. NOTE: This is applicable only for T1."
	DEFVAL { enable }
	::= { csDs3Ds1ConfigEntry 4 }

    csDs3Ds1LineCode OBJECT-TYPE
	SYNTAX INTEGER {
		ami  (1),
		b8zs (2)
	}
	MAX-ACCESS  read-write
	STATUS  current
	DESCRIPTION
	       "This object specifies the variety of Zero Code Suppression
	        used on the on the DS1 assigned to this channel.
		    NOTE: This is applicable only for T1."
	DEFVAL { b8zs }
	::= { csDs3Ds1ConfigEntry 5 }

    csDs3Ds1InvertData OBJECT-TYPE
	SYNTAX INTEGER {
		on  (1),
		off (2)
	}
	MAX-ACCESS  read-write
	STATUS  current
	DESCRIPTION
	       "This object specifies whether the 'invert data' feature
	       is enabled on the DS1 assigned to this channel.  This
	       feature must be enabled if the Line Code parameter
	       (csDs3Ds1LineCode) is set to ami. NOTE: This is applicable only for T1."
	DEFVAL { off }
	::= { csDs3Ds1ConfigEntry 6 }

    csDs3Ds1ClockSource OBJECT-TYPE
	SYNTAX INTEGER {
		internal (1),
		line     (2)
	}
	MAX-ACCESS  read-write
	STATUS  current
	DESCRIPTION
	       "This object specifies the source of the Transmit Clock
	       used on the DS1 assigned to this channel.  If this
	       object is set to internal(1), a local clock source
	       is used.  If this object is set to line(2), the recovered
	       received clock is used as the transmit clock.
		   NOTE: This is applicable only for T1."
	DEFVAL { internal }
	::= { csDs3Ds1ConfigEntry 7 }

    csDs3Ds1Fdl OBJECT-TYPE
	SYNTAX INTEGER {
		enable (1),
		disable(2)
	}
	MAX-ACCESS  read-write
	STATUS  current
	DESCRIPTION
		"This is used to enable/disable 1 second transmission
		of performance reports via ANSI 403 FDL.  If this is
		disabled, the AT&T 54016 version of FDL is used.  Note,
		FDL is available only for ESF framing. And so it is only
		applicable for T1."
	DEFVAL { enable }
	::= { csDs3Ds1ConfigEntry 8 }

    csDs3Ds1OperStatus OBJECT-TYPE
	SYNTAX OperStatus
	MAX-ACCESS  read-only
	STATUS  current
	DESCRIPTION
		"This object indicates the current operational status of this DS1."
	::= { csDs3Ds1ConfigEntry 9 }

	csDs3Ds1SendCode OBJECT-TYPE
	SYNTAX INTEGER {
		ds1SendNoCode(1),
        ds1SendLineCode(2),
        ds1SendPayloadCode(3),
        ds1SendResetCode(4)
	}
	MAX-ACCESS  read-write
	STATUS  current
	DESCRIPTION
	    "This variable indicates what type of code is
         being sent across the DS1 interface by the device.
         Setting this variable causes the interface to send
         the code requested. NOTE: This is applicable only for T1..  
		 
		 The values mean:
             ds1SendNoCode
                sending looped or normal data

             ds1SendLineCode
                sending a request for a line loopback

             ds1SendPayloadCode
                sending a request for a payload loopback

             ds1SendResetCode
                sending a loopback termination request "
	::= { csDs3Ds1ConfigEntry 10 }

	csDs3Ds1LoopbackType OBJECT-TYPE
	SYNTAX INTEGER {
		noLoop (1),
		payloadLoop (2),
		lineLoop (3),
		otherLoop (4),
		inwardLoop (5),
		dualLoop (6)
	}
	MAX-ACCESS  read-write
	STATUS  current
	DESCRIPTION
	       "This object represents the desired loopback configuration
		   of the DS1 interface. This variable will be interpreted
		   only when csDs3Ds1LoopbackDestination is set to a
		   valid value.  NOTE: This is applicable only for T1.

               noLoop
                 Not in the loopback state.  A device that is not
                 capable of performing a loopback on the interface
                 shall always return this as its value.

               payloadLoop
                 The received signal at this interface is looped
                 through the device.  Typically the received signal
                 is looped back for retransmission after it has
                 passed through the device's framing function.

               lineLoop
                 The received signal at this interface does not go
                 through the device (minimum penetration) but is
                 looped back out.

               otherLoop
                 Loopbacks that are not defined here. Currently
				 not used in the IPSX system 

               inwardLoop
                 The transmitted signal at this interface is
                 looped back and received by the same interface.
                 What is transmitted onto the line is product
                 dependent. Cannot be applied to far end.

               dualLoop
                 Both dsx1LineLoop and dsx1InwardLoop will be
                 active simultaneously. Cannot be applied to 
				 far end."
	::= { csDs3Ds1ConfigEntry 11 }

	csDs3Ds1LoopbackStatus OBJECT-TYPE
	SYNTAX INTEGER (1..127)
	MAX-ACCESS  read-only
	STATUS  current
	DESCRIPTION
	       "This variable represents the current state of the
            loopback on the DS1 interface.  It contains
            information about loopbacks established by a
            manager and remotely from the far end. 
			NOTE: This is applicable only for T1.

            The csDs3Ds1LoopbackStatus is a bit map represented 
			as a sum, therefore is can represent multiple 
			loopbacks simultaneously.

            The various bit positions are:
                  1  ds1NoLoopback
                  2  ds1NearEndPayloadLoopback
                  4  ds1NearEndLineLoopback
                  8  ds1NearEndOtherLoopback
                 16  ds1NearEndInwardLoopback
                 32  ds1FarEndPayloadLoopback
                 64  ds1FarEndLineLoopback "
	::= { csDs3Ds1ConfigEntry 12 }

	csDs3Ds1LineConfig OBJECT-TYPE
	SYNTAX Integer32
	MAX-ACCESS  read-write
	STATUS  current
	DESCRIPTION
	       "This variable represents DS1/E1 transmit line configuration. This is normally used for
		   dignostic or service purpose, it is not supposed for user to configure.

            The various bit positions are:
				  BIT(0)  not used
                  BIT(1)  ds1NoAlarm         			
                  BIT(2)  ds1RcvFarEndLOF
                  BIT(3)  ds1XmtFarEndLOF 			
                  BIT(4)  ds1RcvAIS          			
                  BIT(5)  ds1XmtAIS       			
                  BIT(6)  ds1LossOfFrame    			
                  BIT(7)  ds1LossOfSignal  			
                  BIT(8)  ds1LoopbackState     			
         		  BIT(9)  ds1T16AIS    
      			 BIT(10)  ds1RcvFarEndLOMF
      			 BIT(11)  ds1XmtFarEndLOMF
        		 BIT(12)  ds1RcvTestCode
       			 BIT(13)  ds1OtherFailure
    			 BIT(14)  ds1UnavailSigState
        	     BIT(15)  ds1NetEquipOOS
      			 BIT(16)  ds1RcvPayloadAIS
   			     BIT(17)  ds1Ds2PerfThreshold
 		  		 BIT(18)  ds1XmtTrnkCond  "
	::= { csDs3Ds1ConfigEntry 13 }

	csDs3Ds1LineStatus OBJECT-TYPE
	SYNTAX Integer32 
	MAX-ACCESS  read-only
	STATUS  current
	DESCRIPTION
	       "This variable represents DS1/E1 transmit and 
		    receive line status.

            The various bit positions are:
				  BIT(0)  not used
                  BIT(1)  ds1NoAlarm         			
                  BIT(2)  ds1RcvFarEndLOF
                  BIT(3)  ds1XmtFarEndLOF 			
                  BIT(4)  ds1RcvAIS          			
                  BIT(5)  ds1XmtAIS       			
                  BIT(6)  ds1LossOfFrame    			
                  BIT(7)  ds1LossOfSignal  			
                  BIT(8)  ds1LoopbackState     			
         		  BIT(9)  ds1T16AIS    
      			 BIT(10)  ds1RcvFarEndLOMF
      			 BIT(11)  ds1XmtFarEndLOMF
        		 BIT(12)  ds1RcvTestCode
       			 BIT(13)  ds1OtherFailure
    			 BIT(14)  ds1UnavailSigState
        	     BIT(15)  ds1NetEquipOOS
      			 BIT(16)  ds1RcvPayloadAIS
   			     BIT(17)  ds1Ds2PerfThreshold
 		  		 BIT(18)  ds1XmtTrnkCond  "
	::= { csDs3Ds1ConfigEntry 14 }

	csDs3E1IntBits OBJECT-TYPE
	SYNTAX INTEGER (0..3)
	MAX-ACCESS  read-write
	STATUS  current
	DESCRIPTION
	       "This variable is used to configure the 2-bits international bits
		    for the E1 interface. NOTE: This is applicable only for E1."
	::= { csDs3Ds1ConfigEntry 15 }

	csDs3E1NatBits OBJECT-TYPE
	SYNTAX INTEGER (0..31)
	MAX-ACCESS  read-write
	STATUS  current
	DESCRIPTION
	       "This 4-bit object is added for the E1 sub-multiframe 
		    aligned national bit codeword configuration.  
			NOTE: This is applicable only for E1."

	::= { csDs3Ds1ConfigEntry 16 }

    -- csChDs3Table.  This table is designed
    -- for those systems dividing a DS3/E3 into channels
    -- containing different data streams that are of local
    -- interest.

    -- The Channelized DS3 table identifies which DS3/E3
    -- channels are being used to support a logical link or channel.
    -- 
    -- A channelized DS3 can be divided into 28 DS1's.  Each
    -- DS1 can then be divided into 24 DS0's.  We can form
    -- 'channels' comprised of an arbitrary number of DS0's
    -- within a single DS1.

    -- A channelized E3 can be divided into 16 E1's.  Each
    -- E1 can then be divided into 32 DS0's.  We can form
    -- 'channels' comprised of an arbitrary number of DS0's
	-- between 1 to 31 within a single E1.


    csChDs3Table OBJECT-TYPE
	SYNTAX  SEQUENCE OF CsChDs3Entry
	MAX-ACCESS  not-accessible
	STATUS  current
	DESCRIPTION
	       "The Channelized DS3 Channel configuration table."
	::= { csOrionDs3Info 3 }

    csChDs3Entry OBJECT-TYPE
	SYNTAX  CsChDs3Entry
	MAX-ACCESS  not-accessible
	STATUS  current
	DESCRIPTION
	      "An entry in the DS3 Fractional table."
	INDEX   { csChDs3SlotIndex, csChDs3PortIndex, csChDs3ChNumber }
	::= { csChDs3Table 1 }

    CsChDs3Entry ::=
	SEQUENCE {
	csChDs3SlotIndex
		Integer32,
	csChDs3PortIndex
		Integer32,
	csChDs3ChNumber
		Integer32,
	csChDs3T1Number
		Integer32,
	csChDs3TimeSlots
		DisplayString,
	csChDs3Speed
		INTEGER,
	csChDs3Encap
		INTEGER,
	csChDs3RowStatus
		RowStatus,
	csChDs3OperStatus
		OperStatus
	}


    csChDs3SlotIndex OBJECT-TYPE
	SYNTAX  Integer32 (1..126)
	MAX-ACCESS  not-accessible
	STATUS  current
	DESCRIPTION
	       "This object identifies the blade to which this Ds3 Port
	       is attached.  Together with csChDs3PortIndex, it uniquely 
	       identifies a physical port."
	::= { csChDs3Entry 1 }

    csChDs3PortIndex OBJECT-TYPE
	SYNTAX  Integer32 (1..126)
	MAX-ACCESS  not-accessible
	STATUS  current
	DESCRIPTION
	       "This object identifies the location of the Ds3 Port on the
	       blade identified by csChDs3SlotIndex.  Together with 
	       csChDs3SlotIndex, it uniquely identifies a physical port."
	::= { csChDs3Entry 2 }

    csChDs3ChNumber OBJECT-TYPE
	SYNTAX  Integer32 (1..128)
	MAX-ACCESS  not-accessible
	STATUS  current
	DESCRIPTION
	       "The channel number for this entry."
	::= { csChDs3Entry 3 }

    csChDs3T1Number OBJECT-TYPE
	SYNTAX  Integer32 (1..28)
	MAX-ACCESS  read-create
	STATUS  current
	DESCRIPTION
	       "This object identifies the DS1 number that is
	       assigned to this channel. This number for E1 is 1 to 16.

	       NOTE: This object can only be set during row creation.
		Once the row is created, this object cannot be modified."
	::= { csChDs3Entry 4 }

    csChDs3TimeSlots OBJECT-TYPE
	SYNTAX  DisplayString (SIZE(1..40))
	MAX-ACCESS  read-create
	STATUS  current
	DESCRIPTION
	       "This object specifies the individual DS0 time slots within 
	       the DS1(T1 or E1, identified by csChDs3T1Number) that are
	       assigned to this channel.  The format can be a range
	       of slots (1-8), a list of slots (1, 3, 7), or a mix of both.

	       NOTE: This object can only be set during row creation.
		Once the row is created, this object cannot be modified."
	::= { csChDs3Entry 5 }

    csChDs3Speed OBJECT-TYPE
	SYNTAX INTEGER {
		kbps64(1),
		kbps56(2)
	}
	MAX-ACCESS  read-create
	STATUS  current
	DESCRIPTION
	       "This object specifies the speed (and,
	       hence the signaling mode) of the DS1 assigned
	       to this channel."
	DEFVAL { kbps64 }
	::= { csChDs3Entry 6 }

    csChDs3Encap OBJECT-TYPE
	SYNTAX INTEGER {
		none		(0),
		ppp			(1),
		frameRelay	(2),
		ciscoHdlc	(3)
	}
	MAX-ACCESS  read-create
	STATUS  current
	DESCRIPTION
		"This object specifies the encapsulation used
		on this DS3 channel.  If the encapsulation type
		is frameRelay(2), use the csFrameRelayTable to
		configure the Frame Relay specific parameters."
	DEFVAL { none }
	::= { csChDs3Entry 7 }

    csChDs3RowStatus OBJECT-TYPE
	SYNTAX	 RowStatus 
	MAX-ACCESS  read-create
	STATUS	current
	DESCRIPTION
	       "A row status type for this Channel."
	::= { csChDs3Entry 8 }

    csChDs3OperStatus OBJECT-TYPE
	SYNTAX	 OperStatus
	MAX-ACCESS  read-only
	STATUS	current
	DESCRIPTION
	       "A operational status for this Channel."
	::= { csChDs3Entry 9 }


	--
	-- Local Statistics Group for fast-ethernet
	--
------------------------------------------------------------------------------
    --
    -- csEthStatsTable.  This table lists the statistics counters for the 100 Mbps 
    -- Fast-ethernet ports.

    csEthStatsTable OBJECT-TYPE
	SYNTAX  SEQUENCE OF CsEthStatsEntry
	MAX-ACCESS  not-accessible
	STATUS  current
	DESCRIPTION
		"The Orion Ethernet Table."
	::= { csOrionEthInfo 3 }

    csEthStatsEntry  OBJECT-TYPE
	SYNTAX  CsEthStatsEntry
	MAX-ACCESS  not-accessible
	STATUS  current
	DESCRIPTION
		"An entry in the Ethernet Statistic Table."
	INDEX   { csEthSlotIndex, csEthPortIndex }
	::= { csEthStatsTable 1 }

    CsEthStatsEntry ::=
    SEQUENCE {
--			csEthStatsTxUnicastPktsOk    		Counter32, 
--			csEthStatsTxMulticastPktsOk   		Counter32,
--			csEthStatsTxBroadcastPktsOk		Counter32,
			csEthStatsTxDeferPktsOk    		Counter32,
			csEthStatsTxColCounts			Counter32,
			csEthStatsTxScolPktsOk			Counter32,
			csEthStatsTxMulticCollisionPktsOK			Counter32,
			csEthStatsTx16CollisionCounts			Counter32,
			csEthStatsTxLateCollisionCounts			Counter32,
			csEthStatsTx64Pkts			Counter32,
			csEthStatsTx65To127Pkts			Counter32,
			csEthStatsTx128To255Pkts			Counter32,
			csEthStatsTx256To511Pkts			Counter32,
			csEthStatsTx512To1023Pkts			Counter32,
			csEthStatsTx1024To1518Pkts			Counter32,
			csEthStatsTx1519Pkts			Counter32,
			csEthStatsTxPausePktsOk			Counter32,
			csEthStatsTxErrCounts			Counter32,
--			csEthStatsTxOctetsOk			Counter32,     
			csEthStatsTxOctetsBad			Counter32,
--			csEthStatsRxUnicastPktsOk		Counter32,
--			csEthStatsRxMulticastPktsOk		Counter32,
--			csEthStatsRxBroadcastPktsOk		Counter32,
			csEthStatsRxRuntCounts			Counter32,
			csEthStatsRxOvfCounts			Counter32,
			csEthStatsRxShortPktsOk			Counter32,
			csEthStatsRxNormCrcCounts		Counter32,
			csEthStatsRxNormAliCounts		Counter32,
			csEthStatsRxLongPktsCounts		Counter32,
			csEthStatsRxLongCrcCounts		Counter32,
			csEthStatsRx64Pkts			Counter32,
			csEthStatsRx65To127Pkts			Counter32,
			csEthStatsRx128To255Pkts			Counter32,
			csEthStatsRx256To511Pkts			Counter32,
			csEthStatsRx512To1023Pkts			Counter32,
			csEthStatsRx1024To1518Pkts			Counter32,
			csEthStatsRx1519Pkts			Counter32,
			csEthStatsRxPausePktsOk			Counter32,
			csEthStatsRxFalsCrcCounts		Counter32,
--			csEthStatsRxOctsOk			Counter32,
			csEthStatsRxOctsBad			Counter32,
			csEthStatsRxSysErrCounts		Counter32
    }

    csEthStatsTxDeferPktsOk OBJECT-TYPE
    SYNTAX  Counter32
    MAX-ACCESS  read-only
    STATUS  current
    DESCRIPTION
     " The counter associated with the number of packets 
	 deferred upon the 		first transmit attempt due to a busy line ."
	::= { csEthStatsEntry 1 }

	csEthStatsTxColCounts OBJECT-TYPE
    SYNTAX  Counter32
    MAX-ACCESS  read-only
    STATUS  current
    DESCRIPTION
     " The counter associated with the number of Regular 
	 collisions during transmission."
	::= { csEthStatsEntry 2 }

	csEthStatsTxScolPktsOk OBJECT-TYPE
    SYNTAX  Counter32
    MAX-ACCESS  read-only
    STATUS  current
    DESCRIPTION
     " The counter associated with the number of packets transmitted
	  without any errors following a single collisions."
	::= { csEthStatsEntry 3 }

	csEthStatsTxMulticCollisionPktsOK OBJECT-TYPE
    SYNTAX  Counter32
    MAX-ACCESS  read-only
    STATUS  current
    DESCRIPTION
     " The counter associated with the number of packets transmitted
	  without any errors following multiple collisions."
	::= { csEthStatsEntry 4 }

	csEthStatsTx16CollisionCounts OBJECT-TYPE
    SYNTAX  Counter32
    MAX-ACCESS  read-only
    STATUS  current
    DESCRIPTION
     " The counter associated with the number of packets that have 
	 experienced 16 consecutive collisions or more."
	::= { csEthStatsEntry 5 }

	csEthStatsTxLateCollisionCounts OBJECT-TYPE
    SYNTAX  Counter32
    MAX-ACCESS  read-only
    STATUS  current
    DESCRIPTION
     " The counter associated with the number of transmission abortions 
	 due to a collision occurring  after the transmission of packets 
	 that are 64 bytes in length."
	::= { csEthStatsEntry 6 }

	csEthStatsTx64Pkts OBJECT-TYPE
    SYNTAX  Counter32
    MAX-ACCESS  read-only
    STATUS  current
    DESCRIPTION
     " The counter associated with the number of transmitted 
	 packets 64 bytes in length, including bad packets."
	::= { csEthStatsEntry 7 }

	csEthStatsTx65To127Pkts OBJECT-TYPE
    SYNTAX  Counter32
    MAX-ACCESS  read-only
    STATUS  current
    DESCRIPTION
     " The counter associated with the number of packets 
	 64 to 127 bytes in length, including bad packets."
	::= { csEthStatsEntry 8 }

	csEthStatsTx128To255Pkts OBJECT-TYPE
    SYNTAX  Counter32
    MAX-ACCESS  read-only
    STATUS  current
    DESCRIPTION
     " The counter associated with the number of packets 
	 128 to 255 bytes in length, including bad packets."
	::= { csEthStatsEntry 9 }

	csEthStatsTx256To511Pkts OBJECT-TYPE
    SYNTAX  Counter32
    MAX-ACCESS  read-only
    STATUS  current
    DESCRIPTION
     " The counter associated with the number of packets 
	 256 to 511 bytes in length, including bad packets."
	::= { csEthStatsEntry 10 }

	csEthStatsTx512To1023Pkts OBJECT-TYPE
    SYNTAX  Counter32
    MAX-ACCESS  read-only
    STATUS  current
    DESCRIPTION
     " The counter associated with the number of transmitted 
	 packets 512 to 1023 bytes in length, including bad packets."
	::= { csEthStatsEntry 11 }

	csEthStatsTx1024To1518Pkts OBJECT-TYPE
    SYNTAX  Counter32
    MAX-ACCESS  read-only
    STATUS  current
    DESCRIPTION
     " The counter associated with the number of transmitted 
	 packets 1024 to 1518 bytes in length, including bad packets."
	::= { csEthStatsEntry 12 }

	csEthStatsTx1519Pkts OBJECT-TYPE
    SYNTAX  Counter32
    MAX-ACCESS  read-only
    STATUS  current
    DESCRIPTION
     " The counter associated with the number of transmitted 
	 packets with length larger than 1518 bytes, including bad packets."
	::= { csEthStatsEntry 13 }

	csEthStatsTxPausePktsOk OBJECT-TYPE
    SYNTAX  Counter32
    MAX-ACCESS  read-only
    STATUS  current
    DESCRIPTION
     " The counter associated with the number of 
	 correct transmitted flow-control packets."
	::= { csEthStatsEntry 14 }

	csEthStatsTxErrCounts OBJECT-TYPE
    SYNTAX  Counter32
    MAX-ACCESS  read-only
    STATUS  current
    DESCRIPTION
     " The counter associated with the number of packets 
	 transmitted with an error due to transmit FIFO underflow 
	 or txerr signal assertion."
	::= { csEthStatsEntry 15 }

	csEthStatsTxOctetsBad OBJECT-TYPE
    SYNTAX  Counter32
    MAX-ACCESS  read-only
    STATUS  current
    DESCRIPTION
     " The counter associated with the number of bytes 
	 transmitted in packets with errors."
	::= { csEthStatsEntry 16 }

	csEthStatsRxRuntCounts OBJECT-TYPE
    SYNTAX  Counter32
    MAX-ACCESS  read-only
    STATUS  current
    DESCRIPTION
     " The counter associated with the number of frames 
	 received without SFD detection but with carrier assertion ."
	::= { csEthStatsEntry 17 }

	csEthStatsRxOvfCounts OBJECT-TYPE
    SYNTAX  Counter32
    MAX-ACCESS  read-only
    STATUS  current
    DESCRIPTION
     " The counter associated with the number of received 
	 packets not fully accepted due to receive FIFO overflow ."
	::= { csEthStatsEntry 18 }

	csEthStatsRxShortPktsOk OBJECT-TYPE
    SYNTAX  Counter32
    MAX-ACCESS  read-only
    STATUS  current
    DESCRIPTION
     " The counter associated with the number of received 
	 packets without error, less than 64 bytes length ."
	::= { csEthStatsEntry 19 }

	csEthStatsRxNormCrcCounts OBJECT-TYPE
    SYNTAX  Counter32
    MAX-ACCESS  read-only
    STATUS  current
    DESCRIPTION
     " The counter associated with the number of packets 
	 received with an integral number of bytes and a CRC 
	 error with lengths between 64 bytes and maximum packet size ."
	::= { csEthStatsEntry 20 }

	csEthStatsRxNormAliCounts OBJECT-TYPE
    SYNTAX  Counter32
    MAX-ACCESS  read-only
    STATUS  current
    DESCRIPTION
     " The counter associated with the number of packets 
	 received with an nonintegral number of bytes and a CRC 
	 error with lengths between 64 bytes and maximum packet size."
	::= { csEthStatsEntry 21 }

	csEthStatsRxLongPktsCounts OBJECT-TYPE
    SYNTAX  Counter32
    MAX-ACCESS  read-only
    STATUS  current
    DESCRIPTION
     " The counter associated with the number ofpackets larger 
	 than maximum packet size received without any error ."
	::= { csEthStatsEntry 22 }

	csEthStatsRxLongCrcCounts OBJECT-TYPE
    SYNTAX  Counter32
    MAX-ACCESS  read-only
    STATUS  current
    DESCRIPTION
     " The counter associated with the number of packets larger 
	 than maximum packet size received with a CRC error"
	::= { csEthStatsEntry 23 }

	csEthStatsRx64Pkts OBJECT-TYPE
    SYNTAX  Counter32
    MAX-ACCESS  read-only
    STATUS  current
    DESCRIPTION
     " The counter associated with the number of received packets 
	 64 bytes in length, including bad packets."
	::= { csEthStatsEntry 24 }

	csEthStatsRx65To127Pkts OBJECT-TYPE
    SYNTAX  Counter32
    MAX-ACCESS  read-only
    STATUS  current
    DESCRIPTION
     " The counter associated with the number of received packets 
	 65 to 127 bytes in length, including bad packets."
	::= { csEthStatsEntry 25 }

	csEthStatsRx128To255Pkts OBJECT-TYPE
    SYNTAX  Counter32
    MAX-ACCESS  read-only
    STATUS  current
    DESCRIPTION
     " The counter associated with the number of packets 128 to 255 
	 bytes in length, including bad packetsO."
	::= { csEthStatsEntry 26 }

	csEthStatsRx256To511Pkts OBJECT-TYPE
    SYNTAX  Counter32
    MAX-ACCESS  read-only
    STATUS  current
    DESCRIPTION
     " The counter associated with the number of packets 256 to 511 
	 bytes in length, including bad packets"
	::= { csEthStatsEntry 27 }

	csEthStatsRx512To1023Pkts OBJECT-TYPE
    SYNTAX  Counter32
    MAX-ACCESS  read-only
    STATUS  current
    DESCRIPTION
     " The counter associated with the number of packets 512 to 1023 
	 bytes in length, including bad packets."
	::= { csEthStatsEntry 28 }

	csEthStatsRx1024To1518Pkts OBJECT-TYPE
    SYNTAX  Counter32
    MAX-ACCESS  read-only
    STATUS  current
    DESCRIPTION
     " The counter associated with the number of packets 1024 to 1518 
	 bytes in length, including bad packets."
	::= { csEthStatsEntry 29 }

	csEthStatsRx1519Pkts OBJECT-TYPE
    SYNTAX  Counter32
    MAX-ACCESS  read-only
    STATUS  current
    DESCRIPTION
     " The counter associated with the number of packets with length 
	 larger than 1518 bytes and the maximum packet size, including bad 
	 packets."
	::= { csEthStatsEntry 30 }

	csEthStatsRxPausePktsOk OBJECT-TYPE
    SYNTAX  Counter32
    MAX-ACCESS  read-only
    STATUS  current
    DESCRIPTION
     " The counter associated with the number of correct received 
	 flow-control packets."
	::= { csEthStatsEntry 31 }

	csEthStatsRxFalsCrcCounts OBJECT-TYPE
    SYNTAX  Counter32
    MAX-ACCESS  read-only
    STATUS  current
    DESCRIPTION
     " The counter associated with the number of false carrier 
	 events detected"
	::= { csEthStatsEntry 32 }

	csEthStatsRxOctsBad OBJECT-TYPE
    SYNTAX  Counter32
    MAX-ACCESS  read-only
    STATUS  current
    DESCRIPTION
     " The counter associated with the number of bytes received 
	 in packets with errors."
	::= { csEthStatsEntry 33 }

	csEthStatsRxSysErrCounts OBJECT-TYPE
    SYNTAX  Counter32
    MAX-ACCESS  read-only
    STATUS  current
    DESCRIPTION
     " The counter associated with the number of received packets 
	 during which PHY symbol errors were detected."
	::= { csEthStatsEntry 34 }



	--
	-- Local Statistics Group for DS3
	--

	--
	-- csDs3StatCurrentTable.  The DS3/E3 Current Statistics Table
	--


    csDs3StatCurrentTable OBJECT-TYPE
    SYNTAX  SEQUENCE OF CsDs3StatCurrentEntry
    MAX-ACCESS  not-accessible
    STATUS  current
    DESCRIPTION
                 "The DS3/E3 current table contains various
                 statistics being collected for the current 15
                 minute interval."
    ::= { csOrionDs3Info 4 }

    csDs3StatCurrentEntry OBJECT-TYPE
    SYNTAX  CsDs3StatCurrentEntry
    MAX-ACCESS  not-accessible
    STATUS  current
    DESCRIPTION
                 "An entry in the DS3/E3 Current table."
    INDEX   { csDs3ConfigSlotIndex, csDs3ConfigPortIndex }
    ::= { csDs3StatCurrentTable 1 }

    CsDs3StatCurrentEntry ::=
    SEQUENCE {
              csDs3StatCurrentPESs            PerfCurrentCount,
              csDs3StatCurrentPSESs           PerfCurrentCount,
              csDs3StatCurrentSEFSs           PerfCurrentCount,
              csDs3StatCurrentUASs            PerfCurrentCount,
              csDs3StatCurrentLCVs            PerfCurrentCount,
              csDs3StatCurrentPCVs            PerfCurrentCount,
              csDs3StatCurrentLESs            PerfCurrentCount,
              csDs3StatCurrentCCVs            PerfCurrentCount,
              csDs3StatCurrentCESs            PerfCurrentCount,
              csDs3StatCurrentCSESs           PerfCurrentCount,
			  csDs3StatCurrentLSESs           PerfCurrentCount
    }


    csDs3StatCurrentPESs OBJECT-TYPE
    SYNTAX  PerfCurrentCount
    MAX-ACCESS  read-only
    STATUS  current
    DESCRIPTION
			"The counter associated with the number of P-bit Errored Seconds.             
			 NOTE: This is applicable only for DS3."
    ::= { csDs3StatCurrentEntry 1 }

    csDs3StatCurrentPSESs OBJECT-TYPE
    SYNTAX  PerfCurrentCount
    MAX-ACCESS  read-only
    STATUS  current
    DESCRIPTION
            "The counter associated with the number of P-bit Severely Errored Seconds. 
             NOTE: This is applicable only for DS3."
    ::= { csDs3StatCurrentEntry 2 }

    csDs3StatCurrentSEFSs OBJECT-TYPE
	SYNTAX  PerfCurrentCount
    MAX-ACCESS  read-only
    STATUS  current
    DESCRIPTION
            "The counter associated with the number of Severely Errored Framing Seconds. 
             NOTE: This is applicable only for DS3."
    ::= { csDs3StatCurrentEntry 3 }

    csDs3StatCurrentUASs OBJECT-TYPE
    SYNTAX  PerfCurrentCount
    MAX-ACCESS  read-only
    STATUS  current
    DESCRIPTION
            "The counter associated with the number of Unavailable Seconds.
             NOTE: This is applicable only for DS3."
    ::= { csDs3StatCurrentEntry 4 }

    csDs3StatCurrentLCVs OBJECT-TYPE
    SYNTAX  PerfCurrentCount
    MAX-ACCESS  read-only
    STATUS  current
    DESCRIPTION
            "The counter associated with the number of Line Coding Violations.
             NOTE: This is applicable for both E3 and DS3."
    ::= { csDs3StatCurrentEntry 5 }

    csDs3StatCurrentPCVs OBJECT-TYPE
    SYNTAX  PerfCurrentCount
    MAX-ACCESS  read-only
    STATUS  current
    DESCRIPTION
            "The counter associated with the number of P-bit Coding Violations.
             NOTE: This is applicable only for DS3."
          ::= { csDs3StatCurrentEntry 6 }

    csDs3StatCurrentLESs OBJECT-TYPE
    SYNTAX  PerfCurrentCount
    MAX-ACCESS  read-only
    STATUS  current
    DESCRIPTION
            "The number of Line Errored Seconds. 
			 NOTE: This is applicable for both E3 and DS3."
    ::= { csDs3StatCurrentEntry 7 }

    csDs3StatCurrentCCVs OBJECT-TYPE
    SYNTAX  PerfCurrentCount
    MAX-ACCESS  read-only
    STATUS  current
    DESCRIPTION
            "The number of C-bit Coding Violations.
			 NOTE: This is applicable only for DS3."
    ::= { csDs3StatCurrentEntry 8 }

    csDs3StatCurrentCESs OBJECT-TYPE
    SYNTAX  PerfCurrentCount
    MAX-ACCESS  read-only
    STATUS  current
    DESCRIPTION
            "The number of C-bit Errored Seconds.
			 NOTE: This is applicable only for DS3."
    ::= { csDs3StatCurrentEntry 9 }

    csDs3StatCurrentCSESs OBJECT-TYPE
    SYNTAX  PerfCurrentCount
    MAX-ACCESS  read-only
    STATUS  current
    DESCRIPTION
            "The number of C-bit Severely Errored Seconds.
			 NOTE: This is applicable only for DS3."
    ::= { csDs3StatCurrentEntry 10 }

	csDs3StatCurrentLSESs OBJECT-TYPE
    SYNTAX  PerfCurrentCount
    MAX-ACCESS  read-only
    STATUS  current
    DESCRIPTION
            "The number of Line Severely Errored Seconds.
			 NOTE: This is applicable for both E3 and DS3."
    ::= { csDs3StatCurrentEntry 11 }


	--
	-- csDs3StatIntervalTable.  The DS3/E3 Interval Statistics Table
	--

    csDs3StatIntervalTable OBJECT-TYPE
    SYNTAX  SEQUENCE OF CsDs3StatIntervalEntry
    MAX-ACCESS  not-accessible
    STATUS  current
    DESCRIPTION
                 "The DS3/E3 Interval Table contains various
                 statistics collected by each DS3/E3 Interface over
                 the previous 24 hours of operation.  The past 24
                 hours are broken into 96 completed 15 minute
                 intervals.  Each row in this table represents one
                 such interval (identified by csDs3StatIntervalNumber)
                 and for one specific DS3 port (identifed by
                 csDs3ConfigPortIndex)."
    ::= { csOrionDs3Info 5 }

    csDs3StatIntervalEntry OBJECT-TYPE
    SYNTAX  CsDs3StatIntervalEntry
    MAX-ACCESS  not-accessible
    STATUS  current
    DESCRIPTION
                 "An entry in the DS3/E3 Interval table."
    INDEX   { csDs3ConfigSlotIndex, csDs3ConfigPortIndex, 
			  csDs3StatIntervalNumber }
    ::= { csDs3StatIntervalTable 1 }

	CsDs3StatIntervalEntry ::=
    SEQUENCE {
              csDs3StatIntervalNumber          INTEGER,
              csDs3StatIntervalPESs            PerfIntervalCount,
              csDs3StatIntervalPSESs           PerfIntervalCount,
              csDs3StatIntervalSEFSs           PerfIntervalCount,
              csDs3StatIntervalUASs            PerfIntervalCount,
              csDs3StatIntervalLCVs            PerfIntervalCount,
              csDs3StatIntervalPCVs            PerfIntervalCount,
              csDs3StatIntervalLESs            PerfIntervalCount,
              csDs3StatIntervalCCVs            PerfIntervalCount,
              csDs3StatIntervalCESs            PerfIntervalCount,
              csDs3StatIntervalCSESs           PerfIntervalCount,
			  csDs3StatIntervalLSESs           PerfIntervalCount,
              csDs3StatIntervalValidData       TruthValue
    }

    csDs3StatIntervalNumber OBJECT-TYPE
    SYNTAX  INTEGER (1..96)
    MAX-ACCESS  not-accessible
    STATUS  current
    DESCRIPTION
            "A number between 1 and 96, where 1 is the most
             recently completed 15 minute interval and 96 is
             the 15 minutes interval completed 23 hours and 45
             minutes prior to interval 1."
    ::= { csDs3StatIntervalEntry 1 }

    csDs3StatIntervalPESs OBJECT-TYPE
    SYNTAX  PerfIntervalCount
    MAX-ACCESS  read-only
    STATUS  current
    DESCRIPTION
            "The counter associated with the number of P-bit Errored Seconds.
             NOTE: This is applicable only for DS3."
    ::= { csDs3StatIntervalEntry 2 }

    csDs3StatIntervalPSESs OBJECT-TYPE
    SYNTAX  PerfIntervalCount
    MAX-ACCESS  read-only
    STATUS  current
    DESCRIPTION
            "The counter associated with the number of P-bit
             Severely Errored Seconds.
			 NOTE: This is applicable only for DS3."
    ::= { csDs3StatIntervalEntry 3 }

    csDs3StatIntervalSEFSs OBJECT-TYPE
    SYNTAX  PerfIntervalCount
    MAX-ACCESS  read-only
    STATUS  current
    DESCRIPTION
            "The counter associated with the number of
             Severely Errored Framing Seconds.
			 NOTE: This is applicable for both DS3 and E3."
    ::= { csDs3StatIntervalEntry 4 }

    csDs3StatIntervalUASs OBJECT-TYPE
    SYNTAX  PerfIntervalCount
    MAX-ACCESS  read-only
    STATUS  current
    DESCRIPTION
            "The counter associated with the number of
             Unavailable Seconds.  This object may decrease if
             the occurance of unavailable seconds occurs across
             an inteval boundary.
			 NOTE: This is applicable only for DS3."
    ::= { csDs3StatIntervalEntry 5 }

    csDs3StatIntervalLCVs OBJECT-TYPE
    SYNTAX  PerfIntervalCount
    MAX-ACCESS  read-only
    STATUS  current
    DESCRIPTION
            "The counter associated with the number of Line
             Coding Violations.
			 NOTE: This is applicable for both E3 and DS3."
    ::= { csDs3StatIntervalEntry 6 }

    csDs3StatIntervalPCVs OBJECT-TYPE
    SYNTAX  PerfIntervalCount
    MAX-ACCESS  read-only
    STATUS  current
    DESCRIPTION
            "The counter associated with the number of P-bit
             Coding Violations.
			 NOTE: This is applicable only for DS3."
    ::= { csDs3StatIntervalEntry 7 }

    csDs3StatIntervalLESs OBJECT-TYPE
    SYNTAX  PerfIntervalCount
    MAX-ACCESS  read-only
    STATUS  current
    DESCRIPTION
            "The number of Line Errored  Seconds  (BPVs  or
             illegal  zero  sequences).
			 NOTE: This is applicable for both E3 and DS3."
    ::= { csDs3StatIntervalEntry 8 }

    csDs3StatIntervalCCVs OBJECT-TYPE
    SYNTAX  PerfIntervalCount
    MAX-ACCESS  read-only
    STATUS  current
    DESCRIPTION
            "The number of C-bit Coding Violations.
			 NOTE: This is applicable only for DS3."
    ::= { csDs3StatIntervalEntry 9 }

    csDs3StatIntervalCESs OBJECT-TYPE
    SYNTAX  PerfIntervalCount
    MAX-ACCESS  read-only
    STATUS  current
    DESCRIPTION
            "The number of C-bit Errored Seconds.
			 NOTE: This is applicable only for DS3."
    ::= { csDs3StatIntervalEntry 10 }

    csDs3StatIntervalCSESs OBJECT-TYPE
    SYNTAX  PerfIntervalCount
    MAX-ACCESS  read-only
    STATUS  current
    DESCRIPTION
            "The number of C-bit Severely Errored Seconds.
			 NOTE: This is applicable only for DS3."
    ::= { csDs3StatIntervalEntry 11 }

	csDs3StatIntervalLSESs OBJECT-TYPE
    SYNTAX  PerfIntervalCount
    MAX-ACCESS  read-only
    STATUS  current
    DESCRIPTION
            "The number of Line Severely Errored Seconds.
			 NOTE: This is applicable for both E3 and DS3."
    ::= { csDs3StatIntervalEntry 12 }

    csDs3StatIntervalValidData OBJECT-TYPE
    SYNTAX  TruthValue
    MAX-ACCESS read-only
    STATUS current
    DESCRIPTION
            "This variable indicates if the data for this
             interval is valid."
    ::= { csDs3StatIntervalEntry 13 }


	--
	-- csDs3StatTotalTable.  The DS3/E3 Total Statistics Table
	--


    csDs3StatTotalTable OBJECT-TYPE
    SYNTAX  SEQUENCE OF CsDs3StatTotalEntry
    MAX-ACCESS  not-accessible
    STATUS  current
    DESCRIPTION
                 "The DS3/E3 Total Table contains the cumulative
                 sum of the various statistics for the 24 hour
                 period preceding the current interval."
    ::= { csOrionDs3Info 6 }

    csDs3StatTotalEntry OBJECT-TYPE
    SYNTAX  CsDs3StatTotalEntry
    MAX-ACCESS  not-accessible
    STATUS  current
    DESCRIPTION
                 "An entry in the DS3/E3 Total table."
    INDEX   { csDs3ConfigSlotIndex, csDs3ConfigPortIndex }
    ::= { csDs3StatTotalTable 1 }

    CsDs3StatTotalEntry ::=
    SEQUENCE {
              csDs3StatTotalPESs       PerfTotalCount,
              csDs3StatTotalPSESs      PerfTotalCount,
              csDs3StatTotalSEFSs      PerfTotalCount,
              csDs3StatTotalUASs       PerfTotalCount,
              csDs3StatTotalLCVs       PerfTotalCount,
              csDs3StatTotalPCVs       PerfTotalCount,
              csDs3StatTotalLESs       PerfTotalCount,
              csDs3StatTotalCCVs       PerfTotalCount,
              csDs3StatTotalCESs       PerfTotalCount,
              csDs3StatTotalCSESs      PerfTotalCount,
			  csDs3StatTotalLSESs      PerfTotalCount
    }

    csDs3StatTotalPESs OBJECT-TYPE
    SYNTAX  PerfTotalCount
    MAX-ACCESS  read-only
    STATUS  current
    DESCRIPTION
                 "The counter associated with the number of P-bit
                 Errored Seconds, encountered by a DS3 interface in
                 the previous 24 hour interval. Invalid 15 minute
                 intervals count as 0.
				 NOTE: This is applicable only for DS3."
    ::= { csDs3StatTotalEntry 1 }

    csDs3StatTotalPSESs OBJECT-TYPE
          SYNTAX  PerfTotalCount
          MAX-ACCESS  read-only
          STATUS  current
          DESCRIPTION
                 "The counter associated with the number of P-bit
                 Severely Errored Seconds, encountered by a DS3
                 interface in the previous 24 hour interval.
                 Invalid 15 minute intervals count as 0.
				 NOTE: This is applicable only for DS3."
    ::= { csDs3StatTotalEntry 2 }

    csDs3StatTotalSEFSs OBJECT-TYPE
    SYNTAX  PerfTotalCount
    MAX-ACCESS  read-only
    STATUS  current
    DESCRIPTION
                 "The counter associated with the number of
                 Severely Errored Framing Seconds, encountered by a
                 DS3/E3 interface in the previous 24 hour interval.
                 Invalid 15 minute intervals count as 0.
				 NOTE: This is applicable only for DS3."
    ::= { csDs3StatTotalEntry 3 }

    csDs3StatTotalUASs OBJECT-TYPE
    SYNTAX  PerfTotalCount
    MAX-ACCESS  read-only
    STATUS  current
    DESCRIPTION
                 "The counter associated with the number of
                 Unavailable Seconds, encountered by a DS3
                 interface in the previous 24 hour interval.
                 Invalid 15 minute intervals count as 0.
				 NOTE: This is applicable only for DS3."
    ::= { csDs3StatTotalEntry 4 }

    csDs3StatTotalLCVs OBJECT-TYPE
    SYNTAX  PerfTotalCount
    MAX-ACCESS  read-only
    STATUS  current
    DESCRIPTION
                 "The counter associated with the number of Line
                 Coding Violations encountered by a DS3/E3
                 interface in the previous 24 hour interval.
                 Invalid 15 minute intervals count as 0.
				 NOTE: This is applicable for both E3 and DS3."
    ::= { csDs3StatTotalEntry 5 }

    csDs3StatTotalPCVs OBJECT-TYPE
    SYNTAX  PerfTotalCount
    MAX-ACCESS  read-only
    STATUS  current
    DESCRIPTION
                 "The counter associated with the number of P-bit
                 Coding Violations, encountered by a DS3 interface
                 in the previous 24 hour interval. Invalid 15
                 minute intervals count as 0.
				 NOTE: This is applicable only for DS3."
    ::= { csDs3StatTotalEntry 6 }

    csDs3StatTotalLESs OBJECT-TYPE
    SYNTAX  PerfTotalCount
    MAX-ACCESS  read-only
    STATUS  current
    DESCRIPTION
                 "The number of Line Errored  Seconds  (BPVs  or
                 illegal  zero  sequences) encountered by a DS3/E3
                 interface in the previous 24 hour interval.
                 Invalid 15 minute intervals count as 0.
				 NOTE: This is applicable for both E3 and DS3."
    ::= { csDs3StatTotalEntry 7 }

    csDs3StatTotalCCVs OBJECT-TYPE
    SYNTAX  PerfTotalCount
    MAX-ACCESS  read-only
    STATUS  current
    DESCRIPTION
                 "The number of C-bit Coding Violations encountered
                 by a DS3 interface in the previous 24 hour
                 interval. Invalid 15 minute intervals count as 0.
				 NOTE: This is applicable only for DS3."
    ::= { csDs3StatTotalEntry 8 }

    csDs3StatTotalCESs OBJECT-TYPE
    SYNTAX  PerfTotalCount
    MAX-ACCESS  read-only
    STATUS  current
    DESCRIPTION
                 "The number of C-bit Errored Seconds encountered
                 by a DS3 interface in the previous 24 hour
                 interval. Invalid 15 minute intervals count as 0.
				 NOTE: This is applicable only for DS3."
    ::= { csDs3StatTotalEntry 9 }

    csDs3StatTotalCSESs OBJECT-TYPE
    SYNTAX  PerfTotalCount
    MAX-ACCESS  read-only
    STATUS  current
    DESCRIPTION
                 "The number of C-bit Severely Errored Seconds
                 encountered by a DS3 interface in the previous 24-hour
                 interval. Invalid 15 minute intervals count as 0.
				 NOTE: This is applicable only for DS3."
    ::= { csDs3StatTotalEntry 10 }

	csDs3StatTotalLSESs OBJECT-TYPE
    SYNTAX  PerfTotalCount
    MAX-ACCESS  read-only
    STATUS  current
    DESCRIPTION
                 "The number of Line Severely Errored Seconds
                 encountered by a DS3 interface in the previous 24-hour
                 interval. Invalid 15 minute intervals count as 0.
				 NOTE: This is applicable for both E3 and DS3."
    ::= { csDs3StatTotalEntry 11 }


	--
	-- csDs3Ds1CurrentTable.  The DS1 Current Statistics Table
	--

    csDs3Ds1CurrentTable OBJECT-TYPE
          SYNTAX  SEQUENCE OF CsDs3Ds1CurrentEntry
          MAX-ACCESS  not-accessible
          STATUS  current
          DESCRIPTION
                 "The DS1 current table contains various statistics
                 being collected for the current 15 minute
                 interval."
          ::= { csOrionDs3Info 7 }

     csDs3Ds1CurrentEntry OBJECT-TYPE
          SYNTAX  CsDs3Ds1CurrentEntry
          MAX-ACCESS  not-accessible
          STATUS  current
          DESCRIPTION
                 "An entry in the DS1 Current table."
          INDEX   { csDs3ConfigSlotIndex, csDs3ConfigPortIndex, csDs3Ds1Id }
          ::= { csDs3Ds1CurrentTable 1 }

     CsDs3Ds1CurrentEntry ::=
          SEQUENCE {
              csDs3Ds1CurrentESs              PerfCurrentCount,
              csDs3Ds1CurrentSESs             PerfCurrentCount,
              csDs3Ds1CurrentSEFSs            PerfCurrentCount,
              csDs3Ds1CurrentUASs             PerfCurrentCount,
              csDs3Ds1CurrentCSSs             PerfCurrentCount,
              csDs3Ds1CurrentPCVs             PerfCurrentCount,
              csDs3Ds1CurrentLESs             PerfCurrentCount,
              csDs3Ds1CurrentBESs             PerfCurrentCount,
              csDs3Ds1CurrentDMs              PerfCurrentCount,
              csDs3Ds1CurrentLCVs             PerfCurrentCount
     }

     csDs3Ds1CurrentESs OBJECT-TYPE
          SYNTAX  PerfCurrentCount
          MAX-ACCESS  read-only
          STATUS  current
          DESCRIPTION
                 "The number of Errored Seconds."
          ::= { csDs3Ds1CurrentEntry 1 }

     csDs3Ds1CurrentSESs OBJECT-TYPE
          SYNTAX  PerfCurrentCount
          MAX-ACCESS  read-only
          STATUS  current
          DESCRIPTION
                 "The number of Severely Errored Seconds."
          ::= { csDs3Ds1CurrentEntry 2 }

     csDs3Ds1CurrentSEFSs OBJECT-TYPE
          SYNTAX  PerfCurrentCount
          MAX-ACCESS  read-only
          STATUS  current
          DESCRIPTION
                 "The number of Severely Errored Framing Seconds."
          ::= { csDs3Ds1CurrentEntry 3 }

     csDs3Ds1CurrentUASs OBJECT-TYPE
          SYNTAX  PerfCurrentCount
          MAX-ACCESS  read-only
          STATUS  current
          DESCRIPTION
                 "The number of Unavailable Seconds."
          ::= { csDs3Ds1CurrentEntry 4 }

     csDs3Ds1CurrentCSSs OBJECT-TYPE
          SYNTAX  PerfCurrentCount
          MAX-ACCESS  read-only
          STATUS  current
          DESCRIPTION
                 "The number of Controlled Slip Seconds."
          ::= { csDs3Ds1CurrentEntry 5 }

     csDs3Ds1CurrentPCVs OBJECT-TYPE
          SYNTAX  PerfCurrentCount
          MAX-ACCESS  read-only
          STATUS  current
          DESCRIPTION
                 "The number of Path Coding Violations."
          ::= { csDs3Ds1CurrentEntry 6 }

     csDs3Ds1CurrentLESs OBJECT-TYPE
          SYNTAX  PerfCurrentCount
          MAX-ACCESS  read-only
          STATUS  current
          DESCRIPTION
                 "The number of Line Errored Seconds."
          ::= { csDs3Ds1CurrentEntry 7 }

     csDs3Ds1CurrentBESs OBJECT-TYPE
          SYNTAX PerfCurrentCount
          MAX-ACCESS read-only
          STATUS current
          DESCRIPTION
                 "The number of Bursty Errored Seconds."
          ::= { csDs3Ds1CurrentEntry 8 }

     csDs3Ds1CurrentDMs OBJECT-TYPE
          SYNTAX PerfCurrentCount
          MAX-ACCESS read-only
          STATUS current
          DESCRIPTION
                 "The number of Degraded Minutes."
          ::= { csDs3Ds1CurrentEntry 9 }

     csDs3Ds1CurrentLCVs OBJECT-TYPE
          SYNTAX PerfCurrentCount
          MAX-ACCESS read-only
          STATUS current
          DESCRIPTION
                 "The number of Line Code Violations (LCVs)."
          ::= { csDs3Ds1CurrentEntry 10 }


	--
    -- csDs3Ds1IntervalTable.  The DS1 Interval Statistics Table
	--

     csDs3Ds1IntervalTable OBJECT-TYPE
          SYNTAX  SEQUENCE OF CsDs3Ds1IntervalEntry
          MAX-ACCESS  not-accessible
          STATUS  current
          DESCRIPTION
                 "The DS1 Interval Table contains various
                 statistics collected by each DS1 Interface over
                 the previous 24 hours of operation.  The past 24
                 hours are broken into 96 completed 15 minute
                 intervals.  Each row in this table represents one
                 such interval (identified by csDs3Ds1IntervalNumber)
                 for one specific instance (identified by csDs3Ds1Id)."
          ::= { csOrionDs3Info 8 }

     csDs3Ds1IntervalEntry OBJECT-TYPE
          SYNTAX  CsDs3Ds1IntervalEntry
          MAX-ACCESS  not-accessible
          STATUS  current
          DESCRIPTION
                 "An entry in the DS1 Interval table."
          INDEX   { csDs3ConfigSlotIndex, csDs3ConfigPortIndex, 
					csDs3Ds1Id, csDs3Ds1IntervalNumber }
          ::= { csDs3Ds1IntervalTable 1 }

     CsDs3Ds1IntervalEntry ::=
          SEQUENCE {
              csDs3Ds1IntervalNumber            INTEGER,
              csDs3Ds1IntervalESs               PerfIntervalCount,
              csDs3Ds1IntervalSESs              PerfIntervalCount,
              csDs3Ds1IntervalSEFSs             PerfIntervalCount,
              csDs3Ds1IntervalUASs              PerfIntervalCount,
              csDs3Ds1IntervalCSSs              PerfIntervalCount,
              csDs3Ds1IntervalPCVs              PerfIntervalCount,
              csDs3Ds1IntervalLESs              PerfIntervalCount,
              csDs3Ds1IntervalBESs              PerfIntervalCount,
              csDs3Ds1IntervalDMs               PerfIntervalCount,
              csDs3Ds1IntervalLCVs              PerfIntervalCount,
              csDs3Ds1IntervalValidData         TruthValue
     }

     csDs3Ds1IntervalNumber OBJECT-TYPE
          SYNTAX  INTEGER (1..96)
          MAX-ACCESS  not-accessible
          STATUS  current
          DESCRIPTION
                 "A number between 1 and 96, where 1 is the most
                 recently completed 15 minute interval and 96 is
                 the 15 minutes interval completed 23 hours and 45
                 minutes prior to interval 1."
          ::= { csDs3Ds1IntervalEntry 1 }

     csDs3Ds1IntervalESs OBJECT-TYPE
          SYNTAX  PerfIntervalCount
          MAX-ACCESS  read-only
          STATUS  current
          DESCRIPTION
                 "The number of Errored Seconds."
          ::= { csDs3Ds1IntervalEntry 2 }

     csDs3Ds1IntervalSESs OBJECT-TYPE
          SYNTAX  PerfIntervalCount
          MAX-ACCESS  read-only
          STATUS  current
          DESCRIPTION
                 "The number of Severely Errored Seconds."
          ::= { csDs3Ds1IntervalEntry 3 }

     csDs3Ds1IntervalSEFSs OBJECT-TYPE
          SYNTAX  PerfIntervalCount
          MAX-ACCESS  read-only
          STATUS  current
          DESCRIPTION
                 "The number of Severely Errored Framing Seconds."
          ::= { csDs3Ds1IntervalEntry 4 }

     csDs3Ds1IntervalUASs OBJECT-TYPE
          SYNTAX  PerfIntervalCount
          MAX-ACCESS  read-only
          STATUS  current
          DESCRIPTION
                 "The number of Unavailable Seconds.  This object
                 may decrease if the occurance of unavailable
                 seconds occurs across an inteval boundary."
          ::= { csDs3Ds1IntervalEntry 5 }

     csDs3Ds1IntervalCSSs OBJECT-TYPE
          SYNTAX  PerfIntervalCount
          MAX-ACCESS  read-only
          STATUS  current
          DESCRIPTION
                 "The number of Controlled Slip Seconds."
          ::= { csDs3Ds1IntervalEntry 6 }

     csDs3Ds1IntervalPCVs OBJECT-TYPE
          SYNTAX  PerfIntervalCount
          MAX-ACCESS  read-only
          STATUS  current
          DESCRIPTION
                 "The number of Path Coding Violations."
          ::= { csDs3Ds1IntervalEntry 7 }

     csDs3Ds1IntervalLESs OBJECT-TYPE
          SYNTAX  PerfIntervalCount
          MAX-ACCESS  read-only
          STATUS  current
          DESCRIPTION
                 "The number of Line Errored Seconds."
          ::= { csDs3Ds1IntervalEntry 8 }

     csDs3Ds1IntervalBESs OBJECT-TYPE
          SYNTAX PerfIntervalCount
          MAX-ACCESS read-only
          STATUS current
          DESCRIPTION
                 "The number of Bursty Errored Seconds."
          ::= { csDs3Ds1IntervalEntry 9 }

     csDs3Ds1IntervalDMs OBJECT-TYPE
          SYNTAX PerfIntervalCount
          MAX-ACCESS read-only
          STATUS current
          DESCRIPTION
                 "The number of Degraded Minutes."
          ::= { csDs3Ds1IntervalEntry 10 }

     csDs3Ds1IntervalLCVs OBJECT-TYPE
          SYNTAX PerfIntervalCount
          MAX-ACCESS read-only
          STATUS current
          DESCRIPTION
                 "The number of Line Code Violations."
          ::= { csDs3Ds1IntervalEntry 11 }

     csDs3Ds1IntervalValidData OBJECT-TYPE
          SYNTAX TruthValue
          MAX-ACCESS read-only
          STATUS current
          DESCRIPTION
                 "This variable indicates if the data for this
                 interval is valid."
          ::= { csDs3Ds1IntervalEntry 12 }


	--
    -- csDs3Ds1TotalTable.  The DS1 Total Statistics Table.
	--

     csDs3Ds1TotalTable OBJECT-TYPE
          SYNTAX  SEQUENCE OF CsDs3Ds1TotalEntry
          MAX-ACCESS  not-accessible
          STATUS  current
          DESCRIPTION
                 "The DS1 Total Table contains the cumulative sum
                 of the various statistics for the 24 hour period
                 preceding the current interval."
          ::= { csOrionDs3Info 9 }

     csDs3Ds1TotalEntry OBJECT-TYPE
          SYNTAX  CsDs3Ds1TotalEntry
          MAX-ACCESS  not-accessible
          STATUS  current
          DESCRIPTION
                 "An entry in the DS1 Total table."
          INDEX   { csDs3ConfigSlotIndex, csDs3ConfigPortIndex,
					csDs3Ds1Id }
          ::= { csDs3Ds1TotalTable 1 }

     CsDs3Ds1TotalEntry ::=
          SEQUENCE {
              csDs3Ds1TotalESs                  PerfTotalCount,
              csDs3Ds1TotalSESs                 PerfTotalCount,
              csDs3Ds1TotalSEFSs                PerfTotalCount,
              csDs3Ds1TotalUASs                 PerfTotalCount,
              csDs3Ds1TotalCSSs                 PerfTotalCount,
              csDs3Ds1TotalPCVs                 PerfTotalCount,
              csDs3Ds1TotalLESs                 PerfTotalCount,
              csDs3Ds1TotalBESs                 PerfTotalCount,
              csDs3Ds1TotalDMs                  PerfTotalCount,
              csDs3Ds1TotalLCVs                 PerfTotalCount
     }

     csDs3Ds1TotalESs OBJECT-TYPE
          SYNTAX  PerfTotalCount
          MAX-ACCESS  read-only
          STATUS  current
          DESCRIPTION
                 "The sum of Errored Seconds encountered by a DS1
                 interface in the previous 24 hour interval.
                 Invalid 15 minute intervals count as 0."
          ::= { csDs3Ds1TotalEntry 1 }

     csDs3Ds1TotalSESs OBJECT-TYPE
          SYNTAX  PerfTotalCount
          MAX-ACCESS  read-only
          STATUS  current
          DESCRIPTION
                 "The number of Severely Errored Seconds
                 encountered by a DS1 interface in the previous 24
                 hour interval.  Invalid 15 minute intervals count
                 as 0."
          ::= { csDs3Ds1TotalEntry 2 }

     csDs3Ds1TotalSEFSs OBJECT-TYPE
          SYNTAX  PerfTotalCount
          MAX-ACCESS  read-only
          STATUS  current
          DESCRIPTION
                 "The number of Severely Errored Framing Seconds
                 encountered by a DS1 interface in the previous 24
                 hour interval.  Invalid 15 minute intervals count
                 as 0."
          ::= { csDs3Ds1TotalEntry 3 }

     csDs3Ds1TotalUASs OBJECT-TYPE
          SYNTAX  PerfTotalCount
          MAX-ACCESS  read-only
          STATUS  current
          DESCRIPTION
                 "The number of Unavailable Seconds encountered by
                 a DS1 interface in the previous 24 hour interval.
                 Invalid 15 minute intervals count as 0."
          ::= { csDs3Ds1TotalEntry 4 }

     csDs3Ds1TotalCSSs OBJECT-TYPE
          SYNTAX  PerfTotalCount
          MAX-ACCESS  read-only
          STATUS  current
          DESCRIPTION
                 "The number of Controlled Slip Seconds encountered
                 by a DS1 interface in the previous 24 hour
                 interval.  Invalid 15 minute intervals count as
                 0."
          ::= { csDs3Ds1TotalEntry 5 }

     csDs3Ds1TotalPCVs OBJECT-TYPE
          SYNTAX  PerfTotalCount
          MAX-ACCESS  read-only
          STATUS  current
          DESCRIPTION
                 "The number of Path Coding Violations encountered
                 by a DS1 interface in the previous 24 hour
                 interval.  Invalid 15 minute intervals count as
                 0."
          ::= { csDs3Ds1TotalEntry 6 }

     csDs3Ds1TotalLESs OBJECT-TYPE
          SYNTAX  PerfTotalCount
          MAX-ACCESS  read-only
          STATUS  current
          DESCRIPTION
                 "The number of Line Errored Seconds encountered by
                 a DS1 interface in the previous 24 hour interval.
                 Invalid 15 minute intervals count as 0."
          ::= { csDs3Ds1TotalEntry 7 }

     csDs3Ds1TotalBESs OBJECT-TYPE
          SYNTAX PerfTotalCount
          MAX-ACCESS read-only
          STATUS current
          DESCRIPTION
                 "The number of Bursty Errored Seconds (BESs)
                 encountered by a DS1 interface in the previous 24
                 hour interval. Invalid 15 minute intervals count
                 as 0."
          ::= { csDs3Ds1TotalEntry 8 }

     csDs3Ds1TotalDMs OBJECT-TYPE
          SYNTAX PerfTotalCount
          MAX-ACCESS read-only
          STATUS current
          DESCRIPTION
                 "The number of Degraded Minutes (DMs) encountered
                 by a DS1 interface in the previous 24 hour
                 interval.  Invalid 15 minute intervals count as
                 0."
          ::= { csDs3Ds1TotalEntry 9 }

     csDs3Ds1TotalLCVs OBJECT-TYPE
          SYNTAX PerfTotalCount
          MAX-ACCESS read-only
          STATUS current
          DESCRIPTION
                 "The number of Line Code Violations (LCVs)
                 encountered by a DS1 interface in the current 15
                 minute interval.  Invalid 15 minute intervals
                 count as 0."
          ::= { csDs3Ds1TotalEntry 10 }


	--
	-- csUnchanDs3ConfigTable.  This table is used to configure
	-- Unchannelized DS3 parameters.
	-- 

    csUnchanDs3ConfigTable OBJECT-TYPE
	SYNTAX  SEQUENCE OF CsUnchanDs3ConfigEntry
	MAX-ACCESS  not-accessible
	STATUS  current
	DESCRIPTION
	       "The Unchannelized DS3 configuration table."
	::= { csOrionDs3Info 10 }

    csUnchanDs3ConfigEntry OBJECT-TYPE
	SYNTAX  CsUnchanDs3ConfigEntry
	MAX-ACCESS  not-accessible
	STATUS  current
	DESCRIPTION
	       "An entry in the Unchannelized DS3 Configuration table."
	INDEX { csUnchanDs3ConfigSlotIndex, csUnchanDs3ConfigPortIndex }
	::= { csUnchanDs3ConfigTable 1 }

    CsUnchanDs3ConfigEntry ::=
	SEQUENCE {
	csUnchanDs3ConfigSlotIndex
		Integer32,
	csUnchanDs3ConfigPortIndex
		Integer32,
	csUnchanDs3ConfigCableLength
		Integer32,
	csUnchanDs3ConfigFraming
		INTEGER,
	csUnchanDs3ConfigMdlPath
		INTEGER,
	csUnchanDs3ConfigMdlIdleSig
		INTEGER,
	csUnchanDs3ConfigMdlTestSig
		INTEGER,
	csUnchanDs3ConfigMdlEic
		DisplayString,
	csUnchanDs3ConfigMdlLic
		DisplayString,
	csUnchanDs3ConfigMdlFic
		DisplayString,
	csUnchanDs3ConfigMdlUnit
		DisplayString,
	csUnchanDs3ConfigMdlPfi
		DisplayString,
	csUnchanDs3ConfigMdlPort
		DisplayString,
	csUnchanDs3ConfigMdlGenerator
		DisplayString,
	csUnchanDs3ConfigAdminStatus
		INTEGER,
	csUnchanDs3ConfigOperStatus
		OperStatus,
	csUnchanDs3ConfigClockSource
		INTEGER,
	csUnchanDs3ConfigEncap
		INTEGER,
	csUnchanDs3ConfigSendCode
		INTEGER,
	csUnchanDs3ConfigLoopbackType
		INTEGER,
	csUnchanDs3ConfigLoopbackStatus
		INTEGER,
	csUnchanDs3ConfigLineStatus
		INTEGER,
	csUnchanDs3ConfigTimeElapsed
		INTEGER,
	csUnchanDs3ConfigValidInterval
		INTEGER,
	csUnchanDs3ConfigInvalidInterval
		INTEGER,
	csUnchanDs3ConfigDeviceType
		INTEGER
	}

    csUnchanDs3ConfigSlotIndex OBJECT-TYPE
	SYNTAX	Integer32 (1..'7fffffff'h)
	MAX-ACCESS  not-accessible
	STATUS	current
	DESCRIPTION
	       "This object identifies the blade to which this Unchannelized
		   Ds3 Port is attached. Together with csUnchanDs3ConfigPortIndex,
		   it uniquely identifies a physical port."
	::= { csUnchanDs3ConfigEntry 1 }

    csUnchanDs3ConfigPortIndex OBJECT-TYPE
	SYNTAX	Integer32 (1..'7fffffff'h)
	MAX-ACCESS  not-accessible
	STATUS	current
	DESCRIPTION
	       "This object identifies the location of the Unchannelized 
		   Ds3 Port on the blade identified by csUnchanDs3SlotIndex.  
		   Together with csUnchanDs3ConfigSlotIndex, it uniquely identifies
		   a physical port."
	::= { csUnchanDs3ConfigEntry 2 }

    csUnchanDs3ConfigCableLength OBJECT-TYPE
	SYNTAX	Integer32 (0..450)
	MAX-ACCESS  read-write
	STATUS	current
	DESCRIPTION
	       "The length of the DS3 cable."
	DEFVAL { 200 }
	::= { csUnchanDs3ConfigEntry 3 }

    csUnchanDs3ConfigFraming OBJECT-TYPE
	SYNTAX	INTEGER {
		cbit		(1),
		m23			(2),
		auto		(3),
		e3Framed	(4)
	}
	MAX-ACCESS  read-write
	STATUS	current
	DESCRIPTION
	       "The framing format used on this Ds3 Interface. The default
		    value is cbit if the interface is DS3. If the interface is E3,
			e3Framed will be used, and cannot be configured to any other types."
	::= { csUnchanDs3ConfigEntry 4 }

    csUnchanDs3ConfigMdlPath OBJECT-TYPE
	SYNTAX	INTEGER {
		enable  (1),
		disable (2)
	}
	MAX-ACCESS  read-write
	STATUS	current
	DESCRIPTION
	       "This object controls the transmission of the MDL Path message.
		   NOTE: This is applicable only for DS3."
	DEFVAL { enable }
	::= { csUnchanDs3ConfigEntry 5 }

    csUnchanDs3ConfigMdlIdleSig OBJECT-TYPE
	SYNTAX	INTEGER {
		enable  (1),
		disable (2)
	}
	MAX-ACCESS  read-write
	STATUS	current
	DESCRIPTION
	       "This object controls the transmission of the MDL Idle Signal 
	       message. NOTE: This is applicable only for DS3."
	DEFVAL { enable }
	::= { csUnchanDs3ConfigEntry 6 }

    csUnchanDs3ConfigMdlTestSig OBJECT-TYPE
	SYNTAX	INTEGER {
		enable  (1),
		disable (2)
	}
	MAX-ACCESS  read-write
	STATUS	current
	DESCRIPTION
	       "This object controls the transmission of the MDL Test Signal 
	       message. NOTE: This is applicable only for DS3."
	DEFVAL { enable }
	::= { csUnchanDs3ConfigEntry 7 }

    csUnchanDs3ConfigMdlEic OBJECT-TYPE
	SYNTAX	DisplayString (SIZE(0..10))
	MAX-ACCESS  read-write
	STATUS	current
	DESCRIPTION
	       "This object specifies the Equipment Identification Code.
		    NOTE: This is applicable only for DS3."
	::= { csUnchanDs3ConfigEntry 8 }

    csUnchanDs3ConfigMdlLic OBJECT-TYPE
	SYNTAX	DisplayString (SIZE(0..11))
	MAX-ACCESS  read-write
	STATUS	current
	DESCRIPTION
	       "This object specifies the Location Identification Code.
		    NOTE: This is applicable only for DS3."
	::= { csUnchanDs3ConfigEntry 9 }

    csUnchanDs3ConfigMdlFic OBJECT-TYPE
	SYNTAX	DisplayString (SIZE(0..10))
	MAX-ACCESS  read-write
	STATUS	current
	DESCRIPTION
	       "This object specifies the Frame Identification Code.
		    NOTE: This is applicable only for DS3."
	::= { csUnchanDs3ConfigEntry 10 }

    csUnchanDs3ConfigMdlUnit OBJECT-TYPE
	SYNTAX	DisplayString (SIZE(0..6))
	MAX-ACCESS  read-write
	STATUS	current
	DESCRIPTION
	       "This object specifies the Unit Identification Code.
		    NOTE: This is applicable only for DS3."
	::= { csUnchanDs3ConfigEntry 11 }

    csUnchanDs3ConfigMdlPfi OBJECT-TYPE
	SYNTAX	DisplayString (SIZE(0..38))
	MAX-ACCESS  read-write
	STATUS	current
	DESCRIPTION
	       "This object specifies the Facility Identification Code
	       sent in the MDL Path message. NOTE: This is applicable 
		   only for DS3."
	::= { csUnchanDs3ConfigEntry 12 }

    csUnchanDs3ConfigMdlPort OBJECT-TYPE
	SYNTAX	DisplayString (SIZE(0..38))
	MAX-ACCESS  read-write
	STATUS	current
	DESCRIPTION
	       "This object specifies the Port number string sent in the
	       MDL Idle Signal message. NOTE: This is applicable only for DS3."
	::= { csUnchanDs3ConfigEntry 13}

    csUnchanDs3ConfigMdlGenerator OBJECT-TYPE
	SYNTAX	DisplayString (SIZE(0..38))
	MAX-ACCESS  read-write
	STATUS	current
	DESCRIPTION
	       "This object specifies the Generator number string sent in the
	       MDL Test Signal message. NOTE: This is applicable only for DS3."
	::= { csUnchanDs3ConfigEntry 14}

    csUnchanDs3ConfigAdminStatus OBJECT-TYPE
	SYNTAX		INTEGER {
		enable  (1),
		disable (2)
	}
	MAX-ACCESS	read-write
	STATUS		current
	DESCRIPTION
	       "This object is used to enable/disable this Ds3/E3 port."
	DEFVAL { enable }
	::= { csUnchanDs3ConfigEntry 15 }

    csUnchanDs3ConfigOperStatus OBJECT-TYPE
	SYNTAX  OperStatus
	MAX-ACCESS  read-only
	STATUS	current
	DESCRIPTION
	       "This object indicates the current operational status of this 
	       Ds3/E3 port."
	::= { csUnchanDs3ConfigEntry 16 }

    csUnchanDs3ConfigClockSource OBJECT-TYPE
	SYNTAX INTEGER {
		internal (1),
		line     (2)
	}
	MAX-ACCESS  read-write
	STATUS  current
	DESCRIPTION
	       "This object specifies the source of the Transmit Clock
	       used on this (unchannelized) DS3.  If this
	       object is set to internal(1), a local clock source
	       is used.  If this object is set to line(2), the recovered
	       received clock is used as the transmit clock.
		   NOTE: This is applicable only for DS3."
	::= { csUnchanDs3ConfigEntry 17 }

	csUnchanDs3ConfigEncap OBJECT-TYPE
	SYNTAX INTEGER {
		none		(0),
		ppp			(1),
		frameRelay	(2),
		ciscoHdlc	(3)
	}
	MAX-ACCESS  read-write
	STATUS  current
	DESCRIPTION
		"This object specifies the encapsulation used
		on this DS3/E3 port.  If the encapsulation type
		is frameRelay(2), use the csFrameRelayTable to
		configure the Frame Relay specific parameters."
	::= { csUnchanDs3ConfigEntry 18 }

	csUnchanDs3ConfigSendCode OBJECT-TYPE
	SYNTAX INTEGER {
		ds3SendNoCode(1),
        ds3SendLineCode(2),
        ds3SendResetCode(3)
	}
	MAX-ACCESS  read-write
	STATUS  current
	DESCRIPTION
	       "This variable indicates what type of code is
            being sent across the DS3 interface by the
            device. Setting this variable causes the interface
			to begin sending the code requested.
			NOTE: This is applicable only for DS3.
            The values mean:

               sendNoCode
                   sending looped or normal data

               sendLineCode
                   sending a request for a line loopback

               sendResetCode
                   sending a loopback deactivation request "

	::= { csUnchanDs3ConfigEntry 19 }

	csUnchanDs3ConfigLoopbackType OBJECT-TYPE
	SYNTAX INTEGER {
		noLoop (1),
		lineLoop (2),
		otherLoop (3),
		inwardLoop (4),
		dualLoop (5)
	}
	MAX-ACCESS  read-write
	STATUS  current
	DESCRIPTION
	       "This object represents the desired loopback configuration
		    of the DS3 interface. 

			The values mean:
               noLoop
                 Not in the loopback state.  A device that is
                 not capable of performing a loopback on
                 the interface shall always return this as
                 its value.

               lineLoop
                 The received signal at this interface does not
                 go through the device (minimum penetration) but
                 is looped back out.

               otherLoop
                 Loopbacks that are not defined here. Currently
				 not used in the IPSX system.

               inwardLoop
                 The sent signal at this interface is looped back
                 through the device.

               dualLoop
                 Both lineLoop and inwardLoop will be active 
				 simultaneously."
	::= { csUnchanDs3ConfigEntry 20 }

	csUnchanDs3ConfigLoopbackStatus OBJECT-TYPE
	SYNTAX INTEGER (1..127)
	MAX-ACCESS  read-only
	STATUS  current
	DESCRIPTION
	       "This variable represents the current state of the
            loopback on the DS3 interface.  It contains
            information about loopbacks established by a
            manager and remotely from the far end.

            The csUnchanDs3ConfigLoopbackStatus is a bit map represented 
			as a sum, therefore is can represent multiple 
			loopbacks simultaneously.

            The various bit positions are:
                  1  ds3NoLoopback
                  2  ds3NearEndPayloadLoopback
                  4  ds3NearEndLineLoopback
                  8  ds3NearEndOtherLoopback
                 16  ds3NearEndInwardLoopback
                 32  ds3FarEndPayloadLoopback
                 64  ds3FarEndLineLoopback "
	::= { csUnchanDs3ConfigEntry 21 }

	csUnchanDs3ConfigLineStatus OBJECT-TYPE
    SYNTAX  INTEGER (1..4095)
    MAX-ACCESS  read-only
    STATUS  current
    DESCRIPTION
		"This variable indicates the Line Status of the interface.  
		 It contains loopback state information and failure state 
		 information.  The csUnchanDs3ConfigLineStatus is a bit map 
		 represented as a sum, therefore, it can represent multiple 
		 failures and a loopback (see csUnchanDs3ConfigLoopbackStatus 
		 object for the type of loopback) simultaneously.  
		 The ds3NoAlarm must be set if and only if no other flag is set. 
		 If the ds3LoopbackState bit is set, the loopback in effect
		 can be determined from the csUnchanDs3ConfigLoopbackStatus object.
       The various bit positions are:
        0     ds3NoAlarm         No alarm present
        1     ds3RcvRAIFailure   Receiving Yellow/Remote
                                  Alarm Indication
        2     ds3XmitRAIAlarm    Transmitting Yellow/Remote
                                  Alarm Indication
        3     ds3RcvAIS          Receiving AIS failure state
        4     ds3XmitAIS         Transmitting AIS
        5     ds3LOF             Receiving LOF failure state
        6     ds3LOS             Receiving LOS failure state
        7     ds3LoopbackState   Looping the received signal
        8     ds3RcvTestCode     Receiving a Test Pattern
        9     ds3OtherFailure    any line status not defined
                                  here
       10     ds3UnavailSigState Near End in Unavailable Signal
                                  State
       11     ds3NetEquipOOS     Carrier Equipment Out of Service"
    ::= { csUnchanDs3ConfigEntry 22 }

	csUnchanDs3ConfigTimeElapsed OBJECT-TYPE
    SYNTAX  INTEGER (0..899)
    MAX-ACCESS  read-only
    STATUS  current
    DESCRIPTION
		"The number of seconds that have elapsed since the beginning 
		 of the near end current error-measurement period.  If, for some
		 reason, such as an adjustment in the system's time-of-day clock,
         the current interval exceeds the maximum value, the agent will 
		 return the maximum value."
    ::= { csUnchanDs3ConfigEntry 23 }

	csUnchanDs3ConfigValidInterval OBJECT-TYPE
    SYNTAX  INTEGER (1..96)
    MAX-ACCESS  read-only
    STATUS  current
    DESCRIPTION
		"The number of previous near end intervals for which data was 
		 collected.  The value will be 96 unless the interface was 
		 brought online within the last 24 hours, in which case the 
		 value will be the number of complete 15 minute near end
         intervals since the interface has been online.  In the case
		 where the agent is a proxy, it is possible that some intervals 
		 are unavailable.  In this case, this interval is the maximum 
		 interval number for which data is available."
    ::= { csUnchanDs3ConfigEntry 24 }

	csUnchanDs3ConfigInvalidInterval OBJECT-TYPE
    SYNTAX  INTEGER (1..96)
    MAX-ACCESS  read-only
    STATUS  current
    DESCRIPTION
		"The number of intervals in the range from 0 to csDs3ConfigValidInterval
		 for which no data is available.  This object will typically be zero
         except in cases where the data for some intervals are not available 
		 (e.g., in proxy situations)."
    ::= { csUnchanDs3ConfigEntry 25 }

	csUnchanDs3ConfigDeviceType OBJECT-TYPE
	SYNTAX INTEGER {
		ds3 (1),
		e3  (2)
	}
	MAX-ACCESS  read-only
	STATUS  current
	DESCRIPTION
	       "This object indicates whether the interface is DS3 or E3."
	::= { csUnchanDs3ConfigEntry 26 }


	--
	-- Far End Statistics Group for DS3
	--
	-- To be done ...
	--

	csOrionOc3Config	  OBJECT IDENTIFIER ::= { csOrionOc3Info 1 }
    csOrionOc3Section	  OBJECT IDENTIFIER ::= { csOrionOc3Info 2 }
    csOrionOc3Line		  OBJECT IDENTIFIER ::= { csOrionOc3Info 3 }
    csOrionOc3FarEndLine  OBJECT IDENTIFIER ::= { csOrionOc3Info 4 }
    csOrionOc3Path		  OBJECT IDENTIFIER ::= { csOrionOc3Info 5 }
    csOrionOc3FarEndPath  OBJECT IDENTIFIER ::= { csOrionOc3Info 6 }
	csOrionOc3PosStats	  OBJECT IDENTIFIER ::= { csOrionOc3Info 7 }	

    --
    -- csOc3Table.  This table configures parameters for the OC-3 Ports
    --

    csOc3ConfigTable OBJECT-TYPE
	SYNTAX  SEQUENCE OF CsOc3ConfigEntry
	MAX-ACCESS  not-accessible
	STATUS  current
	DESCRIPTION
	       "The OC3 configuration table."
	::= { csOrionOc3Config 1 }

    csOc3ConfigEntry OBJECT-TYPE
	SYNTAX  CsOc3ConfigEntry
	MAX-ACCESS  not-accessible
	STATUS  current
	DESCRIPTION
	       "An entry in the DS3 Configuration table."
	INDEX { csOc3SlotIndex, csOc3PortIndex }
	::= { csOc3ConfigTable 1 }

    CsOc3ConfigEntry ::=
	SEQUENCE {
	csOc3SlotIndex				Integer32,
	csOc3PortIndex				Integer32,
	csOc3ClockSource			INTEGER,
	csOc3CrcType				INTEGER,
	csOc3SectionJ0				INTEGER,
	csOc3LineS1S0				INTEGER,
	csOc3PathC2					INTEGER,
	csOc3PathJ1					DisplayString,
	csOc3FarEndJ1				DisplayString,	
	csOc3Scramble				INTEGER,
	csOc3NearEndPerfMonControl	INTEGER,
	csOc3FarEndPerfMonControl	INTEGER,
	csOc3ApsControl				INTEGER,
	csOc3ApsForce				INTEGER,
	csOc3ApsActivePort			INTEGER,
	csOc3AlarmControl			INTEGER,
	csOc3Loopback				INTEGER,
	csOc3AdminStatus			INTEGER,
	csOc3OperStatus				OperStatus,
	csOc3TimeElapsed			Integer32,
	csOc3ValidIntervals			Integer32,
	csOc3InvalidIntervals		Integer32,
	csOc3PosEncapType			INTEGER,
	csOc3PosEmptyCellType	  	INTEGER,  -- deprecated
	csOc3PosMaxPacketSize		Integer32,
	csOc3PosOperStatus			OperStatus,  -- deprecated  
	csOc3MediumLineType			INTEGER,
	csOc3ReceivedPathJ1		DisplayString
	}


    csOc3SlotIndex OBJECT-TYPE
	SYNTAX  Integer32 (1..'7fffffff'h)
	MAX-ACCESS  not-accessible
	STATUS  current
	DESCRIPTION
	    "This object identifies the blade to which this OC3 Port
	    is attached.  Together with csOc3PortIndex, it uniquely 
	    identifies a physical port."
	::= { csOc3ConfigEntry 1 }

    csOc3PortIndex OBJECT-TYPE
	SYNTAX  Integer32 (1..'7fffffff'h)
	MAX-ACCESS  not-accessible
	STATUS  current
	DESCRIPTION
	    "This object identifies the location of the OC3 Port on the
	    blade identified by csOc3SlotIndex.  Together with 
	    csOc3SlotIndex, it uniquely identifies a physical port."
	::= { csOc3ConfigEntry 2 }

    csOc3ClockSource OBJECT-TYPE
	SYNTAX	INTEGER {
		internal (1),
		line     (2)
	}
	MAX-ACCESS  read-write
	STATUS  current
	DESCRIPTION
	    "This object identifies the source of the clock signal for 
	    this OC3 port."
	DEFVAL { internal }
	::= { csOc3ConfigEntry 3 }

    csOc3CrcType OBJECT-TYPE
	SYNTAX	INTEGER {
		crc16 (1),
		crc32 (2)
	}
	MAX-ACCESS  read-write
	STATUS	current
	DESCRIPTION
	    "This object identifies the type of CRC used on this OC3 
	    port. This is only used by Packet Over Sonet."
	DEFVAL { crc16 }
	::= { csOc3ConfigEntry 4 }

	csOc3SectionJ0 OBJECT-TYPE
	SYNTAX	INTEGER {
		hex01 (1),
		hexCC (2)
	}
	MAX-ACCESS  read-write
	STATUS	current
	DESCRIPTION
	    "This object identifies the section trace byte (j0) used on this
	    OC3 port.  If this object is set to hex01(1),
	    the value sent within the j0 (section trace byte) element
	    of the frame header is 0x01.  This value should be set for
	    interoperability with some SDH devices in Japan.  If this object 
	    is set to hexCC(2), the value of the j0 element is 0xcc.  This
	    is the default value and should be used in the majority of cases."
	DEFVAL { hexCC }
	::= { csOc3ConfigEntry 5 }

    csOc3LineS1S0 OBJECT-TYPE
	SYNTAX	INTEGER {
		oc3c (1),
		au4  (2)
	}
	MAX-ACCESS  read-write
	STATUS	current
	DESCRIPTION
	    "This object identifies the payload pointer byte (s1s0) used on 
	    this OC3 port.  If this object is set to oc3c(1),
	    the value sent within the s1s0 (payload pointer byte) element
	    of the frame header is 0.  If this object is set to au4(2), the 
	    value of the s1s0 element is 2."
	DEFVAL { oc3c }
	::= { csOc3ConfigEntry 6 }

    csOc3PathC2 OBJECT-TYPE
	SYNTAX	INTEGER {
		pos (1),
		atm	(2)
	}
	MAX-ACCESS  read-only
	STATUS	current
	DESCRIPTION
	    "This object identifies the path signal identifier used on this
	    OC3 port.  If this object is set to pppOrHdlc(1),
	    the value sent within the c2 (path signal identifier) element
	    of the frame header is 0xCF.  If this object is set to atm(2), 
	    the value of the c2 element is 0x13."
	::= { csOc3ConfigEntry 7 }

	csOc3PathJ1 OBJECT-TYPE
	SYNTAX	DisplayString (SIZE(0..62))
	MAX-ACCESS  read-write
	STATUS	current
	DESCRIPTION
	    "This object is the path trace sent in the J1 byte of path overhead.
		 It is padded by the OC3 driver with <cr> and <lf> to make up the 
		 64-byte length."
	DEFVAL { "" }
	::= { csOc3ConfigEntry 8 }

	csOc3FarEndJ1 OBJECT-TYPE
	SYNTAX	DisplayString (SIZE(0..62))
	MAX-ACCESS  read-write
	STATUS	current
	DESCRIPTION
	    "The expected path trace of the far end interface."
	DEFVAL { "" }
	::= { csOc3ConfigEntry 9 }

    csOc3Scramble OBJECT-TYPE
	SYNTAX	INTEGER {
		enable  (1),
		disable (2)
	}
	MAX-ACCESS  read-write
	STATUS	current
	DESCRIPTION
	    "This object controls the scrambling feature on this OC3 
	     port.  If this object is enabled, the SPE payload will be scrambled.  
		 If this object is diabled, the SPE payload will not be scrambled.
		 SPE payload refers to that of either ATM or POS depending on the
		 value of csOc3PathC2."
	DEFVAL { enable }
	::= { csOc3ConfigEntry 10 }

	csOc3NearEndPerfMonControl OBJECT-TYPE
	SYNTAX	INTEGER {
		enable  (1),
		disable (2)
	}
	MAX-ACCESS  read-write
	STATUS	current
	DESCRIPTION
	    ""
	DEFVAL { disable }
	::= { csOc3ConfigEntry 11 }

	csOc3FarEndPerfMonControl OBJECT-TYPE
	SYNTAX	INTEGER {
		enable  (1),
		disable (2)
	}
	MAX-ACCESS  read-write
	STATUS	current
	DESCRIPTION
	    ""
	DEFVAL { disable }
	::= { csOc3ConfigEntry 12 }

	csOc3ApsControl OBJECT-TYPE
	SYNTAX	INTEGER {
		enable  (1),
		disable (2)
	}
	MAX-ACCESS  read-write
	STATUS	current
	DESCRIPTION
	    ""
	DEFVAL { disable }
	::= { csOc3ConfigEntry 13 }

	csOc3ApsForce OBJECT-TYPE
	SYNTAX	INTEGER {
	    none            (1),
		forceToSwitch	(2)
	}
	MAX-ACCESS  read-write
	STATUS	current
	DESCRIPTION
	    "Force protection  switch. When set to 'forceToSwitch' it
		 switches the active port between the two internal ports
		 indicated by csOc3ApsActivePort object.
		 NOTE: This is an action object. Read operation 
		       returns 'none'. "
	::= { csOc3ConfigEntry 14 }

	csOc3ApsActivePort OBJECT-TYPE
	SYNTAX	INTEGER {
	    portOne (1),
		portTwo	(2)
	}
	MAX-ACCESS  read-only
	STATUS	current
	DESCRIPTION
	    "This object indicates which of the internal port is
		 currently active. The non-active one is used for protection."
	::= { csOc3ConfigEntry 15 }

	csOc3AlarmControl OBJECT-TYPE
	SYNTAX	INTEGER {
		enable  (1),
		disable (2)
	}
	MAX-ACCESS  read-write
	STATUS	current
	DESCRIPTION
	    ""
	DEFVAL { enable }
	::= { csOc3ConfigEntry 16 }

    csOc3Loopback OBJECT-TYPE
	SYNTAX	INTEGER {
		noLoop		 (1),
		facilityLoop (2),
		terminalLoop (3)
	}
	MAX-ACCESS  read-write
	STATUS	current
	DESCRIPTION
	    "The current loopback state of the SONET/SDH interface.
		 The values mean:

          noLoop
             Not in the loopback state. A device that is not
             capable of performing a loopback on this interface
             shall always return this value.

          facilityLoop
             The received signal at this interface is looped back
             out through the corresponding transmitter in the return
             direction.

          terminalLoop
             The signal that is about to be transmitted is connected
             to the associated incoming receiver."
	DEFVAL { noLoop }
	::= { csOc3ConfigEntry 17 }


    csOc3AdminStatus OBJECT-TYPE
	SYNTAX  INTEGER {
		enable  (1),
		disable (2)
	}
	MAX-ACCESS  read-write
	STATUS	current
	DESCRIPTION
	    "This object is used to enable/disable this Ds3 port."
	DEFVAL { enable }
	::= { csOc3ConfigEntry 18 }

    csOc3OperStatus OBJECT-TYPE
	SYNTAX  OperStatus
	MAX-ACCESS  read-only
	STATUS	current
	DESCRIPTION
	    "This object indicates the current operational status of this 
	    Ds3 port."
	::= { csOc3ConfigEntry 19 }

	csOc3TimeElapsed OBJECT-TYPE
	SYNTAX  Integer32 (1..900)
	MAX-ACCESS  read-only
	STATUS  current
	DESCRIPTION
		"The number of seconds that have elapsed since the beginning
		of the current measurement period."
	::= { csOc3ConfigEntry 20 }

	csOc3ValidIntervals OBJECT-TYPE
	SYNTAX  Integer32 (0..32)
	MAX-ACCESS  read-only
	STATUS  current
	DESCRIPTION
		"This object indicates the number of previous 15-minute intervals
		for which data was collected."
	::= { csOc3ConfigEntry 21 }

	csOc3InvalidIntervals OBJECT-TYPE
	SYNTAX  Integer32 (0..32)
	MAX-ACCESS  read-only
	STATUS  current
	DESCRIPTION
		"This object indicates the number of previous 15-minute intervals
		for which data was not able to be collected."
	::= { csOc3ConfigEntry 22 }

	csOc3PosEncapType OBJECT-TYPE
	SYNTAX INTEGER {
			none            (0),
			ppp             (1),
			frameRelay      (2),
			ciscoHdlc       (3)
	}
	MAX-ACCESS  read-write
	STATUS  current
	DESCRIPTION
			"This object specifies the encapsulation used
			on this port.  If the encapsulation type
			is frameRelay(2), use the csFrameRelayTable to
			configure the Frame Relay specific parameters."
	DEFVAL { none }
	::= { csOc3ConfigEntry 23 }
	
	csOc3PosEmptyCellType OBJECT-TYPE
	SYNTAX  INTEGER {
			unassigned	(1),
			idle		(2)
	}
	MAX-ACCESS  read-write
	STATUS  deprecated
	DESCRIPTION
		"This object is used to select the type of empty cell to be 
		transmitted. It is deprecated due to not being supported in POS." 
	DEFVAL { unassigned }
	::= { csOc3ConfigEntry 24 }

	csOc3PosMaxPacketSize OBJECT-TYPE
	SYNTAX  Integer32 (4..65535)
	MAX-ACCESS  read-write
	STATUS  current
	DESCRIPTION
		"This object specifies the maximum packet size required for
		 this port. This object applies to POS only." 
		::= { csOc3ConfigEntry 25 }

	csOc3PosOperStatus OBJECT-TYPE
    SYNTAX  OperStatus
    MAX-ACCESS  read-only
    STATUS  deprecated
    DESCRIPTION
        "This object indicates the current operational status of this
        channel. It is deprecated in favor of using csOc3AdminStatus
		instead. "
    ::= { csOc3ConfigEntry 26 }

	csOc3MediumLineType OBJECT-TYPE
    SYNTAX  INTEGER {
                oc3Other(1),
                oc3ShortSingleMode(2),
                oc3LongSingleMode(3),
                oc3MultiMode(4),
                oc3Coax(5),
                oc3UTP(6)
            }
    MAX-ACCESS  read-only
    STATUS  current
    DESCRIPTION
        "This object describes the line type for
        this interface. The line types are
        Short and Long Range
        Single Mode fiber or Multi-Mode fiber interfaces,
        and coax and UTP for electrical interfaces.  The
        value sonetOther should be used when the Line Type is
        not one of the listed values."
    ::= { csOc3ConfigEntry 27 }

	csOc3ReceivedPathJ1 OBJECT-TYPE
    SYNTAX  DisplayString (SIZE(0..62))
    MAX-ACCESS  read-only
    STATUS current
    DESCRIPTION
        "The actual received path trace of the far end interface." 
	DEFVAL { "" }
    ::= { csOc3ConfigEntry 28 }

-- The SONET/SDH Section Current Table

-- The SONET/SDH Section
-- current table contains various statistics
-- being collected for the current 15 minute interval.

	csOc3SectionCurrentTable OBJECT-TYPE
    SYNTAX  SEQUENCE OF CsOc3SectionCurrentEntry
    MAX-ACCESS  not-accessible
    STATUS  current
    DESCRIPTION
       "The SONET/SDH Section Current table."
     ::= { csOrionOc3Section 1 }

	csOc3SectionCurrentEntry OBJECT-TYPE
    SYNTAX  CsOc3SectionCurrentEntry
    MAX-ACCESS  not-accessible
    STATUS  current
    DESCRIPTION
       "An entry in the SONET/SDH Section Current table."
    INDEX   { csOc3SlotIndex, csOc3PortIndex }
     ::= { csOc3SectionCurrentTable 1 }

	CsOc3SectionCurrentEntry ::=
    SEQUENCE {
        csOc3SectionCurrentStatus   Integer32,
        csOc3SectionCurrentESs      PerfCurrentCount,
        csOc3SectionCurrentSESs     PerfCurrentCount,
        csOc3SectionCurrentSEFSs    PerfCurrentCount,
        csOc3SectionCurrentCVs      PerfCurrentCount
    }

	csOc3SectionCurrentStatus OBJECT-TYPE
    SYNTAX  Integer32 (1..6)
    MAX-ACCESS  read-only
    STATUS  current
    DESCRIPTION
       "This variable indicates the status of the interface.
       The sonetSectionCurrentStatus is a bit map represented
       as a sum, therefore, it can represent multiple defects
       simultaneously. The csOc3SectionNoDefect should be set 
	   if and only if no other flag is set.

       The various bit positions are:
             1   csOc3SectionNoDefect
             2   csOc3SectionLOS
             4   csOc3SectionLOF"
     ::= { csOc3SectionCurrentEntry 1 }

	csOc3SectionCurrentESs OBJECT-TYPE
    SYNTAX  PerfCurrentCount
    MAX-ACCESS  read-only
    STATUS  current
    DESCRIPTION
       "The counter associated with the number of 
	   Errored Seconds encountered by a SONET/SDH Section 
	   in the current 15-minute interval."
     ::= { csOc3SectionCurrentEntry 2 }

	csOc3SectionCurrentSESs OBJECT-TYPE
    SYNTAX  PerfCurrentCount
    MAX-ACCESS  read-only
    STATUS  current
    DESCRIPTION
       "The counter associated with the number of 
	   Severely Errored Seconds encountered by a SONET/SDH 
	   Section in the current 15-minute interval."
     ::= { csOc3SectionCurrentEntry 3 }

	csOc3SectionCurrentSEFSs OBJECT-TYPE
    SYNTAX  PerfCurrentCount
    MAX-ACCESS  read-only
    STATUS  current
    DESCRIPTION
       "The counter associated with the number of
       Severely Errored Framing Seconds
       encountered by a SONET/SDH Section in the current
       15 minute interval."
    ::= { csOc3SectionCurrentEntry 4 }

	csOc3SectionCurrentCVs OBJECT-TYPE
    SYNTAX  PerfCurrentCount
    MAX-ACCESS  read-only
    STATUS  current
    DESCRIPTION
       "The counter associated with the number of Coding
       Violations encountered by a
       SONET/SDH Section in the current 15 minute interval."
     ::= { csOc3SectionCurrentEntry 5 }


-- The SONET/SDH Section Interval Table

-- The SONET/SDH Section Interval Table
-- contains various statistics
-- collected by each system over a maximum
-- of the previous 24 hours of
-- operation.  The past 24 hours may be broken into 96
-- completed 15 minute intervals.
-- A system is required to store at
-- least 4 completed 15 minute interval.
-- The default value is 32 intervals.


	csOc3SectionIntervalTable OBJECT-TYPE
    SYNTAX  SEQUENCE OF CsOc3SectionIntervalEntry
    MAX-ACCESS  not-accessible
    STATUS  current
    DESCRIPTION
       "The SONET/SDH Section Interval table."
     ::= { csOrionOc3Section 2 }

	csOc3SectionIntervalEntry OBJECT-TYPE
    SYNTAX  CsOc3SectionIntervalEntry
    MAX-ACCESS  not-accessible
    STATUS  current
    DESCRIPTION
       "An entry in the SONET/SDH Section Interval table."
    INDEX   { csOc3SlotIndex, csOc3PortIndex,
              csOc3SectionIntervalNumber }
     ::= { csOc3SectionIntervalTable 1 }

	CsOc3SectionIntervalEntry ::=
    SEQUENCE {
         csOc3SectionIntervalNumber		Integer32,
         csOc3SectionIntervalESs		PerfIntervalCount,
         csOc3SectionIntervalSESs		PerfIntervalCount,
         csOc3SectionIntervalSEFSs		PerfIntervalCount,
         csOc3SectionIntervalCVs		PerfIntervalCount,
         csOc3SectionIntervalValidData  TruthValue
    }

	csOc3SectionIntervalNumber OBJECT-TYPE
    SYNTAX  Integer32 (1..96)
    MAX-ACCESS  not-accessible
    STATUS  current
    DESCRIPTION
      "A number between 1 and 96, which identifies the
      interval for which the set of statistics is available.
      The interval identified by 1 is the most recently
      completed 15 minute interval,
      and the interval identified
      by N is the interval immediately preceding the
      one identified
      by N-1."
     ::= { csOc3SectionIntervalEntry 1 }

	csOc3SectionIntervalESs OBJECT-TYPE
    SYNTAX  PerfIntervalCount
    MAX-ACCESS  read-only
    STATUS  current
    DESCRIPTION
       "The counter associated with the number of
       Errored Seconds encountered
       by a SONET/SDH Section in a
       particular 15-minute interval
       in the past 24 hours."
     ::= { csOc3SectionIntervalEntry 2 }

	csOc3SectionIntervalSESs OBJECT-TYPE
    SYNTAX  PerfIntervalCount
    MAX-ACCESS  read-only
    STATUS  current
    DESCRIPTION
       "The counter associated with the number of
       Severely Errored Seconds
       encountered by a SONET/SDH Section in a
       particular 15-minute interval
       in the past 24 hours."
    ::= { csOc3SectionIntervalEntry 3 }

	csOc3SectionIntervalSEFSs OBJECT-TYPE
    SYNTAX  PerfIntervalCount
    MAX-ACCESS  read-only
    STATUS  current
    DESCRIPTION
       "The counter associated with the number of
       Severely Errored Framing Seconds
       encountered by a SONET/SDH Section in a
       particular 15-minute interval
       in the past 24 hours."
    ::= { csOc3SectionIntervalEntry 4 }

	csOc3SectionIntervalCVs OBJECT-TYPE
    SYNTAX  PerfIntervalCount
    MAX-ACCESS  read-only
    STATUS  current
    DESCRIPTION
       "The counter associated with the number of Coding
       Violations encountered by a
       SONET/SDH Section in a particular 15-minute interval
       in the past 24 hours."
    ::= { csOc3SectionIntervalEntry 5 }

	csOc3SectionIntervalValidData OBJECT-TYPE
    SYNTAX  TruthValue
    MAX-ACCESS  read-only
    STATUS  current
    DESCRIPTION
       "This variable indicates if the data for this
        interval is valid."
    ::= { csOc3SectionIntervalEntry 6 }


-- The SONET/SDH Section Day Table

-- The SONET/SDH Section
-- day table contains various statistics
-- being collected for the day.

	csOc3SectionDayTable OBJECT-TYPE
    SYNTAX  SEQUENCE OF CsOc3SectionDayEntry
    MAX-ACCESS  not-accessible
    STATUS  current
    DESCRIPTION
       "The SONET/SDH Section Day table."
     ::= { csOrionOc3Section 3 }

	csOc3SectionDayEntry OBJECT-TYPE
    SYNTAX  CsOc3SectionDayEntry
    MAX-ACCESS  not-accessible
    STATUS  current
    DESCRIPTION
       "An entry in the SONET/SDH Section Day table."
    INDEX   { csOc3SlotIndex, csOc3PortIndex }
     ::= { csOc3SectionDayTable 1 }

	CsOc3SectionDayEntry ::=
    SEQUENCE {
        csOc3SectionDayESs      PerfCurrentCount,
        csOc3SectionDaySESs     PerfCurrentCount,
        csOc3SectionDaySEFSs    PerfCurrentCount,
        csOc3SectionDayCVs      PerfCurrentCount
    }

	csOc3SectionDayESs OBJECT-TYPE
    SYNTAX  PerfCurrentCount
    MAX-ACCESS  read-only
    STATUS  current
    DESCRIPTION
       "The counter associated with the number of 
	   Errored Seconds encountered by a SONET/SDH Section 
	   for the day."
     ::= { csOc3SectionDayEntry 1 }

	csOc3SectionDaySESs OBJECT-TYPE
    SYNTAX  PerfCurrentCount
    MAX-ACCESS  read-only
    STATUS  current
    DESCRIPTION
       "The counter associated with the number of 
	   Severely Errored Seconds encountered by a SONET/SDH 
	   Section for the day."
     ::= { csOc3SectionDayEntry 2 }

	csOc3SectionDaySEFSs OBJECT-TYPE
    SYNTAX  PerfCurrentCount
    MAX-ACCESS  read-only
    STATUS  current
    DESCRIPTION
       "The counter associated with the number of
       Severely Errored Framing Seconds
       encountered by a SONET/SDH Section for the day."
    ::= { csOc3SectionDayEntry 3 }

	csOc3SectionDayCVs OBJECT-TYPE
    SYNTAX  PerfCurrentCount
    MAX-ACCESS  read-only
    STATUS  current
    DESCRIPTION
       "The counter associated with the number of Coding
       Violations encountered by a
       SONET/SDH Section for the day."
     ::= { csOc3SectionDayEntry 4 }


-- The SONET/SDH Section Previous Day Table

-- The SONET/SDH Section
-- day table contains various statistics
-- being collected for the previous day.

	csOc3SectionPrevDayTable OBJECT-TYPE
    SYNTAX  SEQUENCE OF CsOc3SectionPrevDayEntry
    MAX-ACCESS  not-accessible
    STATUS  current
    DESCRIPTION
       "The SONET/SDH Section Previous Day table."
     ::= { csOrionOc3Section 4 }

	csOc3SectionPrevDayEntry OBJECT-TYPE
    SYNTAX  CsOc3SectionPrevDayEntry
    MAX-ACCESS  not-accessible
    STATUS  current
    DESCRIPTION
       "An entry in the SONET/SDH Section Day table."
    INDEX   { csOc3SlotIndex, csOc3PortIndex }
     ::= { csOc3SectionPrevDayTable 1 }

	CsOc3SectionPrevDayEntry ::=
    SEQUENCE {
        csOc3SectionPrevDayESs      PerfCurrentCount,
        csOc3SectionPrevDaySESs     PerfCurrentCount,
        csOc3SectionPrevDaySEFSs    PerfCurrentCount,
        csOc3SectionPrevDayCVs      PerfCurrentCount
    }

	csOc3SectionPrevDayESs OBJECT-TYPE
    SYNTAX  PerfCurrentCount
    MAX-ACCESS  read-only
    STATUS  current
    DESCRIPTION
       "The counter associated with the number of 
	   Errored Seconds encountered by a SONET/SDH Section 
	   for the previous day."
     ::= { csOc3SectionPrevDayEntry 1 }

	csOc3SectionPrevDaySESs OBJECT-TYPE
    SYNTAX  PerfCurrentCount
    MAX-ACCESS  read-only
    STATUS  current
    DESCRIPTION
       "The counter associated with the number of 
	   Severely Errored Seconds encountered by a SONET/SDH 
	   Section for the previous day."
     ::= { csOc3SectionPrevDayEntry 2 }

	csOc3SectionPrevDaySEFSs OBJECT-TYPE
    SYNTAX  PerfCurrentCount
    MAX-ACCESS  read-only
    STATUS  current
    DESCRIPTION
       "The counter associated with the number of
       Severely Errored Framing Seconds
       encountered by a SONET/SDH Section for the previous day."
    ::= { csOc3SectionPrevDayEntry 3 }

	csOc3SectionPrevDayCVs OBJECT-TYPE
    SYNTAX  PerfCurrentCount
    MAX-ACCESS  read-only
    STATUS  current
    DESCRIPTION
       "The counter associated with the number of Coding
       Violations encountered by a
       SONET/SDH Section for the previous day."
     ::= { csOc3SectionPrevDayEntry 4 }


-- the SONET/SDH Line Current Table

-- The SONET/SDH Line
-- current table contains various statistics
-- being collected for the current 15 minute interval.

	csOc3LineCurrentTable OBJECT-TYPE
    SYNTAX  SEQUENCE OF CsOc3LineCurrentEntry
    MAX-ACCESS  not-accessible
    STATUS  current
    DESCRIPTION
      "The SONET/SDH Line Current table."
    ::= { csOrionOc3Line 1 }

	csOc3LineCurrentEntry OBJECT-TYPE
    SYNTAX  CsOc3LineCurrentEntry
    MAX-ACCESS  not-accessible
    STATUS  current
    DESCRIPTION
      "An entry in the SONET/SDH Line Current table."
    INDEX   { csOc3SlotIndex, csOc3PortIndex }
    ::= { csOc3LineCurrentTable 1 }

	CsOc3LineCurrentEntry ::=
    SEQUENCE {
         csOc3LineCurrentStatus    Integer32,
         csOc3LineCurrentESs       PerfCurrentCount,
         csOc3LineCurrentSESs      PerfCurrentCount,
         csOc3LineCurrentCVs       PerfCurrentCount,
         csOc3LineCurrentUASs      PerfCurrentCount,
         csOc3LineCurrentFCs       PerfCurrentCount
     }

	csOc3LineCurrentStatus OBJECT-TYPE
    SYNTAX  Integer32 (1..6)
    MAX-ACCESS  read-only
    STATUS  current
    DESCRIPTION
       "This variable indicates the
       status of the interface.
       The sonetLineCurrentStatus
       is a bit map represented
       as a sum, therefore,
       it can represent multiple defects
       simultaneously.
       The sonetLineNoDefect should be
       set if and only if
       no other flag is set.

       The various bit positions are:
        1   csOc3LineNoDefect
        2   csOc3LineAIS
        4   csOc3LineRDI"
     ::= { csOc3LineCurrentEntry 1 }

	csOc3LineCurrentESs OBJECT-TYPE
    SYNTAX  PerfCurrentCount
    MAX-ACCESS  read-only
    STATUS  current
    DESCRIPTION
     "The counter associated with the number of Errored
     Seconds encountered by a SONET/SDH
     Line in the current 15 minute interval."
    ::= { csOc3LineCurrentEntry 2 }

	csOc3LineCurrentSESs OBJECT-TYPE
    SYNTAX  PerfCurrentCount
    MAX-ACCESS  read-only
    STATUS  current
    DESCRIPTION
     "The counter associated with the number of
     Severely Errored Seconds
     encountered by a SONET/SDH Line in the current 15
     minute
     interval."
    ::= { csOc3LineCurrentEntry 3 }

	csOc3LineCurrentCVs OBJECT-TYPE
    SYNTAX  PerfCurrentCount
    MAX-ACCESS  read-only
    STATUS  current
    DESCRIPTION
     "The counter associated with the number of Coding
     Violations encountered by a
     SONET/SDH Line in the current 15 minute interval."
    ::= { csOc3LineCurrentEntry 4 }

	csOc3LineCurrentUASs OBJECT-TYPE
    SYNTAX  PerfCurrentCount
    MAX-ACCESS  read-only
    STATUS  current
    DESCRIPTION
     "The counter associated with the number of
     Unavailable Seconds
     encountered by a SONET/SDH Line in the current 15
     minute
     interval."
    ::= { csOc3LineCurrentEntry 5 }

	csOc3LineCurrentFCs OBJECT-TYPE
    SYNTAX  PerfCurrentCount
    MAX-ACCESS  read-only
    STATUS  current
    DESCRIPTION
     "The counter associated with the number of
     failure counts encountered by a SONET/SDH Line 
	 in the current 15 minute interval."
    ::= { csOc3LineCurrentEntry 6 }

-- the SONET/SDH Line Interval Table

-- The SONET/SDH Line Interval Table
-- contains various statistics
-- collected by each system over a maximum
-- of the previous 24 hours of
-- operation.  The past 24 hours may be broken into 96
-- completed 15 minute intervals.
-- A system is required to store at
-- least 4 completed 15 minute interval.
-- The default value is 32 intervals.

	csOc3LineIntervalTable OBJECT-TYPE
    SYNTAX  SEQUENCE OF CsOc3LineIntervalEntry
    MAX-ACCESS  not-accessible
    STATUS  current
    DESCRIPTION
       "The SONET/SDH Line Interval table."
     ::= { csOrionOc3Line 2 }

	csOc3LineIntervalEntry OBJECT-TYPE
    SYNTAX  CsOc3LineIntervalEntry
    MAX-ACCESS  not-accessible
    STATUS  current
    DESCRIPTION
       "An entry in the SONET/SDH Line Interval table."
   INDEX   { csOc3SlotIndex, csOc3PortIndex,
             csOc3LineIntervalNumber }
   ::= { csOc3LineIntervalTable 1 }

	CsOc3LineIntervalEntry ::=
    SEQUENCE {
        csOc3LineIntervalNumber    Integer32,
        csOc3LineIntervalESs       PerfIntervalCount,
        csOc3LineIntervalSESs      PerfIntervalCount,
        csOc3LineIntervalCVs       PerfIntervalCount,
        csOc3LineIntervalUASs      PerfIntervalCount,
        csOc3LineIntervalValidData TruthValue,
        csOc3LineIntervalFCs       PerfIntervalCount
    }

	csOc3LineIntervalNumber OBJECT-TYPE
    SYNTAX  Integer32 (1..96)
    MAX-ACCESS  not-accessible
    STATUS  current
    DESCRIPTION
        "A number between 1 and 96, which identifies the
        interval for which the set of statistics is available.
        The interval identified by 1 is the most recently
        completed 15 minute interval,
        and the interval identified
        by N is the interval immediately preceding the
        one identified
        by N-1."
     ::= { csOc3LineIntervalEntry 1 }

	csOc3LineIntervalESs OBJECT-TYPE
    SYNTAX  PerfIntervalCount
    MAX-ACCESS  read-only
    STATUS  current
    DESCRIPTION
       "The counter associated with the number of
       Errored Seconds encountered
       by a SONET/SDH Line in a
       particular 15-minute interval
       in the past 24 hours."
     ::= { csOc3LineIntervalEntry 2 }

	csOc3LineIntervalSESs OBJECT-TYPE
    SYNTAX  PerfIntervalCount
    MAX-ACCESS  read-only
    STATUS  current
    DESCRIPTION
       "The counter associated with the number of
       Severely Errored Seconds
       encountered by a SONET/SDH Line in a
       particular 15-minute interval
       in the past 24 hours."
      ::= { csOc3LineIntervalEntry 3 }

	csOc3LineIntervalCVs OBJECT-TYPE
    SYNTAX  PerfIntervalCount
    MAX-ACCESS  read-only
    STATUS  current
    DESCRIPTION
      "The counter associated with the number of Coding
      Violations encountered by a
      SONET/SDH Line in a
      particular 15-minute interval
      in the past 24 hours."
    ::= { csOc3LineIntervalEntry 4 }

	csOc3LineIntervalUASs OBJECT-TYPE
    SYNTAX  PerfIntervalCount
    MAX-ACCESS  read-only
    STATUS  current
    DESCRIPTION
      "The counter associated with the
      number of Unavailable Seconds
      encountered by a SONET/SDH Line in
      a particular 15-minute interval
      in the past 24 hours."
    ::= { csOc3LineIntervalEntry 5 }

	csOc3LineIntervalValidData OBJECT-TYPE
    SYNTAX  TruthValue
    MAX-ACCESS  read-only
    STATUS  current
    DESCRIPTION
       "This variable indicates if the data for this
        interval is valid."
    ::= { csOc3LineIntervalEntry 6 }

	csOc3LineIntervalFCs OBJECT-TYPE
    SYNTAX  PerfIntervalCount
    MAX-ACCESS  read-only
    STATUS  current
    DESCRIPTION
      "The counter associated with the
      number of failure counts 
      encountered by a SONET/SDH Line in
      a particular 15-minute interval
      in the past 24 hours."
    ::= { csOc3LineIntervalEntry 7 }

-- the SONET/SDH Line Day Table

-- The SONET/SDH Line
-- current table contains various statistics
-- being collected for the day.

	csOc3LineDayTable OBJECT-TYPE
    SYNTAX  SEQUENCE OF CsOc3LineDayEntry
    MAX-ACCESS  not-accessible
    STATUS  current
    DESCRIPTION
      "The SONET/SDH Line Day table."
    ::= { csOrionOc3Line 3 }

	csOc3LineDayEntry OBJECT-TYPE
    SYNTAX  CsOc3LineDayEntry
    MAX-ACCESS  not-accessible
    STATUS  current
    DESCRIPTION
      "An entry in the SONET/SDH Line Day table."
    INDEX   { csOc3SlotIndex, csOc3PortIndex }
    ::= { csOc3LineDayTable 1 }

	CsOc3LineDayEntry ::=
    SEQUENCE {
         csOc3LineDayESs       PerfCurrentCount,
         csOc3LineDaySESs      PerfCurrentCount,
         csOc3LineDayCVs       PerfCurrentCount,
         csOc3LineDayUASs      PerfCurrentCount,
         csOc3LineDayFCs       PerfCurrentCount
     }

	csOc3LineDayESs OBJECT-TYPE
    SYNTAX  PerfCurrentCount
    MAX-ACCESS  read-only
    STATUS  current
    DESCRIPTION
     "The counter associated with the number of Errored
     Seconds encountered by a SONET/SDH
     Line for the day."
    ::= { csOc3LineDayEntry 1 }

	csOc3LineDaySESs OBJECT-TYPE
    SYNTAX  PerfCurrentCount
    MAX-ACCESS  read-only
    STATUS  current
    DESCRIPTION
     "The counter associated with the number of
     Severely Errored Seconds
     encountered by a SONET/SDH Line for the day."
    ::= { csOc3LineDayEntry 2 }

	csOc3LineDayCVs OBJECT-TYPE
    SYNTAX  PerfCurrentCount
    MAX-ACCESS  read-only
    STATUS  current
    DESCRIPTION
     "The counter associated with the number of Coding
     Violations encountered by a
     SONET/SDH Line for the day."
    ::= { csOc3LineDayEntry 3 }

	csOc3LineDayUASs OBJECT-TYPE
    SYNTAX  PerfCurrentCount
    MAX-ACCESS  read-only
    STATUS  current
    DESCRIPTION
     "The counter associated with the number of
     Unavailable Seconds
     encountered by a SONET/SDH Line for the day."
    ::= { csOc3LineDayEntry 4 }

	csOc3LineDayFCs OBJECT-TYPE
    SYNTAX  PerfCurrentCount
    MAX-ACCESS  read-only
    STATUS  current
    DESCRIPTION
     "The counter associated with the number of
     failure counts 
     encountered by a SONET/SDH Line for the day."
    ::= { csOc3LineDayEntry 5 }

-- the SONET/SDH Line Previous Day Table

-- The SONET/SDH Line
-- current table contains various statistics
-- being collected for the previous day.

	csOc3LinePrevDayTable OBJECT-TYPE
    SYNTAX  SEQUENCE OF CsOc3LinePrevDayEntry
    MAX-ACCESS  not-accessible
    STATUS  current
    DESCRIPTION
      "The SONET/SDH Line Day table."
    ::= { csOrionOc3Line 4 }

	csOc3LinePrevDayEntry OBJECT-TYPE
    SYNTAX  CsOc3LinePrevDayEntry
    MAX-ACCESS  not-accessible
    STATUS  current
    DESCRIPTION
      "An entry in the SONET/SDH Line Previous Day table."
    INDEX   { csOc3SlotIndex, csOc3PortIndex }
    ::= { csOc3LinePrevDayTable 1 }

	CsOc3LinePrevDayEntry ::=
    SEQUENCE {
         csOc3LinePrevDayESs       PerfCurrentCount,
         csOc3LinePrevDaySESs      PerfCurrentCount,
         csOc3LinePrevDayCVs       PerfCurrentCount,
         csOc3LinePrevDayUASs      PerfCurrentCount,
         csOc3LinePrevDayFCs       PerfCurrentCount
     }

	csOc3LinePrevDayESs OBJECT-TYPE
    SYNTAX  PerfCurrentCount
    MAX-ACCESS  read-only
    STATUS  current
    DESCRIPTION
     "The counter associated with the number of Errored
     Seconds encountered by a SONET/SDH
     Line for the previous day."
    ::= { csOc3LinePrevDayEntry 1 }

	csOc3LinePrevDaySESs OBJECT-TYPE
    SYNTAX  PerfCurrentCount
    MAX-ACCESS  read-only
    STATUS  current
    DESCRIPTION
     "The counter associated with the number of
     Severely Errored Seconds
     encountered by a SONET/SDH Line for the previous day."
    ::= { csOc3LinePrevDayEntry 2 }

	csOc3LinePrevDayCVs OBJECT-TYPE
    SYNTAX  PerfCurrentCount
    MAX-ACCESS  read-only
    STATUS  current
    DESCRIPTION
     "The counter associated with the number of Coding
     Violations encountered by a
     SONET/SDH Line for the previous day."
    ::= { csOc3LinePrevDayEntry 3 }

	csOc3LinePrevDayUASs OBJECT-TYPE
    SYNTAX  PerfCurrentCount
    MAX-ACCESS  read-only
    STATUS  current
    DESCRIPTION
     "The counter associated with the number of
     Unavailable Seconds
     encountered by a SONET/SDH Line for the previous day."
    ::= { csOc3LinePrevDayEntry 4 }

	csOc3LinePrevDayFCs OBJECT-TYPE
    SYNTAX  PerfCurrentCount
    MAX-ACCESS  read-only
    STATUS  current
    DESCRIPTION
     "The counter associated with the number of
     failure counts 
     encountered by a SONET/SDH Line for the previous day."
    ::= { csOc3LinePrevDayEntry 5 }

-- the SONET/SDH Path Current Table

-- The SONET/SDH Path
-- current table contains various statistics
-- being collected for the current 15 minute interval.

	csOc3PathCurrentTable OBJECT-TYPE
    SYNTAX  SEQUENCE OF CsOc3PathCurrentEntry
    MAX-ACCESS  not-accessible
    STATUS  current
    DESCRIPTION
     "The SONET/SDH Path Current table."
	::= { csOrionOc3Path 1 }

	csOc3PathCurrentEntry OBJECT-TYPE
    SYNTAX  CsOc3PathCurrentEntry
    MAX-ACCESS  not-accessible
    STATUS  current
    DESCRIPTION
     "An entry in the SONET/SDH Path Current table."
    INDEX   { csOc3SlotIndex, csOc3PortIndex }
	::= { csOc3PathCurrentTable 1 }

	CsOc3PathCurrentEntry ::=
    SEQUENCE {
        csOc3PathCurrentWidth      INTEGER,
        csOc3PathCurrentStatus     Integer32,
        csOc3PathCurrentESs        PerfCurrentCount,
        csOc3PathCurrentSESs       PerfCurrentCount,
        csOc3PathCurrentCVs        PerfCurrentCount,
        csOc3PathCurrentUASs       PerfCurrentCount,
        csOc3PathCurrentFCs        PerfCurrentCount
    }

	csOc3PathCurrentWidth OBJECT-TYPE
    SYNTAX  INTEGER  {
            sts1(1),
            sts3cSTM1(2),
            sts12cSTM4(3),
            sts24c(4),
            sts48cSTM16(5)
     }
    MAX-ACCESS  read-only
    STATUS  current
    DESCRIPTION
     "A value that indicates the type of the SONET/SDH
     Path.  For SONET, the assigned types are
     the STS-Nc SPEs, where N = 1, 3, 12, 24, and 48.
     STS-1 is equal to 51.84 Mbps.  For SDH, the assigned
     types are the STM-Nc VCs, where N = 1, 4, and 16."
	::= { csOc3PathCurrentEntry 1 }

	csOc3PathCurrentStatus OBJECT-TYPE
    SYNTAX  Integer32 (1..62)
    MAX-ACCESS  read-only
    STATUS  current
    DESCRIPTION
      "This variable indicates the
      status of the interface.
      The sonetPathCurrentStatus
      is a bit map represented
      as a sum, therefore,
      it can represent multiple defects
      simultaneously.
      The sonetPathNoDefect should be
      set if and only if
      no other flag is set.

      The various bit positions are:
         1   sonetPathNoDefect
         2   sonetPathSTSLOP
         4   sonetPathSTSAIS
         8   sonetPathSTSRDI
        16   sonetPathUnequipped
        32   sonetPathSignalLabelMismatch"
	::= { csOc3PathCurrentEntry 2 }

	csOc3PathCurrentESs OBJECT-TYPE
    SYNTAX  PerfCurrentCount
    MAX-ACCESS  read-only
    STATUS  current
    DESCRIPTION
     "The counter associated with the number of Errored
     Seconds encountered by a SONET/SDH
     Path in the current 15 minute interval."
	::= { csOc3PathCurrentEntry 3 }

	csOc3PathCurrentSESs OBJECT-TYPE
    SYNTAX  PerfCurrentCount
    MAX-ACCESS  read-only
    STATUS  current
    DESCRIPTION
     "The counter associated with the number of
     Severely Errored Seconds
     encountered by a SONET/SDH Path in the current 15
     minute
     interval."
	::= { csOc3PathCurrentEntry 4 }

	csOc3PathCurrentCVs OBJECT-TYPE
    SYNTAX  PerfCurrentCount
    MAX-ACCESS  read-only
    STATUS  current
    DESCRIPTION
     "The counter associated with the number of Coding
     Violations encountered by a
     SONET/SDH Path in the current 15 minute interval."
	::= { csOc3PathCurrentEntry 5 }

	csOc3PathCurrentUASs OBJECT-TYPE
    SYNTAX  PerfCurrentCount
    MAX-ACCESS  read-only
    STATUS  current
    DESCRIPTION
     "The counter associated with the number of
     Unavailable Seconds
     encountered by a Path in the current
     15 minute interval."
	::= { csOc3PathCurrentEntry 6 }

	csOc3PathCurrentFCs OBJECT-TYPE
    SYNTAX  PerfCurrentCount
    MAX-ACCESS  read-only
    STATUS  current
    DESCRIPTION
     "The counter associated with the number of
     failure counts 
     encountered by a Path in the current
     15 minute interval."
	::= { csOc3PathCurrentEntry 7 }

-- The SONET/SDH Path Interval Table
-- contains various statistics
-- collected by each system over a maximum
-- of the previous 24 hours of
-- operation.  The past 24 hours may be broken into 96
-- completed 15 minute intervals.
-- A system is required to store at
-- least 4 completed 15 minute interval.
-- The default value is 32 intervals.

	csOc3PathIntervalTable OBJECT-TYPE
    SYNTAX  SEQUENCE OF CsOc3PathIntervalEntry
    MAX-ACCESS  not-accessible
    STATUS  current
    DESCRIPTION
     "The SONET/SDH Path Interval table."
	::= { csOrionOc3Path 2 }

	csOc3PathIntervalEntry OBJECT-TYPE
    SYNTAX  CsOc3PathIntervalEntry
    MAX-ACCESS  not-accessible
    STATUS  current
    DESCRIPTION
     "An entry in the SONET/SDH Path Interval table."
    INDEX   { csOc3SlotIndex, csOc3PortIndex,
              csOc3PathIntervalNumber }
	::= { csOc3PathIntervalTable 1 }

	CsOc3PathIntervalEntry ::=
    SEQUENCE {
         csOc3PathIntervalNumber     Integer32,
         csOc3PathIntervalESs        PerfIntervalCount,
         csOc3PathIntervalSESs       PerfIntervalCount,
         csOc3PathIntervalCVs        PerfIntervalCount,
         csOc3PathIntervalUASs       PerfIntervalCount,
         csOc3PathIntervalValidData  TruthValue,
         csOc3PathIntervalFCs        PerfIntervalCount
    }

	csOc3PathIntervalNumber OBJECT-TYPE
    SYNTAX  Integer32 (1..96)
    MAX-ACCESS  not-accessible
    STATUS  current
    DESCRIPTION
       "A number between 1 and 96, which identifies the
       interval for which the set of statistics is available.
       The interval identified by 1 is the most recently
       completed 15 minute interval,
       and the interval identified
       by N is the interval immediately preceding the
       one identified
       by N-1."
	::= { csOc3PathIntervalEntry 1 }

	csOc3PathIntervalESs OBJECT-TYPE
    SYNTAX  PerfIntervalCount
    MAX-ACCESS  read-only
    STATUS  current
    DESCRIPTION
     "The counter associated with the number of
     Errored Seconds encountered
     by a SONET/SDH Path in a
     particular 15-minute interval
     in the past 24 hours."
	::= { csOc3PathIntervalEntry 2 }

	csOc3PathIntervalSESs OBJECT-TYPE
    SYNTAX  PerfIntervalCount
    MAX-ACCESS  read-only
    STATUS  current
    DESCRIPTION
     "The counter associated with the number of
     Severely Errored Seconds
     encountered by a SONET/SDH Path in
     a particular 15-minute interval
     in the past 24 hours."
	::= { csOc3PathIntervalEntry 3 }

	csOc3PathIntervalCVs OBJECT-TYPE
    SYNTAX  PerfIntervalCount
    MAX-ACCESS  read-only
    STATUS  current
    DESCRIPTION
     "The counter associated with the number of Coding
     Violations encountered by a
     SONET/SDH Path in a particular 15-minute interval
     in the past 24 hours."
	::= { csOc3PathIntervalEntry 4 }

	csOc3PathIntervalUASs OBJECT-TYPE
    SYNTAX  PerfIntervalCount
    MAX-ACCESS  read-only
    STATUS  current
    DESCRIPTION
     "The counter associated with the number of
     Unavailable Seconds
     encountered by a Path in a
     particular 15-minute interval
     in the past 24 hours."
	::= { csOc3PathIntervalEntry 5 }

	csOc3PathIntervalValidData OBJECT-TYPE
    SYNTAX  TruthValue
    MAX-ACCESS  read-only
    STATUS  current
    DESCRIPTION
       "This variable indicates if the data for this
        interval is valid."
    ::= { csOc3PathIntervalEntry 6 }

	csOc3PathIntervalFCs OBJECT-TYPE
    SYNTAX  PerfIntervalCount
    MAX-ACCESS  read-only
    STATUS  current
    DESCRIPTION
     "The counter associated with the number of
     failure counts 
     encountered by a Path in a
     particular 15-minute interval
     in the past 24 hours."
	::= { csOc3PathIntervalEntry 7 }

-- the SONET/SDH Path Day Table

-- The SONET/SDH Path
-- current table contains various statistics
-- being collected for the day.

	csOc3PathDayTable OBJECT-TYPE
    SYNTAX  SEQUENCE OF CsOc3PathDayEntry
    MAX-ACCESS  not-accessible
    STATUS  current
    DESCRIPTION
     "The SONET/SDH Path Day table."
	::= { csOrionOc3Path 3 }

	csOc3PathDayEntry OBJECT-TYPE
    SYNTAX  CsOc3PathDayEntry
    MAX-ACCESS  not-accessible
    STATUS  current
    DESCRIPTION
     "An entry in the SONET/SDH Path Day table."
    INDEX   { csOc3SlotIndex, csOc3PortIndex }
	::= { csOc3PathDayTable 1 }

	CsOc3PathDayEntry ::=
    SEQUENCE {
        csOc3PathDayESs        PerfCurrentCount,
        csOc3PathDaySESs       PerfCurrentCount,
        csOc3PathDayCVs        PerfCurrentCount,
        csOc3PathDayUASs       PerfCurrentCount,
        csOc3PathDayFCs        PerfCurrentCount
    }

	csOc3PathDayESs OBJECT-TYPE
    SYNTAX  PerfCurrentCount
    MAX-ACCESS  read-only
    STATUS  current
    DESCRIPTION
     "The counter associated with the number of Errored
     Seconds encountered by a SONET/SDH
     Path for the day."
	::= { csOc3PathDayEntry 1 }

	csOc3PathDaySESs OBJECT-TYPE
    SYNTAX  PerfCurrentCount
    MAX-ACCESS  read-only
    STATUS  current
    DESCRIPTION
     "The counter associated with the number of
     Severely Errored Seconds
     encountered by a SONET/SDH Path for the day."
	::= { csOc3PathDayEntry 2 }

	csOc3PathDayCVs OBJECT-TYPE
    SYNTAX  PerfCurrentCount
    MAX-ACCESS  read-only
    STATUS  current
    DESCRIPTION
     "The counter associated with the number of Coding
     Violations encountered by a
     SONET/SDH Path for the day."
	::= { csOc3PathDayEntry 3 }

	csOc3PathDayUASs OBJECT-TYPE
    SYNTAX  PerfCurrentCount
    MAX-ACCESS  read-only
    STATUS  current
    DESCRIPTION
     "The counter associated with the number of
     Unavailable Seconds
     encountered by a Path for the day."
	::= { csOc3PathDayEntry 4 }

	csOc3PathDayFCs OBJECT-TYPE
    SYNTAX  PerfCurrentCount
    MAX-ACCESS  read-only
    STATUS  current
    DESCRIPTION
     "The counter associated with the number of
     failure counts 
     encountered by a Path for the day."
	::= { csOc3PathDayEntry 5 }

-- the SONET/SDH Path Previous Day Table

-- The SONET/SDH Path
-- current table contains various statistics
-- being collected for the previous day.

	csOc3PathPrevDayTable OBJECT-TYPE
    SYNTAX  SEQUENCE OF CsOc3PathPrevDayEntry
    MAX-ACCESS  not-accessible
    STATUS  current
    DESCRIPTION
     "The SONET/SDH Path Previous Day table."
	::= { csOrionOc3Path 4 }

	csOc3PathPrevDayEntry OBJECT-TYPE
    SYNTAX  CsOc3PathPrevDayEntry
    MAX-ACCESS  not-accessible
    STATUS  current
    DESCRIPTION
     "An entry in the SONET/SDH Path Day table."
    INDEX   { csOc3SlotIndex, csOc3PortIndex }
	::= { csOc3PathPrevDayTable 1 }

	CsOc3PathPrevDayEntry ::=
    SEQUENCE {
        csOc3PathPrevDayESs        PerfCurrentCount,
        csOc3PathPrevDaySESs       PerfCurrentCount,
        csOc3PathPrevDayCVs        PerfCurrentCount,
        csOc3PathPrevDayUASs       PerfCurrentCount,
        csOc3PathPrevDayFCs        PerfCurrentCount
    }

	csOc3PathPrevDayESs OBJECT-TYPE
    SYNTAX  PerfCurrentCount
    MAX-ACCESS  read-only
    STATUS  current
    DESCRIPTION
     "The counter associated with the number of Errored
     Seconds encountered by a SONET/SDH
     Path for the previous day."
	::= { csOc3PathPrevDayEntry 1 }

	csOc3PathPrevDaySESs OBJECT-TYPE
    SYNTAX  PerfCurrentCount
    MAX-ACCESS  read-only
    STATUS  current
    DESCRIPTION
     "The counter associated with the number of
     Severely Errored Seconds
     encountered by a SONET/SDH Path for the previous day."
	::= { csOc3PathPrevDayEntry 2 }

	csOc3PathPrevDayCVs OBJECT-TYPE
    SYNTAX  PerfCurrentCount
    MAX-ACCESS  read-only
    STATUS  current
    DESCRIPTION
     "The counter associated with the number of Coding
     Violations encountered by a
     SONET/SDH Path for the previous day."
	::= { csOc3PathPrevDayEntry 3 }

	csOc3PathPrevDayUASs OBJECT-TYPE
    SYNTAX  PerfCurrentCount
    MAX-ACCESS  read-only
    STATUS  current
    DESCRIPTION
     "The counter associated with the number of
     Unavailable Seconds
     encountered by a Path for the previous day."
	::= { csOc3PathPrevDayEntry 4 }

	csOc3PathPrevDayFCs OBJECT-TYPE
    SYNTAX  PerfCurrentCount
    MAX-ACCESS  read-only
    STATUS  current
    DESCRIPTION
     "The counter associated with the number of
     failure counts 
     encountered by a Path for the previous day."
	::= { csOc3PathPrevDayEntry 5 }


-- the OC3/POS statistics counter Table

	csOc3PosStatsTable OBJECT-TYPE
    SYNTAX  SEQUENCE OF CsOc3PosStatsEntry
    MAX-ACCESS  not-accessible
    STATUS  current
    DESCRIPTION
     "The OC3/POS statistics counter table."
	::= { csOrionOc3PosStats 1 }

	csOc3PosStatsEntry OBJECT-TYPE
    SYNTAX  CsOc3PosStatsEntry
    MAX-ACCESS  not-accessible
    STATUS  current
    DESCRIPTION
     "An entry in the OC3/POS statistics counter table."
    INDEX   { csOc3SlotIndex, csOc3PortIndex }
	::= { csOc3PosStatsTable 1 }

	CsOc3PosStatsEntry ::=
    SEQUENCE {
        csOc3PosRcvBytes    				Counter32,
        csOc3PosRcvFrames   				Counter32,
        csOc3PosRcvAbortedFrames			Counter32,
        csOc3PosRcvFrameFCSError    		Counter32,
        csOc3PosRcvFrameMinPacketError		Counter32,
        csOc3PosRcvFrameMaxPacketError		Counter32,
		csOc3PosSentBytes					Counter32,
		csOc3PosSentFrames					Counter32,
		csOc3PosSentFrameUserAborted		Counter32,
		csOc3PosSentFrameUnderrunAborted	Counter32
    }

	csOc3PosRcvBytes OBJECT-TYPE
    SYNTAX  Counter32
    MAX-ACCESS  read-only
    STATUS  current
    DESCRIPTION
     " The counter associated with the number of bytes written
	 	to receive FIFO."
	::= { csOc3PosStatsEntry 1 }

	csOc3PosRcvFrames OBJECT-TYPE
    SYNTAX  Counter32
    MAX-ACCESS  read-only
    STATUS  current
    DESCRIPTION
     " The counter indicates the number of frames successfully 
		received in a 15 minute interval."
	::= { csOc3PosStatsEntry 2 }

	csOc3PosRcvAbortedFrames OBJECT-TYPE
    SYNTAX  Counter32
    MAX-ACCESS  read-only
    STATUS  current
    DESCRIPTION
     " The counter indicates the number of aborted frames received."
	::= { csOc3PosStatsEntry 3 }

	csOc3PosRcvFrameFCSError OBJECT-TYPE
    SYNTAX  Counter32
    MAX-ACCESS  read-only
    STATUS  current
    DESCRIPTION
     " The counter indicates the number of received frames with
		FCS error."
	::= { csOc3PosStatsEntry 4 }

	csOc3PosRcvFrameMinPacketError OBJECT-TYPE
    SYNTAX  Counter32
    MAX-ACCESS  read-only
    STATUS  current
    DESCRIPTION
     " The counter indicates the number of received frames violating 
		the minimal packet length."
	::= { csOc3PosStatsEntry 5 }

	csOc3PosRcvFrameMaxPacketError OBJECT-TYPE
    SYNTAX  Counter32
    MAX-ACCESS  read-only
    STATUS  current
    DESCRIPTION
     " The counter indicates the number of received frames violating 
		the maximum packet length."
	::= { csOc3PosStatsEntry 6 }

	csOc3PosSentBytes OBJECT-TYPE
    SYNTAX  Counter32
    MAX-ACCESS  read-only
    STATUS  current
    DESCRIPTION
     " The counter indicates the number of bytes trasmitted."
	::= { csOc3PosStatsEntry 7 }

	csOc3PosSentFrames OBJECT-TYPE
    SYNTAX  Counter32
    MAX-ACCESS  read-only
    STATUS  current
    DESCRIPTION
     " The counter indicates the number of frames trasmitted."
	::= { csOc3PosStatsEntry 8 }

	csOc3PosSentFrameUserAborted OBJECT-TYPE
    SYNTAX  Counter32
    MAX-ACCESS  read-only
    STATUS  current
    DESCRIPTION
     " The counter indicates the number of transmit frames aborted 
		by the user."
	::= { csOc3PosStatsEntry 9 }

	csOc3PosSentFrameUnderrunAborted OBJECT-TYPE
    SYNTAX  Counter32
    MAX-ACCESS  read-only
    STATUS  current
    DESCRIPTION
     " The counter indicates the number of transmit frames aborted 
		due to FIFO underrun."
	::= { csOc3PosStatsEntry 10 }


--
--      the range of a Data Link Connection Identifier
--

     DLCI ::= TEXTUAL-CONVENTION
         STATUS      current
         DESCRIPTION
            "The range of DLCI values.  Note that this varies by
            interface configuration; normally, interfaces may use
            0..1023, but may be configured to use ranges as large
            as 0..2^23."
         SYNTAX      Integer32(0..8388607)


     --
     --  Data Link Connection Management Interface
     --      The variables that configure the DLC Management Interface.

     csFrDlcmiTable OBJECT-TYPE
         SYNTAX   SEQUENCE OF CsFrDlcmiEntry
         MAX-ACCESS   not-accessible
         STATUS   current
         DESCRIPTION
            "The Parameters for the Data Link Connection Management
            Interface for the frame relay service on this
            interface."
         REFERENCE
            "American National Standard T1.617-1991, Annex D"
         ::= { csOrionFrInfo 1 }

     csFrDlcmiEntry OBJECT-TYPE
         SYNTAX   CsFrDlcmiEntry
         MAX-ACCESS   not-accessible
         STATUS   current
         DESCRIPTION
            "The Parameters for a particular Data Link Connection
            Management Interface."
         INDEX { csFrDlcmiSlot, csFrDlcmiPort, csFrDlcmiChannel }
         ::= { csFrDlcmiTable 1 }

     CsFrDlcmiEntry ::=
         SEQUENCE {
	csFrDlcmiSlot			  Integer32,
	csFrDlcmiPort			  Integer32,
	csFrDlcmiChannel		  Integer32,
	csFrDlcmiState                    INTEGER,
	csFrDlcmiAddress                  INTEGER,
	csFrDlcmiAddressLen               INTEGER,
	csFrDlcmiPollingInterval          Integer32,
	csFrDlcmiFullEnquiryInterval      Integer32,
	csFrDlcmiErrorThreshold           Integer32,
	csFrDlcmiMonitoredEvents          Integer32,
	csFrDlcmiMaxSupportedVCs          DLCI,
	csFrDlcmiMulticast                INTEGER,
	csFrDlcmiStatus                   INTEGER,
	csFrDlcmiIfType                   INTEGER,
	csFrDlcmiBECNFlowControl          INTEGER,
	csFrDlcmiInjectionManagement      INTEGER,
	csFrDlcmiName				      DisplayString,
	csFrDlcmiLmiDlci				  DLCI,
	csFrDlcmiDceN392			      Integer32,
	csFrDlcmiDceN393				  Integer32,
	csFrDlcmiDceT392				  Integer32,
	csFrDlcmiAsyncEnabled             INTEGER
     }


     csFrDlcmiSlot OBJECT-TYPE
         SYNTAX   Integer32 (1..'7fffffff'h)
         MAX-ACCESS   not-accessible
         STATUS   current
         DESCRIPTION
            "This table entry configures Frame Relay Dlcmi-specific
	    parameters for a single interface.  The interface is
	    identified by the slot its blade resides in, the physical 
	    port on that blade that contains the interface, and (if
	    applicable) the specific DS3 channel on that port.  This
	    object is used to identify the Slot."
         ::= { csFrDlcmiEntry 1 }

     csFrDlcmiPort OBJECT-TYPE
         SYNTAX   Integer32 (1..'7fffffff'h)
         MAX-ACCESS   not-accessible
         STATUS   current
         DESCRIPTION
            "This table entry configures Frame Relay Dlcmi-specific
	    parameters for a single interface.  The interface is
	    identified by the slot its blade resides in, the physical 
	    port on that blade that contains the interface, and (if
	    applicable) the specific DS3 channel on that port.  This
	    object is used to identify the Port."
         ::= { csFrDlcmiEntry 2 }

     csFrDlcmiChannel OBJECT-TYPE
         SYNTAX   Integer32 (0..'7fffffff'h)
         MAX-ACCESS   not-accessible
         STATUS   current
         DESCRIPTION
            "This table entry configures Frame Relay Dlcmi-specific
	    parameters for a single interface.  The interface is
	    identified by the slot its blade resides in, the physical 
	    port on that blade that contains the interface, and (if
	    applicable) the specific DS3 channel on that port.  This
	    object is used to identify the Channel.  If there is no
	    DS3 channel (or unchannelized), this object should have 
		the value 0."
         ::= { csFrDlcmiEntry 3 }

     csFrDlcmiState OBJECT-TYPE
         SYNTAX INTEGER      {
             noLmiConfigured (1),
             lmiRev1         (2),
             ansiT1617D      (3),  -- ANSI T1.617 Annex D
             ansiT1617B      (4),  -- ANSI T1.617 Annex B
             itut933A        (5),  -- CCITT Q933 Annex A
             ansiT1617D1994  (6),  -- ANSI T1.617a-1994 Annex D
			 cisco			 (7)   -- Cisco 
         }
         MAX-ACCESS   read-write
         STATUS   current
         DESCRIPTION
            "This variable states which Data Link Connection
            Management scheme is active (and by implication, what
            DLCI it uses) on the Frame Relay interface."
         REFERENCE
            "American National Standard T1.617-1991, American
            National Standard T1.617a-1994, ITU-T Recommendation
            Q.933 (03/93)."
		 DEFVAL { ansiT1617D }
         ::= { csFrDlcmiEntry 4 }

     csFrDlcmiAddress OBJECT-TYPE
         SYNTAX      INTEGER {
                     q921           (1),  -- 13 bit DLCI
                     q922March90    (2),  -- 11 bit DLCI
                     q922November90 (3),  -- 10 bit DLCI
                     q922           (4)   -- Final Standard
         }
         MAX-ACCESS  read-only
         STATUS  current
         DESCRIPTION
            "This variable states which address format is in use on
            the Frame Relay interface."
         ::= { csFrDlcmiEntry 5 }


     csFrDlcmiAddressLen OBJECT-TYPE
         SYNTAX  INTEGER     {
                 twoOctets (2),
                 threeOctets (3),
                 fourOctets (4)
         }
         MAX-ACCESS  read-only
         STATUS  current
         DESCRIPTION
            "This variable states the address length in octets.  In
            the case of Q922 format, the length indicates the
            entire length of the address including the control
            portion."
         ::= { csFrDlcmiEntry 6 }


     csFrDlcmiPollingInterval OBJECT-TYPE
         SYNTAX   Integer32 (5..30)
         UNITS    "seconds"
         MAX-ACCESS   read-write
         STATUS   current
         DESCRIPTION
            "This is the number of seconds between successive
            status enquiry messages."
         REFERENCE
            "American National Standard T1.617-1991, Section D.7
            Timer T391."
         DEFVAL { 10 }
         ::= { csFrDlcmiEntry 7 }


     csFrDlcmiFullEnquiryInterval OBJECT-TYPE
         SYNTAX   Integer32 (1..255)
         MAX-ACCESS   read-write
         STATUS   current
         DESCRIPTION
            "Number of status enquiry intervals that pass before
            issuance of a full status enquiry message."
         REFERENCE
            "American National Standard T1.617-1991, Section D.7
            Counter N391."
         DEFVAL { 6 }
         ::= { csFrDlcmiEntry 8 }


     csFrDlcmiErrorThreshold OBJECT-TYPE
         SYNTAX   Integer32 (1..10)
         MAX-ACCESS   read-write
         STATUS   current
         DESCRIPTION
            "This is the maximum number of unanswered Status
            Enquiries the equipment shall accept before declaring
            the interface down."
         REFERENCE
            "American National Standard T1.617-1991, Section D.5.1
            Counter N392."
         DEFVAL { 3 }
         ::= { csFrDlcmiEntry 9 }


     csFrDlcmiMonitoredEvents OBJECT-TYPE
         SYNTAX   Integer32 (1..10)
         MAX-ACCESS   read-write
         STATUS   current
         DESCRIPTION
            "This is the number of status polling intervals over
            which the error threshold is counted.  For example, if
            within 'MonitoredEvents' number of events the station
            receives 'ErrorThreshold' number of errors, the
            interface is marked as down."
         REFERENCE
            "American National Standard T1.617-1991, Section D.5.2
            Counter N393."
         DEFVAL { 4 }
         ::= { csFrDlcmiEntry 10 }


     csFrDlcmiMaxSupportedVCs OBJECT-TYPE
         SYNTAX   DLCI
         MAX-ACCESS   read-only
         STATUS   current
         DESCRIPTION
            "The maximum number of Virtual Circuits allowed for
            this interface.  Usually dictated by the Frame Relay
            network.

            In response to a SET, if a value less than zero or
            higher than the agent's maximal capability is
            configured, the agent should respond badValue"
         ::= { csFrDlcmiEntry 11 }


     csFrDlcmiMulticast OBJECT-TYPE
         SYNTAX   INTEGER    {
                     nonBroadcast (1),
                     broadcast (2)
                     }
         MAX-ACCESS   read-only
         STATUS   obsolete
         DESCRIPTION
            "This indicates whether the Frame Relay interface is
            using a multicast service."
         ::= { csFrDlcmiEntry 12 }


     csFrDlcmiStatus OBJECT-TYPE
         SYNTAX   INTEGER    {
                     running      (1),    -- init complete, system running
                     fault        (2),    -- error threshold exceeded
                     initializing (3)     -- system start up
                     }
         MAX-ACCESS   read-only
         STATUS   current
         DESCRIPTION
            "This indicates the status of the Frame Relay interface
            as determined by the performance of the dlcmi.  If no
            dlcmi is running, the Frame Relay interface will stay
            in the running state indefinitely."
         ::= { csFrDlcmiEntry 13 }

	csFrDlcmiIfType OBJECT-TYPE
        SYNTAX   INTEGER    {
                     dce      (1),
                     dte      (2)
                     }
        MAX-ACCESS   read-write
        STATUS   current
        DESCRIPTION
            "This indicates the type of interface."
		DEFVAL { dte }
        ::= { csFrDlcmiEntry 14 }
		
	csFrDlcmiBECNFlowControl OBJECT-TYPE
        SYNTAX   INTEGER    {
                     enable      (1),
                     disable     (2)
                     }
        MAX-ACCESS   read-write
        STATUS   current
        DESCRIPTION
            "This object enables or disables the BECN flow control."
		DEFVAL { disable }
        ::= { csFrDlcmiEntry 15 }

	csFrDlcmiInjectionManagement OBJECT-TYPE
        SYNTAX   INTEGER    {
                     forced      (1),
                     buffered    (2),
					 standard    (3)
                     }
        MAX-ACCESS   read-write
        STATUS   current
        DESCRIPTION
            "."
		DEFVAL { forced }
        ::= { csFrDlcmiEntry 16 }

	csFrDlcmiName OBJECT-TYPE
        SYNTAX   DisplayString (SIZE(0..80))
        MAX-ACCESS   read-write
        STATUS   current
        DESCRIPTION
            "."
		DEFVAL { "" }
        ::= { csFrDlcmiEntry 17 }

	csFrDlcmiLmiDlci OBJECT-TYPE
        SYNTAX   DLCI
         MAX-ACCESS   read-write
         STATUS   current
         DESCRIPTION
            "The DLCI of the LMI for this interface."
		 DEFVAL { 0 }
         ::= { csFrDlcmiEntry 18 }

	csFrDlcmiDceN392 OBJECT-TYPE
        SYNTAX   Integer32 (1..10)
         MAX-ACCESS   read-write
         STATUS   current
         DESCRIPTION
            "LMI error threshold. For DCE IF Type.
			 This is the maximum number of unanswered
			 unreceived Status Enquiries the equipment shall
			 accept before declaring the interface down."
	    DEFVAL { 3 }
        ::= { csFrDlcmiEntry 19 }

	csFrDlcmiDceN393 OBJECT-TYPE
        SYNTAX   Integer32 (1..10)
         MAX-ACCESS   read-write
         STATUS   current
         DESCRIPTION
            "LMI monitored event count. For DCE IF Type.
			 This is the number of status polling intervals
			 over which the error threshold is counted."
	    DEFVAL { 4 }
        ::= { csFrDlcmiEntry 20 }
	
	csFrDlcmiDceT392 OBJECT-TYPE
        SYNTAX   Integer32 (5..30)
         MAX-ACCESS   read-write
         STATUS   current
         DESCRIPTION
            "LMI monitored event count. For DCE IF Type.
			 This indicates the expected number of
			 seconds between heartbeat polls."
	    DEFVAL { 15 }
        ::= { csFrDlcmiEntry 21 }

	csFrDlcmiAsyncEnabled OBJECT-TYPE
        SYNTAX   INTEGER    {
                     enable  (1),
                     disable (2)
                     }
        MAX-ACCESS   read-write
        STATUS   current
        DESCRIPTION
            "."
		DEFVAL { disable }
        ::= { csFrDlcmiEntry 22 }



     --
     -- A Frame Relay service is a multiplexing service.  Data
     -- Link Connection Identifiers enumerate virtual circuits
     -- (permanent or dynamic) which are layered onto the underlying
     -- circuit, represented by ifEntry.  Therefore, each of the entries
     -- in the Standard MIB's Interface Table with an IfType of
     -- Frame Relay represents a Q.922 interface.  Zero or more
     -- virtual circuits are layered onto this interface and provide
     -- interconnection with various remote destinations.
     -- Each such virtual circuit is represented by an entry in the
     -- circuit table.  The management virtual circuit (i.e. DLCI 0)
     -- is a virtual circuit by this definition and will be represented
     -- with an entry in the circuit table.

     --   Circuit Table

     -- The table describing the use of the DLCIs attached to
     -- each Frame Relay Interface.

     csFrCircuitTable OBJECT-TYPE
         SYNTAX   SEQUENCE OF CsFrCircuitEntry
         MAX-ACCESS   not-accessible
         STATUS   current
         DESCRIPTION
            "A table containing information about specific Data
            Link Connections (DLC) or virtual circuits."
         ::= { csOrionFrInfo 2 }


     csFrCircuitEntry OBJECT-TYPE
         SYNTAX   CsFrCircuitEntry
         MAX-ACCESS   not-accessible
         STATUS   current
         DESCRIPTION
            "The information regarding a single Data Link
            Connection.  Discontinuities in the counters contained
            in this table are indicated by the value in
            csFrCircuitCreationTime."
         INDEX { csFrDlcmiSlot, csFrDlcmiPort, csFrDlcmiChannel, 
		csFrCircuitSubIf }
         ::= { csFrCircuitTable 1 }


     CsFrCircuitEntry ::=
         SEQUENCE {
	     csFrCircuitSubIf		       Integer32,
             csFrCircuitDlci                   DLCI,
             csFrCircuitState                  INTEGER,
             csFrCircuitReceivedFECNs          Counter32,
             csFrCircuitReceivedBECNs          Counter32,
             csFrCircuitSentFrames             Counter32,
             csFrCircuitSentOctets             Counter32,
             csFrCircuitReceivedFrames         Counter32,
             csFrCircuitReceivedOctets         Counter32,
             csFrCircuitCreationTime           TimeStamp,
             csFrCircuitLastTimeChange         TimeStamp,
             csFrCircuitCommittedBurst         Integer32,
             csFrCircuitExcessBurst            Integer32,
             csFrCircuitThroughput             Integer32,
             csFrCircuitMulticast              INTEGER,
             csFrCircuitType                   INTEGER,
             csFrCircuitDiscards               Counter32,
             csFrCircuitReceivedDEs            Counter32,
             csFrCircuitSentDEs                Counter32,
             csFrCircuitRemoteIpAddress        IpAddress,
             csFrCircuitRowStatus              RowStatus,
			 csFrCircuitOperStatus             OperStatus,
			 csFrCircitFwdDlciType             INTEGER,
			 csFrCircuitFwdLink				   OCTET STRING,
			csFrCircuitRatePolice		INTEGER,
			csFrCircuitUpperProtocol	INTEGER

     }

     csFrCircuitSubIf OBJECT-TYPE
         SYNTAX   Integer32(2..65535)
         MAX-ACCESS   not-accessible
         STATUS   current
         DESCRIPTION
            "The identifier for this Frame Relay Circuit.  This
	    corresponds to the 'subinterface' entered via the CLI."
         ::= { csFrCircuitEntry 1 }


     csFrCircuitDlci OBJECT-TYPE
         SYNTAX   DLCI
         MAX-ACCESS   read-create
         STATUS   current
         DESCRIPTION
            "The Data Link Connection Identifier for this virtual
            circuit.  Note, this impelemtation supports only values between 
	    16 and 1023 (inclusive)."
         REFERENCE
            "American National Standard T1.618-1991, Section 3.3.6"
         ::= { csFrCircuitEntry 2 }


     csFrCircuitState OBJECT-TYPE
         SYNTAX   INTEGER    {

                     invalid (1),
                     active (2),
                     inactive (3)
                  }
         MAX-ACCESS   read-create
         STATUS   obsolete
         DESCRIPTION
            "Indicates whether the particular virtual circuit is
            operational.  In the absence of a Data Link Connection
            Management Interface, virtual circuit entries (rows)
            may be created by setting virtual circuit state to
            'active', or deleted by changing Circuit state to
            'invalid'.

            Whether or not the row actually disappears is left to
            the implementation, so this object may actually read as
            'invalid' for some arbitrary length of time.  It is
            also legal to set the state of a virtual circuit to
            'inactive' to temporarily disable a given circuit.

            The use of 'invalid' is deprecated in this SNMP Version
            2 MIB, in favor of csFrCircuitRowStatus."
         DEFVAL { active }
         ::= { csFrCircuitEntry 3 }


     csFrCircuitReceivedFECNs OBJECT-TYPE
         SYNTAX   Counter32
         MAX-ACCESS   read-only
         STATUS   current
         DESCRIPTION
            "Number of frames received from the network indicating
            forward congestion since the virtual circuit was
            created.  This occurs when the remote DTE sets the FECN
            flag, or when a switch in the network enqueues the
            frame to a trunk whose transmission queue is
            congested."
         REFERENCE
            "American National Standard T1.618-1991, Section 3.3.3"
         ::= { csFrCircuitEntry 4 }


     csFrCircuitReceivedBECNs OBJECT-TYPE
         SYNTAX   Counter32
         MAX-ACCESS   read-only


         STATUS   current
         DESCRIPTION
            "Number of frames received from the network indicating
            backward congestion since the virtual circuit was
            created.  This occurs when the remote DTE sets the BECN
            flag, or when a switch in the network receives the
            frame from a trunk whose transmission queue is
            congested."
         REFERENCE
            "American National Standard T1.618-1991, Section 3.3.4"
         ::= { csFrCircuitEntry 5 }


     csFrCircuitSentFrames OBJECT-TYPE
         SYNTAX   Counter32
         MAX-ACCESS   read-only
         STATUS   current
         DESCRIPTION
            "The number of frames sent from this virtual circuit
            since it was created."
         ::= { csFrCircuitEntry 6 }


     csFrCircuitSentOctets OBJECT-TYPE
         SYNTAX   Counter32
         MAX-ACCESS   read-only
         STATUS   current
         DESCRIPTION
            "The number of octets sent from this virtual circuit
            since it was created.  Octets counted are the full
            frame relay header and the payload, but do not include
            the flag characters or CRC."
         ::= { csFrCircuitEntry 7 }


     csFrCircuitReceivedFrames OBJECT-TYPE
         SYNTAX   Counter32
         MAX-ACCESS   read-only
         STATUS   current
         DESCRIPTION
            "Number of frames received over this virtual circuit
            since it was created."
         ::= { csFrCircuitEntry 8 }


     csFrCircuitReceivedOctets OBJECT-TYPE
         SYNTAX   Counter32
         MAX-ACCESS   read-only
         STATUS   current
         DESCRIPTION
            "Number of octets received over this virtual circuit
            since it was created.  Octets counted include the full
            frame relay header, but do not include the flag
            characters or the CRC."
         ::= { csFrCircuitEntry 9 }


     csFrCircuitCreationTime OBJECT-TYPE
         SYNTAX   TimeStamp
         MAX-ACCESS   read-only
         STATUS   current
         DESCRIPTION
            "The value of sysUpTime when the virtual circuit was
            created, whether by the Data Link Connection Management
            Interface or by a SetRequest."
         ::= { csFrCircuitEntry 10 }


     csFrCircuitLastTimeChange OBJECT-TYPE
         SYNTAX   TimeStamp
         MAX-ACCESS   read-only
         STATUS   current
         DESCRIPTION
            "The value of sysUpTime when last there was a change in
            the virtual circuit state"
         ::= { csFrCircuitEntry 11 }


     csFrCircuitCommittedBurst OBJECT-TYPE
         SYNTAX   Integer32(0..2147483647)
         MAX-ACCESS   read-create
         STATUS   current
         DESCRIPTION
            "This variable indicates the maximum amount of data, in
            bits, that the network agrees to transfer under normal
            conditions, during the measurement interval."
         REFERENCE
            "American National Standard T1.617-1991, Section
            6.5.19"
         DEFVAL   { 0 }  -- the default indicates no commitment
         ::= { csFrCircuitEntry 12 }


     csFrCircuitExcessBurst OBJECT-TYPE
         SYNTAX   Integer32(0..2147483647)
         MAX-ACCESS   read-create
         STATUS   current
         DESCRIPTION
            "This variable indicates the maximum amount of
            uncommitted data bits that the network will attempt to
            deliver over the measurement interval."
         REFERENCE
            "American National Standard T1.617-1991, Section
            6.5.19"
         DEFVAL   { 1024 }
         ::= { csFrCircuitEntry 13 }


     csFrCircuitThroughput OBJECT-TYPE
         SYNTAX   Integer32(0..2147483647)
         MAX-ACCESS   read-create
         STATUS   current
         DESCRIPTION
            "Throughput is the average number of 'Frame Relay
            Information Field' bits transferred per second across a
            user network interface in one direction, measured over
            the measurement interval.

            If the configured committed burst size and throughput
            are both non-zero, the measurement interval, T, is
                T=csFrCircuitCommittedBurst/csFrCircuitThroughput.

            If the configured committed burst size and throughput
            are both zero, the measurement interval, T, is
                       T=csFrCircuitExcessBurst/ifSpeed."
         REFERENCE
            "American National Standard T1.617-1991, Section
            6.5.19"
         DEFVAL {0}  -- the default value of Throughput is
                     -- "no commitment".
         ::= { csFrCircuitEntry 14 }


     csFrCircuitMulticast OBJECT-TYPE
         SYNTAX   INTEGER    {
                     unicast   (1),
                     oneWay    (2),
                     twoWay    (3),
                     nWay      (4)
                     }
         MAX-ACCESS   read-only
         STATUS   obsolete
         DESCRIPTION
            "This indicates whether this VC is used as a unicast VC
            (i.e. not multicast) or the type of multicast service
            subscribed to"
         REFERENCE
            "Frame Relay PVC Multicast Service and Protocol
            Description Implementation: FRF.7 Frame Relay Forum
            Technical Committe October 21, 1994"
              ::= { csFrCircuitEntry 15 }


     csFrCircuitType OBJECT-TYPE
         SYNTAX   INTEGER    {
                     static  (1),
                     dynamic (2)
                  }
         MAX-ACCESS   read-only
         STATUS   obsolete
         DESCRIPTION
            "Indication of whether the VC was manually created
            (static), or dynamically created (dynamic) via the data
            link control management interface."
         ::= { csFrCircuitEntry 16 }


     csFrCircuitDiscards OBJECT-TYPE
         SYNTAX   Counter32
         MAX-ACCESS   read-only
         STATUS   current
         DESCRIPTION
            "The number of inbound frames dropped because of format
            errors, or because the VC is inactive."
         ::= { csFrCircuitEntry 17 }


     csFrCircuitReceivedDEs OBJECT-TYPE
         SYNTAX   Counter32
         MAX-ACCESS   read-only
         STATUS   current
         DESCRIPTION
            "Number of frames received from the network indicating
            that they were eligible for discard since the virtual
            circuit was created.  This occurs when the remote DTE
            sets the DE flag, or when in remote DTE's switch
            detects that the frame was received as Excess Burst
            data."
         REFERENCE
            "American National Standard T1.618-1991, Section 3.3.4"
         ::= { csFrCircuitEntry 18 }


     csFrCircuitSentDEs OBJECT-TYPE
         SYNTAX   Counter32
         MAX-ACCESS   read-only
         STATUS   current
         DESCRIPTION
            "Number of frames sent to the network indicating that
            they were eligible for discard since the virtual
            circuit was created.   This occurs when the local DTE
            sets the DE flag, indicating that during Network
            congestion situations those frames should be discarded
            in preference of other frames sent without the DE bit
            set."
         REFERENCE
            "American National  Standard  T1.618-1991, Section
            3.3.4"
        ::= { csFrCircuitEntry 19 }


     csFrCircuitRemoteIpAddress OBJECT-TYPE
         SYNTAX   IpAddress
         MAX-ACCESS   read-create
         STATUS   obsolete
         DESCRIPTION
            "The remote IP address mapped to this VC."
         ::= { csFrCircuitEntry 20 }


     csFrCircuitRowStatus OBJECT-TYPE
         SYNTAX   RowStatus
         MAX-ACCESS   read-create
         STATUS   current
         DESCRIPTION
            "This object is used to create a new row or modify or
            destroy an existing row in the manner described in the
            definition of the RowStatus textual convention.
            Writable objects in the table may be written in any
            RowStatus state."
         ::= { csFrCircuitEntry 21 }


     csFrCircuitOperStatus OBJECT-TYPE
         SYNTAX   OperStatus
         MAX-ACCESS   read-only
         STATUS   current
         DESCRIPTION
            "The operational status of this circuit."
         ::= { csFrCircuitEntry 22 }

	csFrCircitFwdDlciType OBJECT-TYPE
         SYNTAX   INTEGER    {
                     frDlci  (1),
                     froipDlci (2)
                  }
         MAX-ACCESS   read-create
         STATUS   current
         DESCRIPTION
            "Indication of whether the DLCI corresponding to the forward link of this
			DLCI, is a Frame Relay DLCI or Frame over IP DLCI. Depending on this the
			csFrCircuitFwdLink object is interpreted differently. When setting a
			csFrCircuitFwdLink object, this object also must be set."
		 DEFVAL {frDlci}
         ::= { csFrCircuitEntry 23 }
	csFrCircuitFwdLink OBJECT-TYPE
         SYNTAX   OCTET STRING (SIZE(16))
         MAX-ACCESS   read-create
         STATUS   current
         DESCRIPTION
            "The forwarding link of this DLCI. This is a switching 
			 parameters for intra blade and inter-blade switching.
			 It takes the following format: 
			 If csFrCircitFwdDlciType is  frDlci
			   byte #0 to #3  : Slot number (csFrDlcmiSlot)
			   byte #4 to #7  : Port number (csFrDlcmiPort)
			   byte #8 to #11 : Channel number (csFrDlcmiChannel, 
										zero for unchannelized blade)
			   byte #12 to #15: DLCI number (csFrCircuitDlci)
					 
			 If csFrCircitFwdDlciType is  froipDlci
			   byte #0 to #3  : VPN Id (csOrionGlobalVPNIndex)
			   byte #4 to #7  : VR Id (csOrionVPNVRouterIndex)
			   byte #8 to #11 : Transport Id (csOrionFRoIPTransportPeer)
			   byte #12 to #15: DLCI number (csFroIPCircuitDlci)

			   NOTE: all zero indicates that this DLCI is not connected
			         to any link."
		 DEFVAL { '00000000000000000000000000000000'H }
         ::= { csFrCircuitEntry 24 }
		 
     csFrCircuitRatePolice OBJECT-TYPE
         SYNTAX   INTEGER    {
                     enable  (1),
                     disable (2)
                  }
         MAX-ACCESS   read-create
         STATUS   current
         DESCRIPTION
            "This object enables or disables ingress traffic 
            rate-policing.

            Ingress rate-policing is controlled by the values
            configured for csFrCircuitThroughput,
            csFrCircuitCommitedBurst and CsFrCircuitExcessBurst.

            If the number of bits received in the measurement
            interval is less than or equal to the committed burst
            size, the frame is forwared for further processing.

            If the number of bits received in the measurement
            interval is greater than the commited burst size but
            less than the sum of commited burst size and excess
            burst size, the DE bit is set in the frame and then
            forwared for further processing.

            If the number of bits received in the measurement
            interval is greater than the sum of commited burst
            size and excess burst size, the frame is dropped."

		 DEFVAL { disable }
         ::= { csFrCircuitEntry 25 }

     csFrCircuitUpperProtocol OBJECT-TYPE
         SYNTAX   INTEGER    {
                     none (1),
                     ip (2),
		     ppp (3)
                  }
         MAX-ACCESS   read-create
         STATUS   current
         DESCRIPTION
	       "This object is used to set the upper protocol.
		    For PPP over FR this is set to 'ppp'. 
			NOTE: This object cannot be set to 'ip'. Only when
			      a VI is connected to this interface that it
				  becomes 'ip'."
		 DEFVAL { none }
         ::= { csFrCircuitEntry 26 }

     --
     --  Error Table

     -- The table describing errors encountered on each Frame
     -- Relay Interface.

     csFrErrTable OBJECT-TYPE
         SYNTAX   SEQUENCE OF CsFrErrEntry
         MAX-ACCESS   not-accessible
         STATUS   current
         DESCRIPTION
            "A table containing information about Errors on the
            Frame Relay interface.  Discontinuities in the counters
            contained in this table are the same as apply to the
            ifEntry associated with the Interface."
         ::= { csOrionFrInfo 3 }

     csFrErrEntry OBJECT-TYPE
         SYNTAX   CsFrErrEntry
         MAX-ACCESS   not-accessible
         STATUS   current
         DESCRIPTION
            "The error information for a single frame relay
            interface."
         INDEX { csFrDlcmiSlot, csFrDlcmiPort, csFrDlcmiChannel }
         ::= { csFrErrTable 1 }


     CsFrErrEntry ::=
         SEQUENCE {
             csFrErrType               INTEGER,
             csFrErrData               OCTET STRING,
             csFrErrTime               TimeStamp,
             csFrErrFaults             Counter32,
             csFrErrFaultTime          TimeStamp
     }


         csFrErrType OBJECT-TYPE
             SYNTAX   INTEGER    {
                         unknownError(1),
                         receiveShort(2),
                         receiveLong(3),
                         illegalAddress(4),
                         unknownAddress(5),
                         dlcmiProtoErr(6),
                         dlcmiUnknownIE(7),
                         dlcmiSequenceErr(8),
                         dlcmiUnknownRpt(9),
                         noErrorSinceReset(10)
                      }
         MAX-ACCESS   read-only
         STATUS   current
         DESCRIPTION
     "The type of error that was last seen  on  this interface:

     receiveShort: frame was not long enough to allow
             demultiplexing - the address field was incomplete,
             or for virtual circuits using Multiprotocol over
             Frame Relay, the protocol identifier was missing
             or incomplete.

     receiveLong: frame exceeded maximum length configured for this
                  interface.

     illegalAddress: address field did not match configured format.

     unknownAddress: frame received on a virtual circuit which was not
                     active or administratively disabled.

     dlcmiProtoErr: unspecified error occurred when attempting to
                    interpret link maintenance frame.

     dlcmiUnknownIE: link maintenance frame contained an Information
                     Element type which is not valid for the
                     configured link maintenance protocol.

     dlcmiSequenceErr: link maintenance frame contained a sequence
                       number other than the expected value.

     dlcmiUnknownRpt: link maintenance frame contained a Report Type
                      Information Element whose value was not valid
                      for the configured link maintenance protocol.

     noErrorSinceReset: no errors have been detected since the last
                        cold start or warm start."
         ::= { csFrErrEntry 1 }


     csFrErrData OBJECT-TYPE
         SYNTAX   OCTET STRING (SIZE(1..1600))
         MAX-ACCESS   read-only
         STATUS   current
         DESCRIPTION
            "An octet string containing as much of the error packet
            as possible.  As a minimum, it must contain the Q.922
            Address or as much as was delivered.  It is desirable
            to include all header and demultiplexing information."
         ::= { csFrErrEntry 2 }


     csFrErrTime OBJECT-TYPE
         SYNTAX   TimeStamp
         MAX-ACCESS   read-only
         STATUS   current
         DESCRIPTION
            "The value of sysUpTime at which the error was
            detected."
         ::= { csFrErrEntry 3 }


     csFrErrFaults OBJECT-TYPE
         SYNTAX   Counter32
         MAX-ACCESS   read-only
         STATUS   current
         DESCRIPTION
            "The number of times the interface has gone down since
            it was initialized."
         ::= { csFrErrEntry 4 }


     csFrErrFaultTime OBJECT-TYPE
         SYNTAX   TimeStamp
         MAX-ACCESS   read-only
         STATUS   current
         DESCRIPTION
            "The value of sysUpTime at the time when the interface
            was taken down due to excessive errors.  Excessive
            errors is defined as the time when a DLCMI exceeds the
            frDlcmiErrorThreshold number of errors within
            frDlcmiMonitoredEvents. See FrDlcmiEntry for further
            details."
         ::= { csFrErrEntry 5 }


     --
     --  Frame Relay Statistics Table

     -- The table describing the statistics on every DLCMI.
	 -- 
	
     csFrDlcmiStatTable OBJECT-TYPE
         SYNTAX   SEQUENCE OF CsFrDlcmiStatEntry
         MAX-ACCESS   not-accessible
         STATUS   current
         DESCRIPTION
            "A table containing information about the statistics
			on every DLCMI."
         ::= { csOrionFrInfo 4 }

     csFrDlcmiStatEntry OBJECT-TYPE
         SYNTAX   CsFrDlcmiStatEntry
         MAX-ACCESS   not-accessible
         STATUS   current
         DESCRIPTION
            "The statistics information for a single frame relay
            interface."
         INDEX { csFrDlcmiSlot, csFrDlcmiPort, csFrDlcmiChannel }
         ::= { csFrDlcmiStatTable 1 }

	
     CsFrDlcmiStatEntry ::=
         SEQUENCE {
             csFrDlcmiStatStatusEnquiries		Counter32,
             csFrDlcmiStatFullStatusEnquiries   Counter32,
             csFrDlcmiStatStatusResponses		Counter32,
             csFrDlcmiStatFullStatusResponses   Counter32,
			 csFrDlcmiStatAsyncUpdates			Counter32,
			 csFrDlcmiStatUnknownMessages		Counter32,
			 csFrDlcmiStatLostSequences			Counter32,
			 csFrDlcmiStatMissingResponses		Counter32,
			 csFrDlcmiStatLocalSequenceNumber	Counter32,
             csFrDlcmiStatNetSequenceNumber		Counter32
     }
	

     csFrDlcmiStatStatusEnquiries OBJECT-TYPE
         SYNTAX			Counter32
         MAX-ACCESS		read-only
         STATUS			current
         DESCRIPTION
			"Number of times the Status Equiry is sent."
         ::= { csFrDlcmiStatEntry 1 }


     csFrDlcmiStatFullStatusEnquiries OBJECT-TYPE
         SYNTAX			Counter32
         MAX-ACCESS		read-only
         STATUS			current
         DESCRIPTION
			"Number of times the Full Status Equiry is sent."
         ::= { csFrDlcmiStatEntry 2 }


     csFrDlcmiStatStatusResponses OBJECT-TYPE
         SYNTAX			Counter32
         MAX-ACCESS		read-only
         STATUS			current
         DESCRIPTION
			"Number of times the Status Response is received."
         ::= { csFrDlcmiStatEntry 3 }


     csFrDlcmiStatFullStatusResponses OBJECT-TYPE
         SYNTAX			Counter32
         MAX-ACCESS		read-only
         STATUS			current
         DESCRIPTION
			"Number of times the Full Status Response is received."
         ::= { csFrDlcmiStatEntry 4 }


     csFrDlcmiStatAsyncUpdates OBJECT-TYPE
         SYNTAX			Counter32
         MAX-ACCESS		read-only
         STATUS			current
         DESCRIPTION
			"Number of times the Asyn Update is made."
         ::= { csFrDlcmiStatEntry 5 }


     csFrDlcmiStatUnknownMessages OBJECT-TYPE
         SYNTAX			Counter32
         MAX-ACCESS		read-only
         STATUS			current
         DESCRIPTION
			"Number of times the Unknown Messages is encountered."
         ::= { csFrDlcmiStatEntry 6 }


     csFrDlcmiStatLostSequences OBJECT-TYPE
         SYNTAX			Counter32
         MAX-ACCESS		read-only
         STATUS			current
         DESCRIPTION
			"Number of times the Lost Sequence is encountered."
         ::= { csFrDlcmiStatEntry 7 }


     csFrDlcmiStatMissingResponses OBJECT-TYPE
         SYNTAX			Counter32
         MAX-ACCESS		read-only
         STATUS			current
         DESCRIPTION
			"Number of times the Missing Response is encountered."
         ::= { csFrDlcmiStatEntry 8 }


     csFrDlcmiStatLocalSequenceNumber OBJECT-TYPE
         SYNTAX			Counter32
         MAX-ACCESS		read-only
         STATUS			current
         DESCRIPTION
			"The local sequence number."
         ::= { csFrDlcmiStatEntry 9 }


     csFrDlcmiStatNetSequenceNumber OBJECT-TYPE
         SYNTAX			Counter32
         MAX-ACCESS		read-only
         STATUS			current
         DESCRIPTION
			"The network sequence number."
         ::= { csFrDlcmiStatEntry 10 }



	--
	--
    --    ATM Interface Configuration Parameters Table
	--

	csAtmInterfaceConfTable OBJECT-TYPE
         SYNTAX   SEQUENCE OF CsAtmInterfaceConfEntry
         MAX-ACCESS   not-accessible
         STATUS   current
         DESCRIPTION
            "This table contains ATM local interface configuration
			 parameters, one entry per ATM interface port."
         ::= { csAtmInfo 1 }

    csAtmInterfaceConfEntry OBJECT-TYPE
         SYNTAX   CsAtmInterfaceConfEntry
         MAX-ACCESS   not-accessible
         STATUS   current
         DESCRIPTION
            "This list contains ATM interface configuration
            parameters and state variables."
         INDEX { csAtmInterfaceConfSlotIndex, csAtmInterfaceConfPortIndex }
	     ::= { csAtmInterfaceConfTable 1 }

    CsAtmInterfaceConfEntry ::=
	SEQUENCE {
	csAtmInterfaceConfSlotIndex
		Integer32,
	csAtmInterfaceConfPortIndex
		Integer32,
	csAtmInterfaceConfMaxVpcs
		Integer32,
	csAtmInterfaceConfMaxVccs
		Integer32,
	csAtmInterfaceConfVpcs
		Integer32,
	csAtmInterfaceConfVccs
		Integer32,
	csAtmInterfaceConfMaxActiveVpiBits
	    Integer32,
	csAtmInterfaceConfCurrentMaxVpiBits
		Integer32,
	csAtmInterfaceConfMaxActiveVciBits
		Integer32,
	csAtmInterfaceConfCurrentMaxVciBits
		Integer32,
	csAtmInterfaceConfIlmiVpi
		AtmVpIdentifier,
	csAtmInterfaceConfIlmiVci
		AtmVcIdentifier,
	csAtmInterfaceConfMyIfName
		DisplayString,
	csAtmInterfaceConfMyNeighbourIpAddress
		IpAddress,
	csAtmInterfaceConfMyNeighbourIfName
		DisplayString,
	csAtmInterfaceConfIlmiVersion
		INTEGER,
	csAtmInterfaceConfUniType
		INTEGER,
	csAtmInterfaceConfUniVersion
		INTEGER,
	csAtmInterfaceConfAdminStatus
		INTEGER,
	csAtmInterfaceConfOperStatus
		OperStatus,
	csAtmInterfaceConfIlmiControl
		INTEGER,
	csAtmInterfaceConfIlmiStatus
		INTEGER
	--csAtmInterfaceConfServedVPN
	--    Integer32, 
	--csAtmInterfaceConfServedVR
	--    IpAddress 
	}
	
	csAtmInterfaceConfSlotIndex OBJECT-TYPE
	SYNTAX	Integer32 (1..64)
	MAX-ACCESS  not-accessible
	STATUS	current
	DESCRIPTION
	       "This object identifies the blade to which this ATM Port
	        is attached.  Together with csAtmInterfaceConfPortIndex, it uniquely 
	        identifies a physical port."
	::= { csAtmInterfaceConfEntry 1 }

	csAtmInterfaceConfPortIndex OBJECT-TYPE
	SYNTAX	Integer32 (1..64)
	MAX-ACCESS  not-accessible
	STATUS	current
	DESCRIPTION
	       "This object identifies the blade to which this ATM Port
	        is attached.  Together with csAtmInterfaceConfSlotIndex, it uniquely 
	        identifies a physical port."
	::= { csAtmInterfaceConfEntry 2 }

	csAtmInterfaceConfMaxVpcs OBJECT-TYPE
	SYNTAX	Integer32 (0..4096)
	MAX-ACCESS  read-write
	STATUS	current
	DESCRIPTION
	       "The maximum number of VPCs (PVPCs and SVPCs)
	        supported at this ATM interface. At the ATM UNI,
			the maximum number of VPCs (PVPCs and SVPCs)
			ranges from 0 to 256 only."
	DEFVAL{ 0 }
	::= { csAtmInterfaceConfEntry 3 }

	csAtmInterfaceConfMaxVccs OBJECT-TYPE
	SYNTAX	Integer32 (0..65536)
	MAX-ACCESS  read-write
	STATUS	current
	DESCRIPTION
	       "The maximum number of VCCs (PVCCs and SVCCs)
			supported at this ATM interface."
	DEFVAL{ 16384 }
	::= { csAtmInterfaceConfEntry 4 }

	csAtmInterfaceConfVpcs OBJECT-TYPE
	SYNTAX	Integer32 (0..4096)
	MAX-ACCESS  read-only
	STATUS	current
	DESCRIPTION
	       "The number of VPCs (PVPC, Soft PVPC and SVPC)
			currently in use at this ATM interface.  It includes
			the number of PVPCs and Soft PVPCs that are configured
			at the interface, plus the number of SVPCs that 
			are currently  established at the interface.

			At the ATM UNI, the configured number of 
			VPCs (PVPCs and SVPCs) can range from 0 to 256 only."
	::= { csAtmInterfaceConfEntry 5 }

	csAtmInterfaceConfVccs OBJECT-TYPE
	SYNTAX	Integer32 (0..65536)
	MAX-ACCESS  read-only
	STATUS	current
	DESCRIPTION
	       "The number of VCCs (PVCC, Soft PVCC and SVCC)
			currently in use at this ATM interface.  It includes
			the number of PVCCs and Soft PVCCs that are configured
			at the interface, plus the number of SVCCs
			that are currently  established at the interface."
	::= { csAtmInterfaceConfEntry 6 }

	csAtmInterfaceConfMaxActiveVpiBits OBJECT-TYPE
	SYNTAX	Integer32 (0..16)
	MAX-ACCESS  read-write
	STATUS	current
	DESCRIPTION
	       "The  maximum number of active VPI bits configured 
		    for use at the ATM interface. At the ATM UNI, 
			the maximum number of active VPI bits configured 
			for use ranges from 0 to 8 only."
	DEFVAL{ 0 }
	::= { csAtmInterfaceConfEntry 7 }

	csAtmInterfaceConfCurrentMaxVpiBits OBJECT-TYPE
	SYNTAX	Integer32 (0..16)
	MAX-ACCESS  read-only
	STATUS	current
	DESCRIPTION
	       "The maximum number of VPI Bits that may currently be used
		    at this ATM interface. The value is the minimum of
			AtmInterfaceMaxActiveVpiBits, and the AtmInterfaceMaxActiveVpiBits 
			of the interface's UNI/NNI peer.
	
			If the interface does not negotiate with its peer to 
			determine the number of VPI Bits that can be used on 
			the interface, then the value of this object must 
			equal AtmInterfaceMaxActiveVpiBits."
	::= { csAtmInterfaceConfEntry 8 }

	csAtmInterfaceConfMaxActiveVciBits OBJECT-TYPE
	SYNTAX	Integer32 (0..16)
	MAX-ACCESS  read-write
	STATUS	current
	DESCRIPTION
	       "The maximum number of active VCI bits
	        configured for use at this ATM interface."
	DEFVAL{ 14 }
	::= { csAtmInterfaceConfEntry 9 }

	csAtmInterfaceConfCurrentMaxVciBits OBJECT-TYPE
	SYNTAX	Integer32 (0..16)
	MAX-ACCESS  read-only
	STATUS	current
	DESCRIPTION
	       "The maximum number of VCI Bits that may currently
		    be used at this ATM interface. The value is the 
			minimum of AtmInterfaceMaxActiveVciBits, and the
			AtmInterfaceMaxActiveVciBits of the interface's
			UNI/NNI peer.
	
			If the interface does not negotiate with its peer 
			to determine the number of VCI Bits that can be 
			used on the interface, then the value of this 
			object must equal AtmInterfaceMaxActiveVciBits."
	::= { csAtmInterfaceConfEntry 10 }

	csAtmInterfaceConfIlmiVpi OBJECT-TYPE
	SYNTAX	AtmVpIdentifier
	MAX-ACCESS  read-write
	STATUS	current
	DESCRIPTION
	       "The VPI value of the VCC supporting the ILMI at this
		    ATM interface.  If the values of AtmInterfaceIlmiVpi 
			and AtmInterfaceIlmiVci are both equal to zero then 
			the ILMI is not supported at this ATM interface."
	DEFVAL{ 0 }
	::= { csAtmInterfaceConfEntry 11 }

	csAtmInterfaceConfIlmiVci OBJECT-TYPE
	SYNTAX	AtmVcIdentifier
	MAX-ACCESS  read-write
	STATUS	current
	DESCRIPTION
	       "The VCI value of the VCC supporting the ILMI at this
		    ATM interface.  If the values of AtmInterfaceIlmiVpi
			and AtmInterfaceIlmiVci are both equal to zero then 
			the ILMI is not supported at this ATM interface."
	DEFVAL{ 16 }
	::= { csAtmInterfaceConfEntry 12 }

	csAtmInterfaceConfMyIfName OBJECT-TYPE
	SYNTAX	DisplayString (SIZE(0..255))
	MAX-ACCESS  read-write
	STATUS	current
	DESCRIPTION
	       "A textual name of this interface. if this system is
			manageable through SNMP, and supports the object
			ifName, the value of this object must be identical
			with that of ifName for the ifEntry of the lowest
			level physical interface for this port. This interface
			must be uniquely named on this system to distinguish
			parallel links with a neighboring system. if this
			interface does not have a textual name, the value of
			this object is a zero length strin."
	DEFVAL{ "" }
	::= { csAtmInterfaceConfEntry 13 }

	csAtmInterfaceConfMyNeighbourIpAddress OBJECT-TYPE
	SYNTAX	IpAddress
	MAX-ACCESS  read-write
	STATUS	current
	DESCRIPTION
	       "The IP address of the neighbor system connected to
	        the  far end of this interface, to which a Network
			Management Station can send SNMP messages, as IP
			datagrams sent to UDP port 161, in order to access
			network management information concerning the
			operation of that system.  Note that the value
			of this object may be obtained in different ways,
			e.g., by manual configuration, or through ILMI
			interaction with the neighbor system."
	DEFVAL{ '00000000'H }  -- 0.0.0.0
	::= { csAtmInterfaceConfEntry 14 }

	csAtmInterfaceConfMyNeighbourIfName OBJECT-TYPE
	SYNTAX	DisplayString (SIZE(0..255))
	MAX-ACCESS  read-write
	STATUS	current
	DESCRIPTION
	       "The textual name of the interface on the neighbor system
	        on the far end of this interface, and to which this 
			interface connects.  If the neighbor system is manageable
			through SNMP and supports the object ifName, the value of 
			this object must be identical with that of ifName for the
			ifEntry of the lowest level physical interface for this 
			port.  If this interface does not have a textual name, 
			the value of this object is a zero length string.  
			Note that the value of this object may be obtained in 
			different ways, e.g., by manual configuration, or through
			ILMI interaction with the neighbor system."
	DEFVAL{ "" }
	::= { csAtmInterfaceConfEntry 15 }

	csAtmInterfaceConfIlmiVersion OBJECT-TYPE
	SYNTAX	INTEGER {
				unsupported(1), 
				version4point0 (2) 
	}
	MAX-ACCESS  read-only
	STATUS	current
	DESCRIPTION
	       "An indication of the latest version of the ATM Forum
			ILMI specification that is supported on this ATM interface.

			If the peer IME's value of this object is the same as,
			or later than the local IME's value, then the version
			corresponding to the local IME's value should be
			attempted. Otherwise, if the peer IME's value of this
			object is earlier, and supported locally, then the
			local IME should attempt the version corresponding to
			the peer IME's value. Otherwise, compatibility of the
			two IMEs cannot be assumed.

			If this object is not present, a version of the ILMI earlier
			than 4.0 is supported."
	::= { csAtmInterfaceConfEntry 16 }

	csAtmInterfaceConfUniType OBJECT-TYPE
	SYNTAX	INTEGER {
				public(1), 
				private(2) 
	}
	MAX-ACCESS  read-only
	STATUS	current
	DESCRIPTION
	       "The type of the ATM device, either public or private."
	::= { csAtmInterfaceConfEntry 17 }

	csAtmInterfaceConfUniVersion OBJECT-TYPE
	SYNTAX	INTEGER {
				version2point0(1),
				version3point0(2),
				version3point1(3), 
				version4point0(4),
				unsupported(5) 
	}
	MAX-ACCESS  read-only
	STATUS	current
	DESCRIPTION
	       "An indication of the latest version of the ATM Forum UNI
			Signalling Specification that is supported on this ATM
			Interface. if this value is not present, a version of the UNI
			earlier than 3.1 is supported.
			
			If the peer IME's value of this object is the same as,
			or earlier than the local IME's value, then the version
			corresponding to the local IME's value should be
			attempted. Otherwise, if the peer IME's value of this
			object is earlier, and supported locally, then the
			local IME should attempt the version corresponding to
			the peer IME's value. Otherwise compatibility of the
			two IMEs cannot be assumed."
	::= { csAtmInterfaceConfEntry 18 }

	csAtmInterfaceConfAdminStatus OBJECT-TYPE
	SYNTAX	INTEGER {
				enable(1), 
				disable(2) 
	}
	MAX-ACCESS  read-write
	STATUS	current
	DESCRIPTION
	       "The object used to enable/disable this ATM interface."
	DEFVAL{ disable }
	::= { csAtmInterfaceConfEntry 19 }

	csAtmInterfaceConfOperStatus OBJECT-TYPE
	SYNTAX	OperStatus
	MAX-ACCESS  read-only
	STATUS	current
	DESCRIPTION
	       "The operational status of this ATM interface."
	::= { csAtmInterfaceConfEntry 20 }

	csAtmInterfaceConfIlmiControl OBJECT-TYPE
	SYNTAX	INTEGER {
				enable(1), 
				disable(2) 
	}
	MAX-ACCESS  read-write
	STATUS	current
	DESCRIPTION
	       "The object is used to enable/disable the ILMI on 
			this ATM interface."
	DEFVAL{ disable }
	::= { csAtmInterfaceConfEntry 21 }

	csAtmInterfaceConfIlmiStatus OBJECT-TYPE
	SYNTAX	INTEGER {
				up(1), 
				down(2) 
	}
	MAX-ACCESS  read-only
	STATUS	current
	DESCRIPTION
	       "The object is used to monitor the status of the ILMI on 
			this ATM interface."
	::= { csAtmInterfaceConfEntry 22 }

	--csAtmInterfaceConfServedVPN OBJECT-TYPE
	--SYNTAX	Integer32 
	--MAX-ACCESS  read-write
	--STATUS	current
	--DESCRIPTION
	--    "This object contains the VPN number in which this ATM interface/port is
    --     managed." 
	--DEFVAL{ 0 }
	--::= { csAtmInterfaceConfEntry 23 }

	--csAtmInterfaceConfServedVR OBJECT-TYPE
	--SYNTAX	    IpAddress 
	--MAX-ACCESS  read-write
	--STATUS	    current
	--DESCRIPTION
	--    "This object contains the VR Identifier in which this ATM
    --    interface/port is
    --     managed." 
    --DEFVAL{ '00000000'H }  
    -- 0.0.0.0
	--::= { csAtmInterfaceConfEntry 24 }


	--
	--
    --    ATM Connection Table
	--

	csAtmConnTable OBJECT-TYPE
         SYNTAX   SEQUENCE OF CsAtmConnEntry
         MAX-ACCESS   not-accessible
         STATUS   current
         DESCRIPTION
            "This table can be used to creata virtual connections
			 in this ATM interface."
         ::= { csAtmInfo 2 }

    csAtmConnEntry OBJECT-TYPE
         SYNTAX   CsAtmConnEntry
         MAX-ACCESS   not-accessible
         STATUS   current
         DESCRIPTION
            "This list contains ATM virtual connections."
         INDEX { csAtmInterfaceConfSlotIndex, csAtmInterfaceConfPortIndex,
				 csAtmConnChannelIndex, csAtmConnSubIfIndex }
	     ::= { csAtmConnTable 1 }

    CsAtmConnEntry ::=
	SEQUENCE {
	csAtmConnChannelIndex
		Integer32,
	csAtmConnSubIfIndex
		Integer32,
	csAtmConnVpi
		AtmVpIdentifier,
	csAtmConnVci
		AtmVcIdentifier,
	csAtmConnType
		AtmServiceCategory,
	csAtmConnPvcType
	    INTEGER,		
	csAtmConnPCR
		Integer32,
	csAtmConnSCR
		Integer32,
	csAtmConnMBS
		Integer32,
	csAtmConnICR
		Integer32,
	csAtmConnMCR
		Integer32,
	csAtmConnOamLoopback
		INTEGER,
	csAtmConnOamContinuity
		INTEGER,
	csAtmConnAal5CpcsTransmitSduSize
		Integer32,
	csAtmConnAal5CpcsReceiveSduSize
		Integer32,
	csAtmConnEncapType
		INTEGER,
	csAtmConnKind
		INTEGER,
	csAtmConnAdminStatus
		INTEGER,
	csAtmConnOperStatus
		OperStatus,
	csAtmConnRowStatus
		RowStatus,
	csAtmConnUpperProtocol
	    INTEGER,
    csAtmConnArpAgingTime
        Integer32,
    csAtmConnArpCacheSize
        Integer32,
    csAtmConnEthernetMacAddress
        MacAddress
	--csAtmConnServedVPN
    --    Integer32,
    --csAtmConnServedVR
    --    IpAddress
	}

	csAtmConnChannelIndex OBJECT-TYPE
	SYNTAX	Integer32 (0..64)
	MAX-ACCESS  not-accessible
	STATUS	current
	DESCRIPTION
	       "Channel ID of this ATM connection. Currently, it
		    will always be 0."
	::= { csAtmConnEntry 1 }

	csAtmConnSubIfIndex OBJECT-TYPE
	SYNTAX	Integer32 (1..2147483647)
	MAX-ACCESS  not-accessible
	STATUS	current
	DESCRIPTION
	       "The identifier for this ATM connection.  This
			corresponds to the 'subinterface' entered via the CLI."
	::= { csAtmConnEntry 2 }

	csAtmConnVpi OBJECT-TYPE
	SYNTAX	AtmVpIdentifier
	MAX-ACCESS  read-create
	STATUS	current
	DESCRIPTION
	       "Virtual Path ID of this connection. This is mandatory in
		    creating a connection."
	::= { csAtmConnEntry 3 }

	csAtmConnVci OBJECT-TYPE
	SYNTAX	AtmVcIdentifier
	MAX-ACCESS  read-create
	STATUS	current
	DESCRIPTION
	       "Virtual Channel ID of this connection. This is mandatory in
		    creating a connection."
	::= { csAtmConnEntry 4 }

	csAtmConnType OBJECT-TYPE
	SYNTAX	AtmServiceCategory
	MAX-ACCESS  read-create
	STATUS	current
	DESCRIPTION
	       "The ATM service category. 
		    NOTE : The type other(1) is not implemented for write operation. 
			       Setting to this type will default to ubr(6)."
	DEFVAL{ ubr }
	::= { csAtmConnEntry 5 }

	csAtmConnPvcType OBJECT-TYPE
	SYNTAX	INTEGER {
			pvpc (1),
			pvcc (2)
	}
	MAX-ACCESS  read-create
	STATUS	current
	DESCRIPTION
	       ""
	DEFVAL{ pvcc }
	::= { csAtmConnEntry 6 }

	csAtmConnPCR OBJECT-TYPE
	SYNTAX	Integer32 (0..'7fffffff'h)
	MAX-ACCESS  read-create
	STATUS	current
	DESCRIPTION
	       "Peak Cell rate for the connection."
	DEFVAL{ 175 }
	::= { csAtmConnEntry 7 }

	csAtmConnSCR OBJECT-TYPE
	SYNTAX	Integer32 (0..'7fffffff'h)
	MAX-ACCESS  read-create
	STATUS	current
	DESCRIPTION
	       "Sustain Cell rate for the connection.
		    NOTE: This value is applicable for VBR service categories."
	DEFVAL{ 175 }
	::= { csAtmConnEntry 8 }

	csAtmConnMBS OBJECT-TYPE
	SYNTAX	Integer32 (0..'7fffffff'h)
	MAX-ACCESS  read-create
	STATUS	current
	DESCRIPTION
	       "Maximum Burst Size for the connection.
		    NOTE: This value is applicable for VBR service categories."
	DEFVAL{ 175 }
	::= { csAtmConnEntry 9 }

	csAtmConnICR OBJECT-TYPE
	SYNTAX	Integer32 (0..'7fffffff'h)
	MAX-ACCESS  read-create
	STATUS	current
	DESCRIPTION
	       "Inital Cell rate for the connection.
		    NOTE: This value is applicable for ABR service category."
	DEFVAL{ 175 }
	::= { csAtmConnEntry 10 }

	csAtmConnMCR OBJECT-TYPE
	SYNTAX	Integer32 (0..'7fffffff'h)
	MAX-ACCESS  read-create
	STATUS	current
	DESCRIPTION
	       "Minimum Cell rate for the connection.
		   NOTE: This value is applicable for ABR service category."
	DEFVAL{ 175 }
	::= { csAtmConnEntry 11 }

    csAtmConnOamLoopback OBJECT-TYPE
	SYNTAX	INTEGER {
			enable (1),
			disable (2)
	}
	MAX-ACCESS  read-create
	STATUS	current
	DESCRIPTION
	       "This object is used to enable/disable the loopback."
	DEFVAL{ disable }
	::= { csAtmConnEntry 12 }

	csAtmConnOamContinuity OBJECT-TYPE
	SYNTAX	INTEGER {
			enable (1),
			disable (2)
	}
	MAX-ACCESS  read-create
	STATUS	current
	DESCRIPTION
	       "This object is used to enable/disable the continuity."
	DEFVAL{ disable }
	::= { csAtmConnEntry 13 }

	csAtmConnAal5CpcsTransmitSduSize OBJECT-TYPE
    SYNTAX         Integer32 (1..65535)
    MAX-ACCESS     read-create
    STATUS         current
    DESCRIPTION
           "An instance of this object only exists when the
            local VCL end-point is also the VCC end-point,
            and AAL5 is in use.
            The maximum AAL5 CPCS SDU size in octets that is
            supported on the transmit direction of this VCC.
			NOTE : For now, a maximum of 1792 is supported. "
	DEFVAL{ 1792 }
    ::= { csAtmConnEntry 14 }

	csAtmConnAal5CpcsReceiveSduSize OBJECT-TYPE
    SYNTAX         Integer32 (1..65535)
    MAX-ACCESS     read-create
    STATUS         current
    DESCRIPTION
           "An instance of this object only exists when the
            local VCL end-point is also the VCC end-point,
            and AAL5 is in use.
            The maximum AAL5 CPCS SDU size in octets that is
            supported on the receive direction of this VCC."
    DEFVAL { 1792 }
    ::= { csAtmConnEntry 15 }

	csAtmConnEncapType OBJECT-TYPE
    SYNTAX		   INTEGER {
					unknown (1),
					llcRoutedEncapsulation (2),
					vcMultiplexRoutedProtocol (3),
                    llcBridgedEncapsulation (4),
                    vcMultiplexedBridged802dot3 (5)
	}
    MAX-ACCESS     read-create
    STATUS         current
    DESCRIPTION
		   "The use of call control."
    DEFVAL { llcRoutedEncapsulation }
    ::= {csAtmConnEntry 16}

	csAtmConnKind OBJECT-TYPE
    SYNTAX		   INTEGER {
					pvc  (1),
					svc  (2),
					spvc (3)
	}
    MAX-ACCESS     read-create
    STATUS         current
    DESCRIPTION
		   "The use of call control."
    DEFVAL { pvc }
    ::= {csAtmConnEntry 17}


	csAtmConnAdminStatus OBJECT-TYPE
	SYNTAX	INTEGER {
			enable (1),
			disable (2)
	}
	MAX-ACCESS  read-create
	STATUS	current
	DESCRIPTION
	       "This object is instanciated only for a connection 
	        which terminates a VCC (i.e., one which is NOT
			cross-connected to other connections). Its value
			specifies the desired administrative state of
			the connection."
	DEFVAL{ disable }
	::= { csAtmConnEntry 18 }

	csAtmConnOperStatus OBJECT-TYPE
	SYNTAX	OperStatus
	MAX-ACCESS  read-only
	STATUS	current
	DESCRIPTION
	       "The current operational status of the connection."
	::= { csAtmConnEntry 19 }

	csAtmConnRowStatus OBJECT-TYPE
	SYNTAX	RowStatus
	MAX-ACCESS  read-create
	STATUS	current
	DESCRIPTION
	       "This object is used to create, delete or modify
	        a row in this table."
	::= { csAtmConnEntry 20 }

	csAtmConnUpperProtocol OBJECT-TYPE
	SYNTAX	INTEGER {
			none  (1),
			ip	  (2),
			ppp   (3),
			pppoe (4)
	}
	MAX-ACCESS  read-create
	STATUS	current
	DESCRIPTION
	       "This object is used to set the upper protocol.
		    For PPP over ATM this is set to 'ppp'.
			For PPP over Ethernet this is set to 'pppoe'.
			NOTE: This object cannot be set to 'ip'. Only when
			      a VI is connected to this interface that it
				  becomes 'ip'."
	DEFVAL { none }
	::= { csAtmConnEntry 21 }
    csAtmConnArpAgingTime OBJECT-TYPE
    SYNTAX         Integer32 (6..60)
    MAX-ACCESS     read-create
    STATUS         current
    DESCRIPTION
           "An instance of this object only exists when the
            local VCL end-point is also the VCC end-point,
            and AAL5 Encapsulation type supports Bridging format.
            This objects specifies aging time for ARP Cache entries 
            and it takes effect when ATM ARP module restarts."

	DEFVAL{ 15 }    
	::= { csAtmConnEntry 22 }

    csAtmConnArpCacheSize OBJECT-TYPE
    SYNTAX         Integer32 (8..64)
    MAX-ACCESS     read-create
    STATUS         current
    DESCRIPTION
           "An instance of this object only exists when the
            local VCL end-point is also the VCC end-point,
            and AAL5 Encapsulation type supports Bridging format.
            This objects specifies the size of ARP Cache and it takes 
            effect when ATM ARP module restarts."
	DEFVAL{ 8 }
	::= { csAtmConnEntry 23 }

    csAtmConnEthernetMacAddress OBJECT-TYPE 
    SYNTAX         MacAddress
    MAX-ACCESS     read-only
    STATUS         current
    DESCRIPTION
           "An instance of this object only exists when the
            local VCL end-point is also the VCC end-point,
            and AAL5 Encapsulation type supports Bridging format.
            This objects specifies the active MAC Address on  
            the VCC end-point."
	::= { csAtmConnEntry 24 }

	--csAtmConnServedVPN OBJECT-TYPE
	--SYNTAX	Integer32 
	--MAX-ACCESS  read-write
	--STATUS	current
	--DESCRIPTION
	--    "This object contains the VPN number in which this ATM connection is
    --     managed." 
    --DEFVAL{ 0 }
	--::= { csAtmConnEntry 25 }

	--csAtmConnServedVR OBJECT-TYPE
	--SYNTAX	    IpAddress 
	--MAX-ACCESS  read-write
	--STATUS	    current
	--DESCRIPTION
	--    "This object contains the VR Identifier in which this ATM connection is
    --     managed." 
    --DEFVAL{ '00000000'H } 
    -- 0.0.0.0
	--::= { csAtmConnEntry 26 }


	--
   	--    ATM Connection Dynamic ARP Table
	--

	csAtmConnDynamicArpCacheTable OBJECT-TYPE
         SYNTAX   SEQUENCE OF CsAtmConnDynamicArpCacheEntry
         MAX-ACCESS   not-accessible
         STATUS   current
         DESCRIPTION
            ""
         ::= { csAtmInfo 3 }

    csAtmConnDynamicArpCacheEntry OBJECT-TYPE
         SYNTAX   CsAtmConnDynamicArpCacheEntry
         MAX-ACCESS   not-accessible
         STATUS   current
         DESCRIPTION
            "This list contains Dynamic ARP Entries for ATM virtual connections."
         INDEX { csAtmInterfaceConfSlotIndex, csAtmInterfaceConfPortIndex,
				 csAtmConnChannelIndex, csAtmConnSubIfIndex,csAtmConnDynamicArpCacheIpAddress}
	     ::= { csAtmConnDynamicArpCacheTable 1 }

    CsAtmConnDynamicArpCacheEntry ::=
	SEQUENCE {
	csAtmConnDynamicArpCacheIpAddress
		IpAddress,
	csAtmConnDynamicArpCacheMacAddress
		MacAddress,
	--csAtmConnDynamicArpCacheType
    --    INTEGER,
	csAtmConnDynamicArpCacheRowStatus
		RowStatus
    }

	csAtmConnDynamicArpCacheIpAddress OBJECT-TYPE
        SYNTAX	IpAddress
        MAX-ACCESS  not-accessible
        STATUS	current
        DESCRIPTION
            "This object holds IP address associated with MAC Address."
        ::= { csAtmConnDynamicArpCacheEntry 1 }

	csAtmConnDynamicArpCacheMacAddress OBJECT-TYPE
        SYNTAX	MacAddress
        MAX-ACCESS  read-only
        STATUS	current
        DESCRIPTION
            "This object holds MAC address associated with IP Address."
        ::= { csAtmConnDynamicArpCacheEntry 2 }

	--csAtmConnDynamicArpCacheType OBJECT-TYPE
    --   SYNTAX	INTEGER {
    --		static (1),
	--		dynamic (2)
    --    }
    --    MAX-ACCESS  read-only
    --    STATUS	current
    --    DESCRIPTION
    --        "This object holds type of ARP cache entry."
    --    ::= { csAtmConnDynamicArpCacheEntry 3 }

	csAtmConnDynamicArpCacheRowStatus OBJECT-TYPE
        SYNTAX	RowStatus
        MAX-ACCESS  read-write
        STATUS	current
        DESCRIPTION
               "This object is used to delete 
                a row in this table."
        ::= { csAtmConnDynamicArpCacheEntry 4 }

	--
   	--    ATM Connection Static ARP Table
	--

	csAtmConnStaticArpCacheTable OBJECT-TYPE
         SYNTAX   SEQUENCE OF CsAtmConnStaticArpCacheEntry
         MAX-ACCESS   not-accessible
         STATUS   current
         DESCRIPTION
            ""
         ::= { csAtmInfo 4}

    csAtmConnStaticArpCacheEntry OBJECT-TYPE
         SYNTAX   CsAtmConnStaticArpCacheEntry
         MAX-ACCESS   not-accessible
         STATUS   current
         DESCRIPTION
            "This list contains Static (configured) ARP Entries for ATM virtual connections. "
         INDEX { csAtmInterfaceConfSlotIndex, csAtmInterfaceConfPortIndex,
				 csAtmConnChannelIndex, csAtmConnSubIfIndex,csAtmConnStaticArpCacheIpAddress}
	     ::= { csAtmConnStaticArpCacheTable 1 }

    CsAtmConnStaticArpCacheEntry ::=
	SEQUENCE {
	csAtmConnStaticArpCacheIpAddress
		IpAddress,
	csAtmConnStaticArpCacheMacAddress
		MacAddress,
	--csAtmConnStaticArpCacheType
     --   INTEGER,
	csAtmConnStaticArpCacheRowStatus
		RowStatus
    }

	csAtmConnStaticArpCacheIpAddress OBJECT-TYPE
        SYNTAX	IpAddress
        MAX-ACCESS  not-accessible
        STATUS	current
        DESCRIPTION
            "This object holds IP address associated with MAC Address."
        ::= { csAtmConnStaticArpCacheEntry 1 }

	csAtmConnStaticArpCacheMacAddress OBJECT-TYPE
        SYNTAX	MacAddress
        MAX-ACCESS  read-create
        STATUS	current
        DESCRIPTION
            "This object holds MAC address associated with IP Address."
        ::= { csAtmConnStaticArpCacheEntry 2 }

	--csAtmConnStaticArpCacheType OBJECT-TYPE
    --   SYNTAX	INTEGER {
	--		static (1),
	--		dynamic (2)
    --   }
    --   MAX-ACCESS  read-only
    --  STATUS	current
    -- DESCRIPTION
    --    "This object holds type of ARP cache entry."
    --::= { csAtmConnStaticArpCacheEntry 3 }

	csAtmConnStaticArpCacheRowStatus OBJECT-TYPE
        SYNTAX	RowStatus
        MAX-ACCESS  read-create
        STATUS	current
        DESCRIPTION
               "This object is used to create, delete or modify
                a row in this table."
        ::= { csAtmConnStaticArpCacheEntry 4 }


     
	--
    --    ATM Connection IP Address Table
	--

	csAtmConnIpAddressTable OBJECT-TYPE
         SYNTAX   SEQUENCE OF CsAtmConnIpAddressEntry
         MAX-ACCESS   not-accessible
         STATUS   current
         DESCRIPTION
            ""
         ::= { csAtmInfo 5}

    csAtmConnIpAddressEntry OBJECT-TYPE
         SYNTAX   CsAtmConnIpAddressEntry
         MAX-ACCESS   not-accessible
         STATUS   current
         DESCRIPTION
            "This list contains ARP Entries for ATM virtual connections."
         INDEX { csAtmInterfaceConfSlotIndex, csAtmInterfaceConfPortIndex,
				 csAtmConnChannelIndex, csAtmConnSubIfIndex,csAtmConnIpAddressIpAddress}
	     ::= { csAtmConnIpAddressTable 1 }

    CsAtmConnIpAddressEntry ::=
	SEQUENCE {
	csAtmConnIpAddressIpAddress
		IpAddress,
	csAtmConnIpAddressRowStatus
		RowStatus,
    csAtmConnIpAddressType
        INTEGER
    }
	csAtmConnIpAddressIpAddress OBJECT-TYPE
        SYNTAX	IpAddress
        MAX-ACCESS  not-accessible
        STATUS	current
        DESCRIPTION
            "This object holds IP address for which ATM ARP module responds
            positively."
        ::= { csAtmConnIpAddressEntry 1 }
    
	csAtmConnIpAddressRowStatus OBJECT-TYPE
        SYNTAX	RowStatus
        MAX-ACCESS  read-create
        STATUS	current
        DESCRIPTION
               "This object is used to create, delete or modify
                a row in this table."
        ::= { csAtmConnIpAddressEntry 2 }

	csAtmConnIpAddressType OBJECT-TYPE
        SYNTAX	INTEGER {
			nonProxyIp (1),
			proxyIp (2),
            none (3)
        }
        MAX-ACCESS  read-only
        STATUS	current
        DESCRIPTION
               "This object specifies the type of IP address, i.e.,NON-PROXY-IP, or
               PROXY IP."
        ::= { csAtmConnIpAddressEntry 3 }
	--
	--
    --    Packet Over Sonet Interface Configuration Parameters Table
	--

	csPosInterfaceConfTable OBJECT-TYPE
         SYNTAX   SEQUENCE OF CsPosInterfaceConfEntry
         MAX-ACCESS   not-accessible
         STATUS   deprecated
         DESCRIPTION
            ""
         ::= { csPOSInfo 1 }

    csPosInterfaceConfEntry OBJECT-TYPE
         SYNTAX   CsPosInterfaceConfEntry
         MAX-ACCESS   not-accessible
         STATUS   deprecated
         DESCRIPTION
            ""
         INDEX { csPosInterfaceConfSlotIndex, csPosInterfaceConfPortIndex }
	     ::= { csPosInterfaceConfTable 1 }

    CsPosInterfaceConfEntry ::=
	SEQUENCE {
	csPosInterfaceConfSlotIndex
		Integer32,
	csPosInterfaceConfPortIndex
		Integer32,
	csPosEncapsulation
		INTEGER,
	csPosAdminStatus
		INTEGER,
	csPosOperStatus
		OperStatus
	}
	
	csPosInterfaceConfSlotIndex OBJECT-TYPE
	SYNTAX	Integer32 (1..64)
	MAX-ACCESS  not-accessible
	STATUS	deprecated
	DESCRIPTION
	       "This object identifies the blade to which this POS Port
	        is attached.  Together with csPosInterfaceConfPortIndex, it uniquely 
	        identifies a physical port."
	::= { csPosInterfaceConfEntry 1 }

	csPosInterfaceConfPortIndex OBJECT-TYPE
	SYNTAX	Integer32 (1..64)
	MAX-ACCESS  not-accessible
	STATUS	deprecated
	DESCRIPTION
	       "This object identifies the blade to which this POS Port
	        is attached.  Together with csPosInterfaceConfPortIndex, it uniquely 
	        identifies a physical port."
	::= { csPosInterfaceConfEntry 2 }

	csPosEncapsulation OBJECT-TYPE
	SYNTAX	INTEGER {
	    none		(1),
		hdlc		(2),
		ppp			(3),
		frameRelay  (4)
	}
	MAX-ACCESS  read-write
	STATUS  deprecated
	DESCRIPTION
	    "This object identifies the encapsulation format used on
	    this Packet Over Sonet port."
	::= { csPosInterfaceConfEntry 3 }

    csPosAdminStatus OBJECT-TYPE
	SYNTAX  INTEGER {
		enable  (1),
		disable (2)
	}
	MAX-ACCESS  read-write
	STATUS	current
	DESCRIPTION
	    "This object is used to enable/disable this POS interface."
	DEFVAL { disable }
	::= { csPosInterfaceConfEntry 4 }

    csPosOperStatus OBJECT-TYPE
	SYNTAX  OperStatus
	MAX-ACCESS  read-only
	STATUS	deprecated
	DESCRIPTION
	    "This object indicates the current operational status of this 
	    POS interface."
	::= { csPosInterfaceConfEntry 5 }


------------------------------------------------------------------------------
--
-- 		The VPN Group Info 
--
------------------------------------------------------------------------------

    csOrionVPNGeneralInfo	OBJECT IDENTIFIER ::= { csOrionVPNInfo 1 }
    csOrionVPNVRouterInfo	OBJECT IDENTIFIER ::= { csOrionVPNInfo 2 }
    csOrionVPNNotifyInfo	OBJECT IDENTIFIER ::= { csOrionVPNInfo 3 } -- objs for notifications
    csOrionVPNServerInfo	OBJECT IDENTIFIER ::= { csOrionVPNInfo 4 }

    csOrionVPNTable OBJECT-TYPE
	SYNTAX	SEQUENCE OF CsOrionVPNEntry
	MAX-ACCESS  not-accessible
	STATUS	current
	DESCRIPTION
	    "A list of VPNs which belong to Orion box."
	::= { csOrionVPNGeneralInfo 1 }

    csOrionVPNEntry OBJECT-TYPE
	SYNTAX 	 CsOrionVPNEntry
	MAX-ACCESS  not-accessible
	STATUS	current
	DESCRIPTION
	    "An entry containing management information applicable
	    to a particular interface or management Blade."
	INDEX   { csOrionGlobalVPNIndex }
	::= { csOrionVPNTable 1 }

    CsOrionVPNEntry ::=
	SEQUENCE {
	csOrionGlobalVPNIndex	
		Integer32,
	csOrionVPNName     
		DisplayString,
	csOrionVPNRadiusSvrList
		Integer32,
	csOrionVPNDNSSvrList
		Integer32,
	csOrionVPNRowStatus
		RowStatus,
	csOrionVPNOperStatus
		OperStatus
	}

    csOrionGlobalVPNIndex OBJECT-TYPE
	SYNTAX	Integer32 (1..2147483647)
	MAX-ACCESS not-accessible
	STATUS	current
	DESCRIPTION
	    "A globally unique value, greater than zero, for each
	    VPN, configured across all existing Orion boxes."
	::= { csOrionVPNEntry 1 }


    csOrionVPNName OBJECT-TYPE
	SYNTAX	DisplayString 
	MAX-ACCESS  read-create
	STATUS	current
	DESCRIPTION
	    "A textual string containing information about the VPN.
		By default this is set to 'VPN x', where x is the VPN ID."
	::= { csOrionVPNEntry 2 }

    csOrionVPNRadiusSvrList OBJECT-TYPE
	SYNTAX 	Integer32
	MAX-ACCESS  read-create
	STATUS	obsolete
	DESCRIPTION
		"This object identifies a prioritized list of RADIUS servers 
		(from the csRadiusSvrTable) that will be used when a packet
		needing RADIUS services is processed.
		NOTE: This object has been obsoleted. Each VR has its own
		      Radius server list. see csOrionRadiusInfo"

	::= { csOrionVPNEntry 3 }

    csOrionVPNDNSSvrList OBJECT-TYPE
	SYNTAX 	Integer32
	MAX-ACCESS  read-create
	STATUS	obsolete
	DESCRIPTION
		"This object identifies a prioritized list of DNS servers 
		(from the csDnsSvrTable) that will be used when a packet
		needing DNS services is processed.
		NOTE: This object has been obsoleted."
	::= { csOrionVPNEntry 4 }

    csOrionVPNRowStatus OBJECT-TYPE
	SYNTAX	      RowStatus 
	MAX-ACCESS  read-create
	STATUS	current
	DESCRIPTION
		"A row status type for the VPN."
	::= { csOrionVPNEntry 5 }

    csOrionVPNOperStatus OBJECT-TYPE
	SYNTAX	OperStatus
	MAX-ACCESS  read-only
	STATUS	current
	DESCRIPTION
		"A operational status for the VPN."
	::= { csOrionVPNEntry 6 }


------------------------------------------------------------------------------
--
-- 		The VPN Virtual Router Group Info 
--
------------------------------------------------------------------------------

    csOrionVrGeneralInfo   OBJECT IDENTIFIER ::= { csOrionVPNVRouterInfo 1 }
	csRtgPolicy		OBJECT IDENTIFIER ::= { csOrionVrGeneralInfo 2 }
	csOrionPing		OBJECT IDENTIFIER ::= { csOrionVrGeneralInfo 3 }
	    csOrionPingCtl	OBJECT IDENTIFIER ::=     { csOrionPing 1 }
	    csOrionPingResults	OBJECT IDENTIFIER ::=     { csOrionPing 2 }
	csOrionTraceRoute	OBJECT IDENTIFIER ::= { csOrionVrGeneralInfo 4 }
    csOrionVIfInfo	   OBJECT IDENTIFIER ::= { csOrionVPNVRouterInfo 2 }
    csOrionIp		   OBJECT IDENTIFIER ::= { csOrionVPNVRouterInfo 3 }
    csOrionOspf		   OBJECT IDENTIFIER ::= { csOrionVPNVRouterInfo 4 }
	csOspfConf         OBJECT IDENTIFIER ::= { csOrionOspf 1 }
	csOspfTrap    	   OBJECT IDENTIFIER ::= { csOrionOspf 2 }

    csOrionRip		   OBJECT IDENTIFIER ::= { csOrionVPNVRouterInfo 5 }
	csRipStats	      OBJECT IDENTIFIER ::= { csOrionRip 1 }
	csRipConf	      OBJECT IDENTIFIER ::= { csOrionRip 2 }
    csOrionTcp		   OBJECT IDENTIFIER ::= { csOrionVPNVRouterInfo 6 }
    csOrionUdp		   OBJECT IDENTIFIER ::= { csOrionVPNVRouterInfo 7 }
    csOrionBgp		   OBJECT IDENTIFIER ::= { csOrionVPNVRouterInfo 8 }
	csBgpStats	      OBJECT IDENTIFIER ::= { csOrionBgp 1 }
	csBgpConf	      OBJECT IDENTIFIER ::= { csOrionBgp 2 }
	    csBgpGen		OBJECT IDENTIFIER ::= { csBgpConf 1 }
	    csBgpNbr		OBJECT IDENTIFIER ::= { csBgpConf 2 }
	    csBgpPol		OBJECT IDENTIFIER ::= { csBgpConf 3 }
	    csBgpConfed		OBJECT IDENTIFIER ::= { csBgpConf 4 }
	    csBgpNetwork	OBJECT IDENTIFIER ::= { csBgpConf 5 }
	    csBgpNbrGroup	OBJECT IDENTIFIER ::= { csBgpConf 6 }

    csOrionIsis		   OBJECT IDENTIFIER ::= { csOrionVPNVRouterInfo 9 }
	csIsisSystem		OBJECT IDENTIFIER ::= { csOrionIsis 1 }
	csIsisCirc		OBJECT IDENTIFIER ::= { csOrionIsis 2 }
	csIsisISAdj		OBJECT IDENTIFIER ::= { csOrionIsis 3 }
	csIsisReachAdddr	OBJECT IDENTIFIER ::= { csOrionIsis 4 }
	csIsisIPReachAddr	OBJECT IDENTIFIER ::= { csOrionIsis 5 }

    csOrionMpls		   OBJECT IDENTIFIER ::= { csOrionVPNVRouterInfo 10 }
	csTeRsvpObjects    OBJECT IDENTIFIER ::= { csOrionMpls 1 }
	csTeMplsObjects    OBJECT IDENTIFIER ::= { csOrionMpls 2 }



------------------------------------------------------------------------------
--
-- 		The VPN Virtual Router General Group 
--
------------------------------------------------------------------------------

--
-- The Virtual Router Table
--

    csOrionVPNVRouterTable OBJECT-TYPE 
	SYNTAX	SEQUENCE OF CsOrionVPNVRouterEntry
	MAX-ACCESS  not-accessible
	STATUS	current
	DESCRIPTION
		"A list of Virtual Routers, configured for the VPN."
	::= { csOrionVrGeneralInfo 1 }

    csOrionVPNVRouterEntry OBJECT-TYPE
	SYNTAX 	 CsOrionVPNVRouterEntry
	MAX-ACCESS  not-accessible
	STATUS	current
	DESCRIPTION
		"An entry containing management information applicable
		to a particular virtual router, configured for the VPN."
	INDEX   { csOrionGlobalVPNIndex, csOrionVPNVRouterIndex }
	::= { csOrionVPNVRouterTable 1 }

    CsOrionVPNVRouterEntry ::=
	SEQUENCE {
	csOrionVPNVRouterIndex	
		IpAddress,
	csOrionVPNVRouterName     
		DisplayString,
 	csOrionVPNVRouterIpForwarding	
		INTEGER,
 	csOrionVPNVRouterIpDefaultTTL
     		Integer32,
	csOrionVPNVRouterIpReasmTimeout
		Integer32,
	csOrionVPNVRouterRowStatus
		RowStatus,
	csOrionVPNVRouterOperStatus
		OperStatus,
	csOrionVPNVRouterLocations
		DisplayString,
	csOrionVPNVRouterType
		INTEGER,
	csOrionVPNVRouterIpDecTtl
		INTEGER,
	csOrionVPNVRouterIpDsByte
		INTEGER,
	csOrionVPNVRouterOperLocations
		DisplayString,
	csOrionVPNVRouterDenyPktFilterEvlogStatus
		INTEGER
	}

    csOrionVPNVRouterIndex OBJECT-TYPE
 	SYNTAX	IpAddress 
 	MAX-ACCESS  not-accessible
	STATUS      current
	DESCRIPTION
		"A unique value, greater than zero, for each
		VPN Virtual Router. "
	::= { csOrionVPNVRouterEntry 1 }

    csOrionVPNVRouterName OBJECT-TYPE
	SYNTAX	DisplayString 
	MAX-ACCESS  read-create
	STATUS	current
	DESCRIPTION
		"A textual string containing information about the
		Virtual Router, configured to the particular VPN. "
	DEFVAL { "" }
	::= { csOrionVPNVRouterEntry 2 }

    csOrionVPNVRouterIpForwarding OBJECT-TYPE
	SYNTAX  INTEGER {
		forwarding(1),    -- acting as a gateway
		not-forwarding(2) -- NOT acting as a gateway
	}
	MAX-ACCESS  read-create
	STATUS  current
	DESCRIPTION
		"The indication of whether this entity is acting
		as an IP gateway in respect to the forwarding of
		datagrams received by, but not addressed to, this
		entity.  IP gateways forward datagrams.  IP hosts
		do not (except those source-routed via the host).

		Note that for some managed nodes, this object may
		take on only a subset of the values possible.
		Accordingly, it is appropriate for an agent to
		return a `badValue' response if a management
		station attempts to change this object to an
		inappropriate value."
	DEFVAL { forwarding }
	::= { csOrionVPNVRouterEntry 3 }

    csOrionVPNVRouterIpDefaultTTL OBJECT-TYPE
	SYNTAX  Integer32 (1..255)
	MAX-ACCESS  read-create
	STATUS  current
	DESCRIPTION
		"The default value inserted into the Time-To-Live
		field of the IP header of datagrams originated at
		this entity, whenever a TTL value is not supplied
		by the transport layer protocol."
	DEFVAL { 255 }
	::= { csOrionVPNVRouterEntry 4 }

    csOrionVPNVRouterIpReasmTimeout OBJECT-TYPE
	SYNTAX Integer32 (1..2147483647)
	MAX-ACCESS  read-create
	STATUS  current
	DESCRIPTION
		"The maximum number of seconds which received
		fragments are held while they are awaiting
		reassembly at this entity."
	DEFVAL { 5 }
	::= { csOrionVPNVRouterEntry 5 }

    csOrionVPNVRouterRowStatus OBJECT-TYPE
	SYNTAX		RowStatus
	MAX-ACCESS  read-create
	STATUS	current
	DESCRIPTION
		"A row status type for the VPN Virtual Router."
	::= { csOrionVPNVRouterEntry 8 }


    csOrionVPNVRouterOperStatus OBJECT-TYPE
	SYNTAX	OperStatus
	MAX-ACCESS  read-only
	STATUS	current
	DESCRIPTION
		"A operational status for the Virtual Router of the VPN."
	::= { csOrionVPNVRouterEntry 9 }

    csOrionVPNVRouterLocations OBJECT-TYPE
	SYNTAX	DisplayString (SIZE(0..80))
	MAX-ACCESS  read-create
	STATUS	current
	DESCRIPTION
		"This object contains an ascii string which is used to
		identify possible address locations for the various
		elements of a Virtual Router.  The format of the string
		is 'a/x, b/y, c/z', where 'a', 'b' and 'c' denote the 
		blade numbers and are integers (1..26); 'x', 'y' and 'z'
		denote the processor engine (PE) ID and are integers 
		(0..3). Specification of PE is optional.

		Note, this object can only be set when the Virtual Router 
		is being created.  If nothing is entered, the Resource 
		Manager will decide where to place the Virtual Router 
		elements. If the blade is specified but not the PE ID, 
		the Resource Manager will decide which PE(s) to place the 
		various Virtual Router objects on." 
	DEFVAL { "" }
	::= { csOrionVPNVRouterEntry 10 }

    csOrionVPNVRouterType OBJECT-TYPE
	SYNTAX	INTEGER {
		customerVr	   (1),
		controlVr	   (2),
		serviceProviderVr  (3)
	}
	MAX-ACCESS  read-create
	STATUS	current
	DESCRIPTION
		"This identifies whether this Virtual Router is a data
		VR or the Control VR.  Note, there can be only one control
		VR on the entire IPSX system and it must be located entirely
		on the control blade.  Further, this object can only be
		set when the Virtual Router is being created."
	DEFVAL { customerVr }
	::= { csOrionVPNVRouterEntry 11 }

    csOrionVPNVRouterIpDecTtl OBJECT-TYPE
	SYNTAX	INTEGER {
		enabled		(1),
		disabled	(2)
	}
	MAX-ACCESS  read-create
	STATUS	current
	DESCRIPTION
		""
	DEFVAL { enabled }
	::= { csOrionVPNVRouterEntry 12 }

    csOrionVPNVRouterIpDsByte OBJECT-TYPE
	SYNTAX		INTEGER (0..256)
	MAX-ACCESS  read-create
	STATUS  current
	DESCRIPTION
		"This object defines the values to be placed in the TypeOfService
		octet of each IP packet sent out or forwarded by the VR. The valid 
		range covers both 7-bit configurations recommended in RFC 1349 
		(Precedence and TOS bits) and 6-bit configurations recommended 
		in RFC 2474 (Differentiated Services). If the value selected 
		is 256, the DsByte is not changed and packets are forwarded with 
		their existing TypeOfService byte value.

		This object can be an IPv4 TOS octet:
		0     1     2     3     4     5     6     7
             +-----+-----+-----+-----+-----+-----+-----+-----+
             |                 |                       |     |
             |   PRECEDENCE    |          TOS          | MBZ |
             |                 |                       |     |
             +-----+-----+-----+-----+-----+-----+-----+-----+

		Precedence (from RFC 791)

          	111 - Network Control
          	110 - Internetwork Control
          	101 - CRITIC/ECP
          	100 - Flash Override
          	011 - Flash
          	010 - Immediate
          	001 - Priority
          	000 - Routine

		TOS (from RFC 1349)

		1000   --   minimize delay
                0100   --   maximize throughput
                0010   --   maximize reliability
                0001   --   minimize monetary cost
                0000   --   normal service

		MBZ (must be zero) is unused.


		Or this object can be a DS field (from RFC 2474):
		0     1     2     3     4     5     6     7
             +-----+-----+-----+-----+-----+-----+-----+-----+
             |                                   |           |
             |               DSCP                |     CU    |
             |                                   |           |
             +-----+-----+-----+-----+-----+-----+-----+-----+

        	DSCP: differentiated services codepoint
        	CU:   currently unused

		DSCP is used to select the PHB (per-hop behavior) a
		packet experiences at each node. It is recommended that
		bits 0-2 of the DSCP field be employed in a manner 
		similar to, or subsuming, the deployed uses of the 
		IP Precedence field of an IPv4 TOS octet to maintain 
		some form of backward compatibility. 
		"
	DEFVAL { 256 }
	::= { csOrionVPNVRouterEntry 13 }

    csOrionVPNVRouterOperLocations OBJECT-TYPE
	SYNTAX	DisplayString (SIZE(0..80))
	MAX-ACCESS  read-only
	STATUS	current
	DESCRIPTION
		"This object contains an ascii string which is used to
		identify the operational address locations for the various
		elements of a Virtual Router.  The format of the string
		is 'a/x, b/y, c/z', where 'a', 'b' and 'c' denote the 
		blade numbers and are integers (1..26); 'x', 'y' and 'z'
		denote the processor engine ID and are integers (0..3)." 
	::= { csOrionVPNVRouterEntry 14 }

	csOrionVPNVRouterDenyPktFilterEvlogStatus OBJECT-TYPE
	SYNTAX		INTEGER {
		enable	(1),
		disable	(2)
	} 
	MAX-ACCESS	read-create
	STATUS		current
	DESCRIPTION
		"If enabled, event logs will be sent when a packet hits a packet filter 
		 on the VR or on any VI in the VR with a DENY action."
	DEFVAL { disable }
	::= { csOrionVPNVRouterEntry 15 }
	
	
------------------------------------------------------------------------------
--
-- 		The Routing Policy Group
--
------------------------------------------------------------------------------

--
-- The Import Policy Table
--

    csImpPolTable OBJECT-TYPE
	SYNTAX  SEQUENCE OF CsImpPolEntry
	MAX-ACCESS  not-accessible
	STATUS  current
	DESCRIPTION
		"This table is used to configure the import policies stored
		on a virtual router.

		Once configured, these policies can be applied to any
		routing protocol."
	::= { csRtgPolicy 1 }

    csImpPolEntry OBJECT-TYPE
	SYNTAX CsImpPolEntry
	MAX-ACCESS not-accessible
	STATUS  current
	DESCRIPTION
		"Each entry contains information about a single import policy."
	INDEX   { csOrionGlobalVPNIndex, csOrionVPNVRouterIndex, csImpPolId }
	::= { csImpPolTable 1 }

    CsImpPolEntry ::=
	SEQUENCE {
	csImpPolId
		Integer32,
	csImpPolGenAclId
		Integer32,
	csImpPolPeerAS
		Integer32,
	csImpPolHomeAS
		Integer32,
	csImpPolOrigin
		INTEGER,
	csImpPolAction
		INTEGER,
	csImpPolPreference
		Integer32,
	csImpPolRowStatus
		RowStatus,
	csImpPolBgpCommunity1
		Integer32
	}

    csImpPolId OBJECT-TYPE
	SYNTAX Integer32 (1..65535)
	MAX-ACCESS  not-accessible
	STATUS  current
	DESCRIPTION
		"This object identifies a specific Import Policy entry."
	::= { csImpPolEntry 1 }

    csImpPolGenAclId OBJECT-TYPE
	SYNTAX  Integer32 (-1..65535)
	MAX-ACCESS  read-create
	STATUS  current
	DESCRIPTION
		"The identifier of General Access List entry that this
		Policy uses.

		The value -1 represents a wildcard for this Import Policy 
		parameter."
	DEFVAL  { -1 }
	::= { csImpPolEntry 2 }

    csImpPolPeerAS OBJECT-TYPE
	SYNTAX  Integer32 (-1..65535)
	MAX-ACCESS  read-create
	STATUS  current
	DESCRIPTION
		"Used by BGP, the autonomous system number of the remote peer.

		The value -1 represents a wildcard for this Import Policy 
		parameter."
	DEFVAL  { -1 }
	::= { csImpPolEntry 3 }

    csImpPolHomeAS OBJECT-TYPE
	SYNTAX  Integer32 (-1..65535)
	MAX-ACCESS  read-create
	STATUS  current
	DESCRIPTION
		"Used by BGP, the home autonomous system number of the BGP 
		system originating the update.

		The value -1 represents a wildcard for this Import Policy 
		parameter."
	DEFVAL  { -1 }
	::= { csImpPolEntry 4 }

    csImpPolOrigin OBJECT-TYPE
	SYNTAX  INTEGER {
		unknown	(1),
		igp	(2),
		egp	(3),
		any	(4)
	}
	MAX-ACCESS  read-create
	STATUS  current
	DESCRIPTION
		"Used by BGP, the origin type as placed in the AS path by the 
		originator of the update.  The origin could be IGP (the route 
		was learned from an internal gateway protocol), EGP (the
		route was learned via an exterior gateway protocol) or
		unknown (the origin of the route cannot be determined).
		any (signal policy module to ignore this value)

		The value egp is deprecated."
	DEFVAL  { any }
	::= { csImpPolEntry 5 }

    csImpPolAction OBJECT-TYPE
	SYNTAX  INTEGER {
		permit	(1),
		deny	(2)
	}
	MAX-ACCESS  read-create
	STATUS  current
	DESCRIPTION
		"The action to take on routes that match this policy."
	::= { csImpPolEntry 6 }

    csImpPolPreference OBJECT-TYPE
	SYNTAX  Integer32 (-1..65535)
	MAX-ACCESS  read-create
	STATUS  current
	DESCRIPTION
		"The preference to apply to routes that match this
		policy.  Note, this object only applies to import policies 
		that have a 'permit' action.

		The value -1 indicates this parameter has not been set."
	DEFVAL  { -1 }
	::= { csImpPolEntry 7 }

    csImpPolRowStatus OBJECT-TYPE
	SYNTAX  RowStatus
	MAX-ACCESS  read-create
	STATUS  current
	DESCRIPTION
		"The RowStatus object for this table.  This is used to
		add/delete rows from this table."
	::= { csImpPolEntry 8 }


    csImpPolBgpCommunity1 OBJECT-TYPE
	SYNTAX  Integer32
	MAX-ACCESS  read-create
	STATUS  current
	DESCRIPTION
                "The BGP Community parameter 1. Refer to RFC1997.
                The following values are not allowed in the configuration:
                0 through 0x0000FFFF and 0xFFFF0000 through 0xFFFFFFFF.
                "
        DEFVAL { 0 }
        ::= { csImpPolEntry 9 }
--
-- The Export Policy Table
--

    csExpPolTable OBJECT-TYPE
	SYNTAX  SEQUENCE OF CsExpPolEntry
	MAX-ACCESS  not-accessible
	STATUS  current
	DESCRIPTION
		"This table is used to configure the export policies stored
		on a virtual router.

		Once configured, these policies can be applied to any
		routing protocol."
	::= { csRtgPolicy 2 }

    csExpPolEntry OBJECT-TYPE
	SYNTAX CsExpPolEntry
	MAX-ACCESS not-accessible
	STATUS  current
	DESCRIPTION
		"Each entry contains information about a single import policy."
	INDEX   { csOrionGlobalVPNIndex, csOrionVPNVRouterIndex, csExpPolId }
	::= { csExpPolTable 1 }

    CsExpPolEntry ::=
	SEQUENCE {
	csExpPolId
		Integer32,
	csExpPolGenAclId
		Integer32,
	csExpPolPeerAS
		Integer32,
	csExpPolProtocol
		INTEGER,
	csExpPolEgpAS
		Integer32,
	csExpPolBgpAS
		Integer32,
	csExpPolExtRteTag
		Integer32,
	csExpPolRipIp
		IpAddress,
	csExpPolRipNbrIp
		IpAddress,
	csExpPolAction
		INTEGER,
	csExpPolMetric
		Integer32,
	csExpPolRowStatus
		RowStatus,
	csExpPolBgpCommunity1
		Integer32,
	csExpPolBgpCommunity2
		Integer32,
	csExpPolRouteType 
		INTEGER,
	csExpPolMetricType
		INTEGER,
	csExpPolLevel
		INTEGER
	}

    csExpPolId OBJECT-TYPE
	SYNTAX Integer32 (1..65535)
	MAX-ACCESS  not-accessible
	STATUS  current
	DESCRIPTION
		"This object identifies a specific Export Policy entry."
	::= { csExpPolEntry 1 }

    csExpPolGenAclId OBJECT-TYPE
	SYNTAX  Integer32 (-1..65535)
	MAX-ACCESS  read-create
	STATUS  current
	DESCRIPTION
		"The identifier of General Access List entry that this
		Policy uses.

		The value -1 represents a wildcard for this Import Policy 
		parameter."
	DEFVAL  { -1 }
	::= { csExpPolEntry 2 }

    csExpPolPeerAS OBJECT-TYPE
	SYNTAX  Integer32 (-1..65535)
	MAX-ACCESS  read-create
	STATUS  current
	DESCRIPTION
		"The target system's autonomous system number. 

		The value -1 represents a wildcard for this Import Policy 
		parameter."
	DEFVAL  { -1 }
	::= { csExpPolEntry 3 }

    csExpPolProtocol OBJECT-TYPE
	SYNTAX  INTEGER {
		all	(1),
		local	(2),
		bgp	(3),
		rip	(4),
		ospf	(5),
		static	(6),
		i-bgp	(7),
		ospf-ext   (8),
		isis	(9),
		aggregate (10)
	}
	MAX-ACCESS  read-create
	STATUS  current
	DESCRIPTION
		"The protocol that has added the route to the routing table."
	DEFVAL  { all }
	::= { csExpPolEntry 4 }

    csExpPolEgpAS OBJECT-TYPE
	SYNTAX  Integer32 (-1..65535)
	MAX-ACCESS  read-create
	STATUS  obsolete
	DESCRIPTION
		"If a route was added via EGP, this object is the AS number
		of the EGP peer.

		The value -1 represents a wildcard for this Import Policy 
		parameter."
	DEFVAL  { -1 }
	::= { csExpPolEntry 5 }

    csExpPolBgpAS OBJECT-TYPE
	SYNTAX  Integer32 (-1..65535)
	MAX-ACCESS  read-create
	STATUS  current
	DESCRIPTION
		"If a route was added via BGP, this object is the AS number
		of the BGP peer.

		The value -1 represents a wildcard for this Import Policy 
		parameter."
	DEFVAL  { -1 }
	::= { csExpPolEntry 6 }

    csExpPolExtRteTag OBJECT-TYPE
	SYNTAX  Integer32 
	MAX-ACCESS  read-create
	STATUS  current
	DESCRIPTION
		"If the route was added via OSPF External, this is the 
		eter
		The value -1 represents a wildcard for this Import Policy 
		parameter."
	DEFVAL  { -1 }
	::= { csExpPolEntry 7 }

    csExpPolRipIp OBJECT-TYPE
	SYNTAX  IpAddress 
	MAX-ACCESS  read-create
	STATUS  current
	DESCRIPTION
		"The value 0.0.0.0 represents a wildcard for this Import Policy 
		parameter."
	DEFVAL   { '00000000'H }    -- 0.0.0.0
	::= { csExpPolEntry 8 }

    csExpPolRipNbrIp OBJECT-TYPE
	SYNTAX  IpAddress 
	MAX-ACCESS  read-create
	STATUS  current
	DESCRIPTION
		"The value 0.0.0.0 represents a wildcard for this Import Policy 
		parameter."
	DEFVAL   { '00000000'H }    -- 0.0.0.0
	::= { csExpPolEntry 9 }

    csExpPolAction OBJECT-TYPE
	SYNTAX  INTEGER {
		export	(1),
		block	(2)
	}
	MAX-ACCESS  read-create
	STATUS  current
	DESCRIPTION
		"The action to perform on  packets matching this policy."
	::= { csExpPolEntry 10 }

    csExpPolMetric OBJECT-TYPE
	SYNTAX  Integer32 (-1..65535)
	MAX-ACCESS  read-create
	STATUS  current
	DESCRIPTION
		"The metric to assign to  packets matching this policy.

		The value -1 indicates this parameter has not been set."
	DEFVAL  { -1 }
	::= { csExpPolEntry 11 }

    csExpPolRowStatus OBJECT-TYPE
	SYNTAX  RowStatus
	MAX-ACCESS  read-create
	STATUS  current
	DESCRIPTION
		"The RowStatus object for this table.  This is used to
		add/delete rows from this table."
	::= { csExpPolEntry 12 }

    csExpPolBgpCommunity1 OBJECT-TYPE
	SYNTAX  Integer32
	MAX-ACCESS  read-create
	STATUS  current
	DESCRIPTION
		"The BGP Community parameter 1. Refer to RFC1997.
		The following values are not allowed in the configuration:
		0 through 0x0000FFFF and 0xFFFF0000 through 0xFFFFFFFF.
		But the following values are allowed within that range:
		0xFFFF FF01 (NO-EXPORT)
		0xFFFF FF02 (NO-ADVERTISE)
		0xFFFF FF03 (NO-EXPORT-SUB)
		Note that this value can not be set to 0 unless 
		csExpPolBgpCommunity2 is set to 0. 
		"
	DEFVAL { 0 }
	::= { csExpPolEntry 13 }

    csExpPolBgpCommunity2 OBJECT-TYPE
	SYNTAX  Integer32
	MAX-ACCESS  read-create
	STATUS  current
	DESCRIPTION
		"Same description as csExpPolBgpCommunity1"
	DEFVAL { 0 }
	::= { csExpPolEntry 14 }

    csExpPolRouteType OBJECT-TYPE
	SYNTAX  INTEGER {
		any			(0),
		isislevel1		(1),
		isislevel2		(2),
		isislevel12		(3),
		ospfinternal		(4),
		ospfexternal		(5),
		ospfexternal1		(6),
		ospfexternal2		(7)
	}
	MAX-ACCESS  read-create
	STATUS  current
	DESCRIPTION
		"RouteType to be matched when exporting ISIS/OSPF route into 
		 another   protocol. ISISlevel1, ISISlevel2 and ISISlevel12 can 
		 be set if csExpPolProtocol is set to ISIS. OSPFinternal, 
		 OSPFexternal, OSPFexternal1 and OSPFexternal2 can be set if 
		 csExpPolProtocol is set to OSPF"
	DEFVAL  { any }
	::= { csExpPolEntry 15 }

    csExpPolMetricType OBJECT-TYPE
	SYNTAX  INTEGER {
		any			(0),
		ospftype1		(1),
		ospftype2		(2),
		isisinternal		(3),
		isisexternal		(4)
	}
	MAX-ACCESS  read-create
	STATUS  current
	DESCRIPTION
	 	"Metric type to be set when exporting route into 
		 a protocol. OSPFtype1     and OSPFtype2 are only applicable 
		for OSPF. ISISinternal and ISISexternal are only applicable for ISIS."
	DEFVAL  { any }
	::= { csExpPolEntry 16 }

    csExpPolLevel OBJECT-TYPE
	SYNTAX  INTEGER {
		any			(0),
		isislevel1		(1),
		isislevel2		(2),
		isislevel12		(3),
		ospfstubarea		(4),
		ospfbackbone		(5)
	}
	MAX-ACCESS  read-create
	STATUS  current
	DESCRIPTION
		"To indicate where to import routes, applicable to ISIS and 
		 OSPF only. ISISlevel1, ISISlevel2, ISISlevel3 are applicable 
		 when you apply export policy for ISIS. OSPFstubarea and OSPFbackbone 
		 are applicable when you apply export policy for OSPF."
	DEFVAL  { any }
	::= { csExpPolEntry 17 }




----------------------------------------------------------------------------
-- Ping Control Table
----------------------------------------------------------------------------

   csOrionPingCtlTable OBJECT-TYPE
	SYNTAX	 SEQUENCE OF CsOrionPingCtlEntry
	MAX-ACCESS  not-accessible
	STATUS	 current
	DESCRIPTION
	    "Defines the ping Control Table for provide, via SNMP,
	    the capability of performing ping operations at
	    a remote host.  The results of these operations are
	    stored in the csOrionPingResultsTable."
	::= { csOrionPingCtl 1 }

   csOrionPingCtlEntry OBJECT-TYPE
	SYNTAX	 CsOrionPingCtlEntry
	MAX-ACCESS  not-accessible
	STATUS	 current
	DESCRIPTION
	    "Defines an entry in the csOrionPingCtlTable.  
	    The 3rd index, csOrionPingCtlTestName, must have the 
	    following format when used for Tunnel Keepalives: TUNNEL vi-id."
	INDEX { csOrionGlobalVPNIndex, csOrionVPNVRouterIndex,
		    csOrionPingCtlTestName }
	::= { csOrionPingCtlTable 1 }

   CsOrionPingCtlEntry ::=
	SEQUENCE {
	    csOrionPingCtlTestName	DisplayString,
	    csOrionPingCtlTargetAddress	IpAddress,
	    csOrionPingCtlTimeOut	Unsigned32,
	    csOrionPingCtlProbeCount	Unsigned32,
	    csOrionPingCtlAdminStatus	INTEGER,
	    csOrionPingCtlFrequency	Unsigned32,
   	    csOrionPingCtlTrapFilter	Unsigned32,
	    csOrionPingCtlRowStatus	RowStatus,
	    csOrionPingCtlSourceAddress IpAddress,
	    csOrionPingCtlLength        Unsigned32,
	    csOrionPingCtlTtl 		Unsigned32
	}


   csOrionPingCtlTestName OBJECT-TYPE
	SYNTAX	 DisplayString (SIZE(0..80))
	MAX-ACCESS  not-accessible
	STATUS	 current
	DESCRIPTION
	    "The name of the ping test.  This is locally unique, within
	    the scope of a Virtual Router.  This must have the following 
		format when used for Tunnel Keepalives: TUNNEL vi-id"
	::= { csOrionPingCtlEntry 1 }

   csOrionPingCtlTargetAddress OBJECT-TYPE
	SYNTAX	 IpAddress
	MAX-ACCESS  read-create
	STATUS	 current
	DESCRIPTION
	    "Specifies the host address to be used at a remote host for
	    performing a ping operation.  

	    A value for this object MUST be set prior to transitioning
	    its corresponding csOrionPingCtlEntry to active(1) via
	    csOrionPingCtlRowStatus."
	::= { csOrionPingCtlEntry 2 }

   csOrionPingCtlTimeOut OBJECT-TYPE
	SYNTAX	 Unsigned32 (1..60)
	MAX-ACCESS  read-create
	STATUS	 current
	DESCRIPTION
	    "Specifies the time-out value, in seconds, for a
	    remote ping operation."
	DEFVAL { 3 }
	::= { csOrionPingCtlEntry 3 }

   csOrionPingCtlProbeCount OBJECT-TYPE
	SYNTAX	 Unsigned32 (1..15)
	MAX-ACCESS  read-create
	STATUS	 current
	DESCRIPTION
	    "Specifies the number of times to perform a ping
	    operation at a remote host."
	DEFVAL { 4 }
	::= { csOrionPingCtlEntry 4 }

   csOrionPingCtlAdminStatus OBJECT-TYPE
	SYNTAX	 INTEGER {
		enabled(1), -- test should be started
		disabled(2) -- test should be stop
	}
	MAX-ACCESS  read-create
	STATUS	 current
	DESCRIPTION
	    "Reflects the desired state that a csOrionPingCtlEntry should be
	    in:

		  enabled(1)  - Attempt to activate the test as defined by
		                this csOrionPingCtlEntry.
		  disabled(2) - Deactivate the test as defined by this
		                csOrionPingCtlEntry.

	    Refer to the corresponding csOrionPingResultsOperStatus to
	    determine the operational state of the test defined by
	    this entry."
	 DEFVAL { disabled }
	::= { csOrionPingCtlEntry 5 }


   csOrionPingCtlFrequency  OBJECT-TYPE
	SYNTAX	 Unsigned32
	MAX-ACCESS  read-create
	STATUS	 current
	DESCRIPTION
	    "The number of seconds to wait before repeating a ping test
	    as defined by the value of the various objects in the
	    corresponding row.

	    A single ping test consists of a series of ping probes.
	    The number of probes is determined by the value of the
	    corresponding csOrionPingCtlProbeCount object.  After a single
	    test completes the number of seconds as defined by the
	    value of csOrionPingCtlFrequency MUST elapse before the
	    next ping test is started.

	    A value of 0 for this object implies that the test
	    as defined by the corresponding entry will not be
	    repeated."
	DEFVAL { 0 }
	::= { csOrionPingCtlEntry 6 }

   csOrionPingCtlTrapFilter OBJECT-TYPE
      SYNTAX      Unsigned32 (0..15)
      MAX-ACCESS  read-create
      STATUS      current
      DESCRIPTION
          "The value of this object is used to determine when
	  a Ping Test fails.  If the number of unanswered Ping
	  requests within a test is greater that the value of this 
	  object within, then the test has failed."
      DEFVAL { 3 }
      ::= { csOrionPingCtlEntry 7 }

   csOrionPingCtlRowStatus OBJECT-TYPE
	SYNTAX	 RowStatus
	MAX-ACCESS  read-create
	STATUS	 current
	DESCRIPTION
	    "This object allows entries to be created and deleted
	    in the csOrionPingCtlTable.  Deletion of an entry in this
	    table results in all corresponding (same
	    csOrionPingCtlTestName index values)
	    csOrionPingResultsTable entries being deleted.

	    A value MUST be specified for csOrionPingCtlTargetAddress
	    prior to a transition to active(1) state being
	    accepted.

	    This object only supports the createAndGo method of
	    row creation.

	    Remove an entry in this table by setting its RowStatus
	    object to destroy(6)."
	REFERENCE
	    "RFC 2579, 'Textual Conventions for SMIv2.'"
	::= { csOrionPingCtlEntry 8 }

   csOrionPingCtlSourceAddress OBJECT-TYPE
	SYNTAX	 IpAddress
	MAX-ACCESS  read-create
	STATUS	 current
	DESCRIPTION
	    "Specifies the Source IP address to be used when performing a 
	    ping operation.  

	    If this object has the value 0.0.0.0, the Source IP Address
	    will be determined automatically by the IP layer."
	DEFVAL   { '00000000'H }    -- 0.0.0.0
	::= { csOrionPingCtlEntry 9 }

   csOrionPingCtlLength OBJECT-TYPE
	SYNTAX	 Unsigned32 (1..1600)
	MAX-ACCESS  read-create
	STATUS	 current
	DESCRIPTION
	    "Specifies the length of the data portion of the ICMP Echo
	    Request packet."
	DEFVAL { 64 }
	::= { csOrionPingCtlEntry 10 }

   csOrionPingCtlTtl OBJECT-TYPE
	SYNTAX	 Unsigned32 (0..255)
	MAX-ACCESS  read-create
	STATUS	 current
	DESCRIPTION
	    "Specifies the Time-To-Live value used in the IP Header when
	    performing a ping operation.

	    Note, if this object has the value 0, the IP layer will set the
	    TTL value to its default."
	DEFVAL { 0 }
	::= { csOrionPingCtlEntry 11 }

----------------------------------------------------------------------------
-- Ping Results Table
----------------------------------------------------------------------------

   csOrionPingResultsTable OBJECT-TYPE
	SYNTAX	 SEQUENCE OF CsOrionPingResultsEntry
	MAX-ACCESS  not-accessible
	STATUS	 current
	DESCRIPTION
	    "Defines the Ping Results Table for providing
	    the capability of performing ping operations at
	    a remote host.  The results of these operations are
	    stored in the csOrionPingResultsTable and the pingPastProbeTable.

	    An entry is added to the csOrionPingResultsTable when an
	    csOrionPingCtlEntry is started by successful transition
	    of its csOrionPingCtlAdminStatus object to enabled(1).
	    An entry is removed from the csOrionPingResultsTable when
	    its corresponding csOrionPingCtlEntry is deleted."
	::= { csOrionPingResults 2 }

   csOrionPingResultsEntry OBJECT-TYPE
	SYNTAX	 CsOrionPingResultsEntry
	MAX-ACCESS  not-accessible
	STATUS	 current
	DESCRIPTION
	    "Defines an entry in the csOrionPingResultsTable.  The
	    csOrionPingResultsTable has the same indexing as the
	    csOrionPingCtlTable in order for a csOrionPingResultsEntry to
	    correspond to the csOrionPingCtlEntry that caused it to
	    be created."
	INDEX {  csOrionGlobalVPNIndex, csOrionVPNVRouterIndex,
		    csOrionPingCtlTestName
	 }
	::= { csOrionPingResultsTable 1 }

   CsOrionPingResultsEntry ::=
	SEQUENCE {
	    csOrionPingResultsIpTargetAddress   IpAddress,
	    csOrionPingResultsMinRtt	        Unsigned32,
	    csOrionPingResultsMaxRtt	        Unsigned32,
	    csOrionPingResultsAverageRtt	Unsigned32,
	    csOrionPingResultsProbeResponses    Counter32,
	    csOrionPingResultsSentProbes	Counter32,
	    csOrionPingResultsErrors		Counter32,
	    csOrionPingResultsTimeOuts		Counter32,
	    csOrionPingResultsLates		Counter32,
	    csOrionPingResultsUnreachables	Counter32,
	    csOrionPingResultsCurrentStatus	INTEGER
	 }

   csOrionPingResultsIpTargetAddress OBJECT-TYPE
	SYNTAX	 IpAddress
	MAX-ACCESS  read-only
	STATUS	 current
	DESCRIPTION
	    "This objects reports the IP address associated
	    with a csOrionPingCtlTargetAddress."
	::= { csOrionPingResultsEntry 1 }

   csOrionPingResultsMinRtt OBJECT-TYPE
	SYNTAX	 Unsigned32
	MAX-ACCESS  read-only
	STATUS	 current
	DESCRIPTION
	    "The minimum ping round-trip-time (RTT) received."
	::= { csOrionPingResultsEntry 2 }

   csOrionPingResultsMaxRtt OBJECT-TYPE
	SYNTAX	 Unsigned32
	MAX-ACCESS  read-only
	STATUS	 current
	DESCRIPTION
	    "The maximum ping round-trip-time (RTT) received."
	::= { csOrionPingResultsEntry 3 }

    csOrionPingResultsAverageRtt OBJECT-TYPE
	SYNTAX	 Unsigned32
	MAX-ACCESS  read-only
	STATUS	 current
	DESCRIPTION
	    "The current average ping round-trip-time (RTT)."
	::= { csOrionPingResultsEntry 4 }

    csOrionPingResultsProbeResponses OBJECT-TYPE
	SYNTAX	 Counter32
	MAX-ACCESS  read-only
	STATUS	 current
	DESCRIPTION
	    "Number of responses received for the corresponding
	    csOrionPingCtlEntry and csOrionPingResultsEntry.  The value 
	    of this object MUST be reported as 0 when no probe responses 
	    have been received."
	::= { csOrionPingResultsEntry 5 }

    csOrionPingResultsSentProbes OBJECT-TYPE
	SYNTAX	 Counter32
	MAX-ACCESS  read-only
	STATUS	 current
	DESCRIPTION
	    "The value of this object reflects the number of probes sent
	    for the corresponding csOrionPingCtlEntry and csOrionPingResultsEntry.
	    The value of this object MUST be reported as 0 when no probes
	    have been sent."
	::= { csOrionPingResultsEntry 6 }

    csOrionPingResultsErrors OBJECT-TYPE
	SYNTAX	 Counter32
	MAX-ACCESS  read-only
	STATUS	 current
	DESCRIPTION
	    "The value of this object reflects the number of times
	    errors were encountered while attempting to send a probe."
	::= { csOrionPingResultsEntry 7 }

    csOrionPingResultsTimeOuts OBJECT-TYPE
	SYNTAX	 Counter32
	MAX-ACCESS  read-only
	STATUS	 current
	DESCRIPTION
	    "The value of this object reflects the number of times
	    a probe was sent and more than csOrionPingCtlTimeOut seconds
	    was spent waiting for the response."
	::= { csOrionPingResultsEntry 8 }

    csOrionPingResultsLates OBJECT-TYPE
	SYNTAX	 Counter32
	MAX-ACCESS  read-only
	STATUS	 current
	DESCRIPTION
	    "The value of this object reflects the number of times
	    a probe was sent and a response was received more than 
	    csOrionPingCtlTimeOut seconds later.  Note, responses that
	    are marked 'late' are not reflected in the 
	    csOrionPingCtlTimeOut counter."
	::= { csOrionPingResultsEntry 9 }

    csOrionPingResultsUnreachables OBJECT-TYPE
	SYNTAX	 Counter32
	MAX-ACCESS  read-only
	STATUS	 current
	DESCRIPTION
	    "The value of this object reflects the number of times
	    a probe was sent and an ICMP Destination Unreachable message
	    was received."
	::= { csOrionPingResultsEntry 10 }

    csOrionPingResultsCurrentStatus OBJECT-TYPE
	SYNTAX	INTEGER {
		successful	(1),
		failed		(2),
		unknown		(3)
	}
	MAX-ACCESS read-only
	STATUS	current
	DESCRIPTION
	    "This object has the results of the most recently completed
	ping test.  If no test has yet been completed, this object will
	have the value: unknown(1)."
	::= { csOrionPingResultsEntry 11 }


----------------------------------------------------------------------------
-- TraceRoute Command
----------------------------------------------------------------------------

   csOrionTraceRouteReqTable OBJECT-TYPE
	SYNTAX  SEQUENCE OF CsOrionTraceRouteReqEntry
	MAX-ACCESS  not-accessible
	STATUS  current
	DESCRIPTION
		"Trace Route Request Table."
	::= { csOrionTraceRoute 1 }

    csOrionTraceRouteReqEntry  OBJECT-TYPE
	SYNTAX  CsOrionTraceRouteReqEntry
	MAX-ACCESS  not-accessible
	STATUS  current
	DESCRIPTION
		"An entry of Trace Route Request Table."
	INDEX   { csOrionGlobalVPNIndex, csOrionVPNVRouterIndex,
			  csOrionTraceRouteReqIndex }
	::= { csOrionTraceRouteReqTable 1 }

    CsOrionTraceRouteReqEntry ::=
	SEQUENCE {
	csOrionTraceRouteReqIndex
		Integer32,
	csOrionTraceRouteReqDestAddr
		IpAddress,
	csOrionTraceRouteReqHops
		Integer32,
	csOrionTraceRouteReqSrcAddr
		IpAddress,
	csOrionTraceRouteReqStatus
		INTEGER,
	csOrionTraceRouteReqRowStatus
		RowStatus
	}

	csOrionTraceRouteReqIndex OBJECT-TYPE
	SYNTAX Integer32 (1..2147483647)
	MAX-ACCESS  not-accessible
	STATUS  current
	DESCRIPTION
		"This object identifies a specific Trace Route request entry.
		NMSs are expected to come up with a unique ID each request.
		This ID will also be used to index the Trace Route result entry."
	::= { csOrionTraceRouteReqEntry 1 }

	csOrionTraceRouteReqDestAddr OBJECT-TYPE
	SYNTAX		IpAddress
	MAX-ACCESS	read-create
	STATUS		current
	DESCRIPTION
	    "The destination host for the Trace Route operation.
		Must be set for request to be processed."
	::= { csOrionTraceRouteReqEntry 2 }

	csOrionTraceRouteReqHops OBJECT-TYPE
	SYNTAX Integer32 (1..65535)
	MAX-ACCESS	read-create
	STATUS		current
	DESCRIPTION
	    "Maximum number of hops to reach destination host."
	DEFVAL {30}
	::= { csOrionTraceRouteReqEntry 3 }

	csOrionTraceRouteReqSrcAddr OBJECT-TYPE
	SYNTAX		IpAddress
	MAX-ACCESS	read-create
	STATUS		current
	DESCRIPTION
	    "The source host for the Trace Route operation."
	::= { csOrionTraceRouteReqEntry 4 }

    csOrionTraceRouteReqStatus OBJECT-TYPE
	SYNTAX		INTEGER {
		none  (1),
		opInProgress (2),
		opSuccess (3),
		opFailed (4)
	}
	MAX-ACCESS	read-only
	STATUS		current
	DESCRIPTION
	       "This object is used to store the status of the Trace Route request.
		   operation. The csOrionTraceRouteResultTable should only be
		   evaluated after this object yields opSuccess(3)."
	::= { csOrionTraceRouteReqEntry 5 }

	csOrionTraceRouteReqRowStatus OBJECT-TYPE
	SYNTAX  RowStatus
	MAX-ACCESS  read-create
	STATUS  current
	DESCRIPTION
		"The RowStatus object for this table.  This is used to
		add/delete rows from this table."
	::= { csOrionTraceRouteReqEntry 6 }

	csOrionTraceRouteResultTable OBJECT-TYPE
	SYNTAX  SEQUENCE OF CsOrionTraceRouteResultEntry
	MAX-ACCESS  not-accessible
	STATUS  current
	DESCRIPTION
		"Trace Route Result Table. The object csOrionTraceRouteReqStatus should
		 be evaluated before obtaing the results from this table."
	::= { csOrionTraceRoute 2 }

    csOrionTraceRouteResultEntry  OBJECT-TYPE
	SYNTAX  CsOrionTraceRouteResultEntry
	MAX-ACCESS  not-accessible
	STATUS  current
	DESCRIPTION
		"An entry of Trace Route Result Table. Each hop taken during the trace 
		route operation corresponds to an entry in csOrionTraceRouteResultEntry.
		Additional 'getnext' is expected to obtain the succeeding hops.
		We will add objects in this table as we expose more trace route info."
	INDEX   { csOrionGlobalVPNIndex, csOrionVPNVRouterIndex, 
			  csOrionTraceRouteResultIndex, csOrionTraceRouteResultHopNum }
	::= { csOrionTraceRouteResultTable 1 }

    CsOrionTraceRouteResultEntry ::=
	SEQUENCE {
	csOrionTraceRouteResultIndex
		Integer32,
	csOrionTraceRouteResultHopNum
		Integer32,
	csOrionTraceRouteResultRtt1
		Integer32,
	csOrionTraceRouteResultRtt2
		Integer32,
	csOrionTraceRouteResultRtt3
		Integer32,
	csOrionTraceRouteResultHopAddr
		IpAddress
	}

	csOrionTraceRouteResultIndex OBJECT-TYPE
	SYNTAX Integer32 (1..2147483647)
	MAX-ACCESS  not-accessible
	STATUS  current
	DESCRIPTION
		"This object identifies a specific File System result entry.
		This index corresponds to the ID provided by NMSs on File System
		request."
	::= { csOrionTraceRouteResultEntry 1 }

	csOrionTraceRouteResultHopNum OBJECT-TYPE
	SYNTAX Integer32 (1..65535)
	MAX-ACCESS	read-only
	STATUS		current
	DESCRIPTION
	    "Hop number for this result."
	::= { csOrionTraceRouteResultEntry 2 }

	csOrionTraceRouteResultRtt1 OBJECT-TYPE
	SYNTAX Integer32 (-1..65535)
	MAX-ACCESS  read-only
	STATUS  current
	DESCRIPTION
		"This is the round trip time for the 1st probe on this hop."
	::= { csOrionTraceRouteResultEntry 3 }

	csOrionTraceRouteResultRtt2 OBJECT-TYPE
	SYNTAX Integer32 (-1..65535)
	MAX-ACCESS  read-only
	STATUS  current
	DESCRIPTION
		"This is the round trip time for the 2nd probe on this hop."
	::= { csOrionTraceRouteResultEntry 4 }

	csOrionTraceRouteResultRtt3 OBJECT-TYPE
	SYNTAX Integer32 (-1..65535)
	MAX-ACCESS  read-only
	STATUS  current
	DESCRIPTION
		"This is the round trip time for the 3rd probe on this hop."
	::= { csOrionTraceRouteResultEntry 5 }

	csOrionTraceRouteResultHopAddr OBJECT-TYPE
	SYNTAX		IpAddress
	MAX-ACCESS	read-only
	STATUS		current
	DESCRIPTION
	    "The host address of this hop."
	::= { csOrionTraceRouteResultEntry 6 }

		

------------------------------------------------------------------------------
--
--	       VPN Virtual Interface table 
--
------------------------------------------------------------------------------



    csOrionVIfaceTable OBJECT-TYPE
	SYNTAX	SEQUENCE OF CsOrionVIfaceEntry
	MAX-ACCESS  not-accessible
	STATUS	current
	DESCRIPTION
	    "A list of Virtual Interfaces, configured for the Virtual Router."
	::= { csOrionVIfInfo 1 }

    csOrionVIfaceEntry OBJECT-TYPE
	SYNTAX 	 CsOrionVIfaceEntry
	MAX-ACCESS  not-accessible
	STATUS	current
	DESCRIPTION
	    "An entry containing management information applicable
	    to a particular virtual router, configured for the VPN."
	INDEX { csOrionGlobalVPNIndex, csOrionVPNVRouterIndex, csOrionVIfIndex }
	::= { csOrionVIfaceTable 1 }

    CsOrionVIfaceEntry ::=
	SEQUENCE {
	csOrionVIfIndex	
		Integer32,
	csOrionVIfRemoteEnd
		DisplayString,
	csOrionVIfIpAddress
		IpAddress,
	csOrionVIfIpMask
		IpAddress,
	csOrionVIfBcastAddr
		INTEGER,
	csOrionVIfMtu
		Integer32,
	csOrionVIfFrameType
		INTEGER,
	csOrionVIfType
		INTEGER,
	csOrionVIfSpeed
		Gauge32,
	csOrionVIfLastChange
		TimeTicks,
	csOrionVIfCryptoMapName
		DisplayString,
	csOrionVIfRowStatus
		RowStatus,
	csOrionVIfOperStatus
		OperStatus,
	csOrionVIfRateLimitNumBytes
		Integer32,
	csOrionVIfRateLimitInterval
		Integer32,
	csOrionVIfRateLimitRate
		Integer32,
	csOrionVIfRateLimitBurstSize
		Integer32,
	csOrionVIfRemIpAddress
		IpAddress,
	csOrionVIfRemIpAddressType
		INTEGER
	}

    csOrionVIfIndex OBJECT-TYPE
	SYNTAX		Integer32 (1..64000)
	MAX-ACCESS	not-accessible
	STATUS		current
	DESCRIPTION
		"A unique value, greater than zero, for each
		VPN Virtual Interface. "
	::= { csOrionVIfaceEntry 1 }

    csOrionVIfRemoteEnd OBJECT-TYPE
 	SYNTAX		DisplayString  (SIZE(0..80))
 	MAX-ACCESS	read-create
	STATUS		current
	DESCRIPTION
	    "This object is used to identify the entity to which
	    this Virtual Interface maps.  That is, the remote end
	    of this Virtual Interface.

	    The format used for this ascii-string valued object is 
	    as follows:
		    'V|L VPNID|SlotID/VRID|PortID/VIID|LLID'

	    Where 'V' indicates the other end of this Virtual Interface
	    is another Virtual Interface.  'L' indicates this Virtual
	    Interface maps to a Logical Link.  'VPNID' is a Virtual
	    Private Network ID.  'SlotID' identifies a specific slot
	    on the Orion Box.  'VRID' is a Virtual Router ID for the
	    VPN specified by VPNID.  'PortID' identifies a specific 
	    Port on the blade installed in the previously identified 
	    slot.  'VIID' is a Virtual Interface on the VR identified
	    by VRID.  'LLID' is a Logical Link ID on PortID.

	    For example, if this Virtual Interface maps to another 
	    Virtual Interface (VI number 1 on VR 1.2.3.4 on VPN 4), 
	    this object might be set to this value:
		    'V 4/1.2.3.4/1'

	    If this Virtual Interface maps to Logical Link 100 on
	    Port 2 of Slot 2, this object might be set to this value:
		    'L 2/2:100'

	    If this Virtual Interface has not been mapped, this object
	    will have the value 'DISCONNECTED'."
	DEFVAL { "DISCONNECTED" }
	::= { csOrionVIfaceEntry 4 }

    csOrionVIfIpAddress OBJECT-TYPE
	SYNTAX		IpAddress
	MAX-ACCESS	read-create
	STATUS		current
	DESCRIPTION
	    "The primary IP Address assigned to this Virtual Interface"
	::= { csOrionVIfaceEntry 5 }

    csOrionVIfIpMask OBJECT-TYPE
	SYNTAX		IpAddress
	MAX-ACCESS	read-create
	STATUS		current
	DESCRIPTION
	    "The primary IP Address Mask assigned to this Virtual Interface"
	::= { csOrionVIfaceEntry 6 }

    csOrionVIfBcastAddr OBJECT-TYPE
	SYNTAX		INTEGER (0..1)
 	MAX-ACCESS	read-create
	STATUS		current
	DESCRIPTION
	    "The value of the least-significant bit in the IP
	    broadcast address used for sending datagrams on
	    this Virtual Interface.  For example, when the
	    Internet standard all-ones broadcast address is
	    used, the value will be 1.  This value applies to
	    both the subnet and network broadcasts addresses
	    used by the entity on this (logical) interface."
	DEFVAL {1}
	::= { csOrionVIfaceEntry 7 }

    csOrionVIfMtu OBJECT-TYPE
	SYNTAX		Integer32 (20..1500)
	MAX-ACCESS	read-create
	STATUS		current
	DESCRIPTION
	    "The size of the largest datagram which can be
	    sent/received on the interface, specified in
	    octets.  For interfaces that are used for
	    transmitting network datagrams, this is the size
	    of the largest network datagram that can be sent
	    on the interface."
	DEFVAL {1500}
	::= { csOrionVIfaceEntry 8 }

    csOrionVIfFrameType OBJECT-TYPE
	SYNTAX		INTEGER {
		frameRelay  (1),
		ppp			(2),
		ipSec	    (3),
		ethernet    (4)
	}
	MAX-ACCESS	read-create
	STATUS		current
	DESCRIPTION
	    "The frame type used on this Virtual Interface."
	::= { csOrionVIfaceEntry 9 }

    csOrionVIfType OBJECT-TYPE
	SYNTAX		INTEGER {
		public  (1),
		private	(2)
	}
	MAX-ACCESS	read-create
	STATUS		current
	DESCRIPTION
	    "This indicates whether this Virtual Interface is of type
	    public or private."
	::= { csOrionVIfaceEntry 10 }

    csOrionVIfSpeed OBJECT-TYPE
	SYNTAX		Gauge32
	MAX-ACCESS	read-create
	STATUS		current
	DESCRIPTION
	    "An estimate of the interface's current bandwidth
	    in bits per second.  If the remote end of this
	    Virtual Interface is a Logical Link, the speed is based
	    on the Logical Link's speed and does not need to be
	    configured.  If the remote end is another Virtual Interface,
	    the speed is based on SLA agreements and needs to be
	    configured.

	    NOTE: This object is currently not supported
	     and will always contain the value 0."
	::= { csOrionVIfaceEntry 11 }

    csOrionVIfLastChange OBJECT-TYPE
	SYNTAX		TimeTicks
	MAX-ACCESS	read-only
	STATUS		current
	DESCRIPTION
	    "The value of sysUpTime at the time the interface
	    entered its current operational state.  If the
	    current state was entered prior to the last re-
	    initialization of the local network management
	    subsystem, then this object contains a zero
	    value."
	::= { csOrionVIfaceEntry 12 }

    csOrionVIfCryptoMapName OBJECT-TYPE
	SYNTAX	DisplayString (SIZE(0..80))
	MAX-ACCESS  read-create
	STATUS	current
	DESCRIPTION
		"A Crypto Map name for the Virtual Interface."
	DEFVAL { "" }
	::= { csOrionVIfaceEntry 13 }

    csOrionVIfRowStatus OBJECT-TYPE
	SYNTAX		RowStatus
	MAX-ACCESS	read-create
	STATUS		current
	DESCRIPTION
		"A row status type for the Virtual Interface."
	::= { csOrionVIfaceEntry 14 }

    csOrionVIfOperStatus OBJECT-TYPE
	SYNTAX		OperStatus
	MAX-ACCESS	read-only
	STATUS		current
	DESCRIPTION
	    "A operational status for the Virtual Iface."
	::= { csOrionVIfaceEntry 15 }

    csOrionVIfRateLimitNumBytes OBJECT-TYPE
	SYNTAX		Integer32
	MAX-ACCESS	read-create
	STATUS		obsolete
	DESCRIPTION
		"The number of bytes that may be forwarded on
		this interface in the interval specified by
		'csOrionVIfRateLimitInterval'.  A value of 0
		indicates that no rate-limiting is done. When
		this field is specified, 'csOrionVIfRateLimit-
		Interval' must also be specified."
	DEFVAL { 0 }
	::= { csOrionVIfaceEntry 16 }

    csOrionVIfRateLimitInterval OBJECT-TYPE
	SYNTAX		Integer32(0..10000)
	MAX-ACCESS	read-create
	STATUS		obsolete
	DESCRIPTION
		"The interval, in milliseconds, over which
		the number of bytes forwared over this interface
		is measured when rate-limiting is being done.
		The rate-limit interval is always a multiple of 10.
		
		This field has no meaning when 'csOrionVIfRate
		LimitNumBytes' is '0'. When 'csOrionVIfRateLimit-
		NumBytes' is specified, this field must also be
		specified."
	DEFVAL { 0 }
	::= { csOrionVIfaceEntry 17 }

    csOrionVIfRateLimitRate OBJECT-TYPE
	SYNTAX		Integer32
	MAX-ACCESS	read-create
	STATUS		current
	DESCRIPTION
		"Long term data throughput, in bytes per second, that
		the VI commits to support under normal network conditions."
	DEFVAL { 0 }
	::={ csOrionVIfaceEntry 18 }

    csOrionVIfRateLimitBurstSize OBJECT-TYPE
	SYNTAX		Integer32
	MAX-ACCESS	read-create
	STATUS		current
	DESCRIPTION
		"The largest burst of data above the commited rate that
		will be allowed temporarily by the VI, even if it exceeds
		the maximum rate. This amount of traffic will be allowed
		only temporarily; on average, the traffice source need
		to be within the committed rate."
	DEFVAL { 0 }
	::={ csOrionVIfaceEntry 19 }
    csOrionVIfRemIpAddress OBJECT-TYPE
		SYNTAX		IpAddress
		MAX-ACCESS	read-create
		STATUS		current
		DESCRIPTION
		    "The remote IP Address assigned to this Virtual Interface"
		::= { csOrionVIfaceEntry 20 }
	csOrionVIfRemIpAddressType OBJECT-TYPE
		SYNTAX		INTEGER {
		other		 (1),
		configured	 (2)
		}
		MAX-ACCESS	read-create
		STATUS		current
		DESCRIPTION
		    "If value is configured, it means csOrionVIfRemIpAddress is configured ,
			 else, it is dynamically learned."
		::= { csOrionVIfaceEntry 21 }

------------------------------------------------------------------------------
--
--	       VPN Virtual Interface Stats table 
--
------------------------------------------------------------------------------

    csOrionViStatsTable OBJECT-TYPE
	SYNTAX	SEQUENCE OF CsOrionViStatsEntry
	MAX-ACCESS  not-accessible
	STATUS	current
	DESCRIPTION
		"A list of Virtual Interfaces Statistics"
	::= { csOrionVIfInfo 2 }

    csOrionViStatsEntry OBJECT-TYPE
	SYNTAX 	 CsOrionViStatsEntry
	MAX-ACCESS  not-accessible
	STATUS	current
	DESCRIPTION
		"A Set of statistics for a single Virtual Interface."
	INDEX { csOrionGlobalVPNIndex, csOrionVPNVRouterIndex, csOrionVIfIndex }
	::= { csOrionViStatsTable 1 }

    CsOrionViStatsEntry ::=
	SEQUENCE {
	csOrionViStatsInOctets
		Counter32,
	csOrionViStatsInUcastPkts
		Counter32,
	csOrionViStatsInNUcastPkts
		Counter32,
	csOrionViStatsInDiscards
		Counter32,
	csOrionViStatsInErrors
		Counter32,
	csOrionViStatsInUnknownProtos
		Counter32,
	csOrionViStatsOutOctets
		Counter32,
	csOrionViStatsOutUcastPkts
		Counter32,
	csOrionViStatsOutNUcastPkts
		Counter32,
	csOrionViStatsOutDiscards
		Counter32,
	csOrionViStatsOutErrors
                Counter32,
        csOrionViStatsRateLimitTxBytesSubmitted
                Counter32,
        csOrionViStatsRateLimitTxPktsSubmitted
                Counter32,
        csOrionViStatsRateLimitTxBytesDropped
                Counter32,
        csOrionViStatsRateLimitTxPktsDropped
                Counter32,
        csOrionViStatsRateLimitRxBytesSubmitted
                Counter32,
        csOrionViStatsRateLimitRxPktsSubmitted
                Counter32,
        csOrionViStatsRateLimitRxBytesDropped
                Counter32,
        csOrionViStatsRateLimitRxPktsDropped
                Counter32,
	csOrionViStatsRateLimitTimeElapsed
		Counter32
	}


    csOrionViStatsInOctets OBJECT-TYPE
	SYNTAX  Counter32
	MAX-ACCESS  read-only
	STATUS  current
	DESCRIPTION
		"The total number of octets received on the
		interface, including framing characters."
	::= { csOrionViStatsEntry 1 }

    csOrionViStatsInUcastPkts OBJECT-TYPE
	SYNTAX  Counter32
	MAX-ACCESS  read-only
	STATUS  current
	DESCRIPTION
		"The number of subnetwork-unicast packets
		delivered to a higher-layer protocol."
	::= { csOrionViStatsEntry 2 }

    csOrionViStatsInNUcastPkts OBJECT-TYPE
	SYNTAX	Counter32
	MAX-ACCESS  read-only
	STATUS	current
	DESCRIPTION
		"The number of packets, delivered by this sub-layer to
		a higher (sub-)layer, which were addressed to a
		non-unicast address at this sub-layer."
	::= { csOrionViStatsEntry 3 }

    csOrionViStatsInDiscards OBJECT-TYPE
	SYNTAX  Counter32
	MAX-ACCESS  read-only
	STATUS  current
	DESCRIPTION
		"The number of inbound packets which were chosen
		to be discarded even though no errors had been
		detected to prevent their being deliverable to a
		higher-layer protocol.  One possible reason for
		discarding such a packet could be to free up
		buffer space."
	::= { csOrionViStatsEntry 4 }

    csOrionViStatsInErrors OBJECT-TYPE
	SYNTAX  Counter32
	MAX-ACCESS  read-only
	STATUS  current
	DESCRIPTION
		"The number of inbound packets that contained
		errors preventing them from being deliverable to a
		higher-layer protocol."
	::= { csOrionViStatsEntry 5 }

    csOrionViStatsInUnknownProtos OBJECT-TYPE
	SYNTAX  Counter32
	MAX-ACCESS  read-only
	STATUS  current
	DESCRIPTION
		"The number of packets received via the interface
		which were discarded because of an unknown or
		unsupported protocol."
	::= { csOrionViStatsEntry 6 }

    csOrionViStatsOutOctets OBJECT-TYPE
	SYNTAX  Counter32
	MAX-ACCESS  read-only
	STATUS  current
	DESCRIPTION
		"The total number of octets transmitted out of the
		interface, including framing characters."
	::= { csOrionViStatsEntry 7 }

    csOrionViStatsOutUcastPkts OBJECT-TYPE
	SYNTAX  Counter32
	MAX-ACCESS  read-only
	STATUS  current
	DESCRIPTION
		"The total number of packets that higher-level
		protocols requested be transmitted to a
		subnetwork-unicast address, including those that
		were discarded or not sent."
	::= { csOrionViStatsEntry 8 }

    csOrionViStatsOutNUcastPkts OBJECT-TYPE
	SYNTAX	Counter32
	MAX-ACCESS  read-only
	STATUS	current
	DESCRIPTION
		"The total number of packets that higher-level
		protocols requested be transmitted, and which were
		addressed to a non-unicast address at this sub-layer,
		including those that were discarded or not sent."
	::= { csOrionViStatsEntry 9 }

    csOrionViStatsOutDiscards OBJECT-TYPE
	SYNTAX  Counter32
	MAX-ACCESS  read-only
	STATUS  current
	DESCRIPTION
		"The number of outbound packets which were chosen
		to be discarded even though no errors had been
		detected to prevent their being transmitted.  One
		possible reason for discarding such a packet  could  
		be to free up buffer space."
	::= { csOrionViStatsEntry 10 }

    csOrionViStatsOutErrors OBJECT-TYPE
	SYNTAX  Counter32
	MAX-ACCESS  read-only
	STATUS  current
	DESCRIPTION
		"The number of outbound packets that could not be
		transmitted because of errors."
	::= { csOrionViStatsEntry 11 }

    csOrionViStatsRateLimitTxBytesSubmitted OBJECT-TYPE
        SYNTAX          Counter32
        MAX-ACCESS      read-only
        STATUS          current
        DESCRIPTION
            "When rate limiting is enabled, the number
            of transmit bytes submitted..."
      ::= { csOrionViStatsEntry 12 }

    csOrionViStatsRateLimitTxPktsSubmitted OBJECT-TYPE
        SYNTAX          Counter32
        MAX-ACCESS      read-only
        STATUS          current
        DESCRIPTION
            "When rate limiting is enabled, the number
            of transmit packets submitted..."
      ::= { csOrionViStatsEntry 13 }

    csOrionViStatsRateLimitTxBytesDropped OBJECT-TYPE
        SYNTAX          Counter32
        MAX-ACCESS      read-only
        STATUS          current
        DESCRIPTION
            "When rate limiting is enabled, the number
            of transmit bytes dropped..."
        ::= { csOrionViStatsEntry 14 }
 
    csOrionViStatsRateLimitTxPktsDropped OBJECT-TYPE
        SYNTAX          Counter32
        MAX-ACCESS      read-only
        STATUS          current
        DESCRIPTION
            "When rate limiting is enabled, the number
            of transmit packets dropped..."
        ::= { csOrionViStatsEntry 15 }
 
    csOrionViStatsRateLimitRxBytesSubmitted OBJECT-TYPE
        SYNTAX          Counter32
        MAX-ACCESS      read-only
        STATUS          current
        DESCRIPTION
            "When rate limiting is enabled, the number
            of receive packets submitted..."
        ::= { csOrionViStatsEntry 16 }
 
    csOrionViStatsRateLimitRxPktsSubmitted OBJECT-TYPE
        SYNTAX          Counter32
        MAX-ACCESS      read-only
        STATUS          current
        DESCRIPTION
            "When rate limiting is enabled, the number
            of receive packets submitted..."
        ::= { csOrionViStatsEntry 17 }
 
    csOrionViStatsRateLimitRxBytesDropped OBJECT-TYPE
        SYNTAX          Counter32
        MAX-ACCESS      read-only
        STATUS          current
        DESCRIPTION
            "When rate limiting is enabled, the number
            of receive packets dropped..."
        ::= { csOrionViStatsEntry 18 }

    csOrionViStatsRateLimitRxPktsDropped OBJECT-TYPE
        SYNTAX          Counter32
        MAX-ACCESS      read-only
        STATUS          current
        DESCRIPTION
            "When rate limiting is enabled, the number
            of receive packets dropped..."
        ::= { csOrionViStatsEntry 19 }

    csOrionViStatsRateLimitTimeElapsed OBJECT-TYPE
        SYNTAX          Counter32
        MAX-ACCESS      read-only
        STATUS          current
        DESCRIPTION
            "The number of seconds that have elapsed since
            the beginning of the current rate-limiting 
            measurement period."
        ::= { csOrionViStatsEntry 20 }


------------------------------------------------------------------------------
--
--	       VPN Virtual Interface GRE Tunnel Config table 
--
------------------------------------------------------------------------------

    csOrionGreConfigTable OBJECT-TYPE
        SYNTAX  SEQUENCE OF CsOrionGreConfigEntry
        MAX-ACCESS  not-accessible
        STATUS  current
        DESCRIPTION
            "The GRE Tunneling configuration table."
        ::= { csOrionVIfInfo 3 }

    csOrionGreConfigEntry OBJECT-TYPE
        SYNTAX   CsOrionGreConfigEntry
        MAX-ACCESS  not-accessible
        STATUS  current
        DESCRIPTION
           "An entry containing configuration information applicable
           to a GRE Tunnel associated with this Virtual Interface."
        INDEX { csOrionGlobalVPNIndex, csOrionVPNVRouterIndex, csOrionVIfIndex }
        ::= { csOrionGreConfigTable 1 }

    CsOrionGreConfigEntry ::=
        SEQUENCE {
        csOrionGreKeyEnable
                INTEGER,
        csOrionGreKey
                Unsigned32,
	csOrionGreSequence
		INTEGER,
	csOrionGreCheckSum
		INTEGER,
	csOrionGreAdminStatus
		INTEGER
	}

    csOrionGreKeyEnable OBJECT-TYPE
	SYNTAX INTEGER {
		enable  (1),
		disable (2)
        }
        MAX-ACCESS      read-create
        STATUS          current
        DESCRIPTION
            "This object is used to enable/disable the GRE Key.
	     When this object is disable, csOrionGreKey has no meaning"
        ::= { csOrionGreConfigEntry 1 }

    csOrionGreKey OBJECT-TYPE
	SYNTAX          Unsigned32 (0..4294967295)
        MAX-ACCESS      read-create
        STATUS          current
        DESCRIPTION
            "The value of a key carried in the GRE header."
        ::= { csOrionGreConfigEntry 2 }

    csOrionGreSequence OBJECT-TYPE
	SYNTAX INTEGER {
		enable  (1),
		disable (2)
        }
        MAX-ACCESS      read-create
        STATUS          current
        DESCRIPTION
            "This object is used to enable/disable the sequencing 
	     info carried in a GRE header."
	DEFVAL  { disable }	
        ::= { csOrionGreConfigEntry 3 }


    csOrionGreCheckSum OBJECT-TYPE
	SYNTAX INTEGER {
		enable  (1),
		disable (2)
        }
        MAX-ACCESS      read-create
        STATUS          current
        DESCRIPTION
            "This object is used to enable/disable the checksum mechanism 
	    for this GRE Tunnel."
	DEFVAL  { disable }	
        ::= { csOrionGreConfigEntry 4 }

    csOrionGreAdminStatus OBJECT-TYPE
	SYNTAX INTEGER {
		enable  (1),
		disable (2)
        }
        MAX-ACCESS      read-create
        STATUS          current
        DESCRIPTION
            "This object controls whether the GRE Tunnel is to be 
	     created or not."
	DEFVAL  { disable }	
        ::= { csOrionGreConfigEntry 5 }

------------------------------------------------------------------------------
--
--	       VPN Virtual Interface GRE Tunnel Stats table 
--
------------------------------------------------------------------------------

    csOrionGreStatsTable OBJECT-TYPE
        SYNTAX  SEQUENCE OF CsOrionGreStatsEntry
        MAX-ACCESS  not-accessible
        STATUS  current
        DESCRIPTION
            "The GRE Tunneling Statistics table."
        ::= { csOrionVIfInfo  4 }

    csOrionGreStatsEntry OBJECT-TYPE
        SYNTAX   CsOrionGreStatsEntry
        MAX-ACCESS  not-accessible
        STATUS  current
        DESCRIPTION
           "An entry containing statistics information applicable
           to a GRE Tunnel associated with this Virtual Interface."
        INDEX { csOrionGlobalVPNIndex, csOrionVPNVRouterIndex, csOrionVIfIndex }
        ::= { csOrionGreStatsTable 1 }

    CsOrionGreStatsEntry ::=
        SEQUENCE {
        csOrionGreStatsKeyErrors
                Counter32,
	csOrionGreStatsSequenceErrors
		Counter32,
	csOrionGreStatsUnknownProto
		Counter32,
	csOrionGreStatsHeaderErrors
		Counter32
	}

    csOrionGreStatsKeyErrors OBJECT-TYPE
        SYNTAX  Counter32
        MAX-ACCESS  read-only
        STATUS  current
        DESCRIPTION
                "The total number of packets with GRE Key errors 
 		 received on this GRE tunnel."
        ::= { csOrionGreStatsEntry 1 }

    csOrionGreStatsSequenceErrors OBJECT-TYPE
        SYNTAX  Counter32
        MAX-ACCESS  read-only
        STATUS  current
        DESCRIPTION
                "The total number of packets with out of sequence 
		 received on this GRE tunnel."
        ::= { csOrionGreStatsEntry 2 }

    csOrionGreStatsUnknownProto OBJECT-TYPE
        SYNTAX  Counter32
        MAX-ACCESS  read-only
        STATUS  current
        DESCRIPTION
                "The number of packets with unknown protocols 
                 received on this GRE tunnel."
        ::= { csOrionGreStatsEntry 3 }

    csOrionGreStatsHeaderErrors OBJECT-TYPE
        SYNTAX  Counter32
        MAX-ACCESS  read-only
        STATUS  current
        DESCRIPTION
                "The total number of packets with header error received
		 on this GRE tunnel."
        ::= { csOrionGreStatsEntry 4 }
------------------------------------------------------------------------------
--
--	       VPN Virtual Router IP table 
--
------------------------------------------------------------------------------



-- the IP generic table

    csOrionVPNVRouterIpStatsTable OBJECT-TYPE
	SYNTAX  SEQUENCE OF CsOrionVPNVRouterIpStatsEntry
	MAX-ACCESS  not-accessible
	STATUS  current
	DESCRIPTION
		"The table of IP related statistics for each Virtual Router."
	::= { csOrionIp 1 }

    csOrionVPNVRouterIpStatsEntry OBJECT-TYPE
	SYNTAX CsOrionVPNVRouterIpStatsEntry
	MAX-ACCESS not-accessible
	STATUS  current
	DESCRIPTION
		"The addressing information for one of this
		Orion's IP addresses."
	INDEX   { csOrionGlobalVPNIndex, csOrionVPNVRouterIndex }
	::= { csOrionVPNVRouterIpStatsTable 1 }

    CsOrionVPNVRouterIpStatsEntry ::=
	SEQUENCE {
	csOrionVPNVRouterIpInReceives
		Counter32,
	csOrionVPNVRouterIpInHdrErrors
		Counter32,
	csOrionVPNVRouterIpInAddrErrors
		Counter32,
	csOrionVPNVRouterIpForwDatagrams
		Counter32,
	csOrionVPNVRouterIpInUnknownProtos
		Counter32,
	csOrionVPNVRouterIpInDiscards
		Counter32,
	csOrionVPNVRouterIpInDelivers
		Counter32,
	csOrionVPNVRouterIpOutRequests
		Counter32,
	csOrionVPNVRouterIpOutDiscards
		Counter32,
	csOrionVPNVRouterIpOutNoRoutes
		Counter32,
	csOrionVPNVRouterIpReasmReqds
		Counter32,
	csOrionVPNVRouterIpReasmOKs
		Counter32,
	csOrionVPNVRouterIpReasmFails
		Counter32,
	csOrionVPNVRouterIpFragOKs
		Counter32,
	csOrionVPNVRouterIpFragFails
		Counter32,
	csOrionVPNVRouterIpFragCreates
		Counter32
	}

    csOrionVPNVRouterIpInReceives OBJECT-TYPE
	SYNTAX  Counter32
	MAX-ACCESS  read-only
	STATUS  current
	DESCRIPTION
		"The total number of input datagrams received from 
		interfaces, including those received in error."
	::= { csOrionVPNVRouterIpStatsEntry 1 }

    csOrionVPNVRouterIpInHdrErrors OBJECT-TYPE
	SYNTAX  Counter32
	MAX-ACCESS  read-only
	STATUS  current
	DESCRIPTION
		"The number of input datagrams discarded due to
		errors in their IP headers, including bad
		checksums, version number mismatch, other format
		errors, time-to-live exceeded, errors discovered
		in processing their IP options, etc."
	::= { csOrionVPNVRouterIpStatsEntry 2 }

    csOrionVPNVRouterIpInAddrErrors OBJECT-TYPE
	SYNTAX  Counter32
	MAX-ACCESS  read-only
	STATUS  current
	DESCRIPTION
		"The number of input datagrams discarded because
		the IP address in their IP header's destination
		field was not a valid address to be received at
		this entity.  This count includes invalid
		addresses (e.g., 0.0.0.0) and addresses of
		unsupported Classes (e.g., Class E).  For entities
		which are not IP Gateways and therefore do not
		forward datagrams, this counter includes datagrams
		discarded because the destination address was not
		a local address."
	::= { csOrionVPNVRouterIpStatsEntry 3 }

    csOrionVPNVRouterIpForwDatagrams OBJECT-TYPE
	SYNTAX  Counter32
	MAX-ACCESS  read-only
	STATUS  current
	DESCRIPTION
		"The number of input datagrams for which this
		entity was not their final IP destination, as a
		result of which an attempt was made to find a
		route to forward them to that final destination.
		In entities which do not act as IP Gateways, this
		Counter32 will include only those packets which were
		Source-Routed via this entity, and the Source-
		Route option processing was successful."
	::= { csOrionVPNVRouterIpStatsEntry 4 }

    csOrionVPNVRouterIpInUnknownProtos OBJECT-TYPE
	SYNTAX  Counter32
	MAX-ACCESS  read-only
	STATUS  current
	DESCRIPTION
		"The number of locally-addressed datagrams
		received successfully but discarded because of an
		unknown or unsupported protocol."
	::= { csOrionVPNVRouterIpStatsEntry 5 }

    csOrionVPNVRouterIpInDiscards OBJECT-TYPE
	SYNTAX  Counter32
	MAX-ACCESS  read-only
	STATUS  current
	DESCRIPTION
		"The number of input IP datagrams for which no
		problems were encountered to prevent their
		continued processing, but which were discarded
		(e.g., for lack of buffer space).  Note that this
		counter does not include any datagrams discarded
		while awaiting re-assembly."
	::= { csOrionVPNVRouterIpStatsEntry 6 }

    csOrionVPNVRouterIpInDelivers OBJECT-TYPE
	SYNTAX  Counter32
	MAX-ACCESS  read-only
	STATUS  current
	DESCRIPTION
		"The total number of input datagrams successfully
		delivered to IP user-protocols (including ICMP)."
	::= { csOrionVPNVRouterIpStatsEntry 7 }

    csOrionVPNVRouterIpOutRequests OBJECT-TYPE
	SYNTAX  Counter32
	MAX-ACCESS  read-only
	STATUS  current
	DESCRIPTION
		"The total number of IP datagrams which local IP
		user-protocols (including ICMP) supplied to IP in
		requests for transmission.  Note that this counter
		does not include any datagrams counted in
		ipForwDatagrams."
	::= { csOrionVPNVRouterIpStatsEntry 8 }

    csOrionVPNVRouterIpOutDiscards OBJECT-TYPE
	SYNTAX  Counter32
	MAX-ACCESS  read-only
	STATUS  current
	DESCRIPTION
		"The number of output IP datagrams for which no
		problem was encountered to prevent their
		transmission to their destination, but which were
		discarded (e.g., for lack of buffer space).  Note
		that this counter would include datagrams counted
		in ipForwDatagrams if any such packets met this
		(discretionary) discard criterion."
	::= { csOrionVPNVRouterIpStatsEntry 9 }

    csOrionVPNVRouterIpOutNoRoutes OBJECT-TYPE
	SYNTAX  Counter32
	MAX-ACCESS  read-only
	STATUS  current
	DESCRIPTION
		"The number of IP datagrams discarded because no
		route could be found to transmit them to their
		destination.  Note that this counter includes any
		packets counted in ipForwDatagrams which meet this
		`no-route' criterion.  Note that this includes any
		datagarms which a host cannot route because all of
		its default gateways are down."
	::= { csOrionVPNVRouterIpStatsEntry 10 }

    csOrionVPNVRouterIpReasmReqds OBJECT-TYPE
	SYNTAX  Counter32
	MAX-ACCESS  read-only
	STATUS  current
	DESCRIPTION
		"The number of IP fragments received which needed
		to be reassembled at this entity."
	::= { csOrionVPNVRouterIpStatsEntry 11 }

    csOrionVPNVRouterIpReasmOKs OBJECT-TYPE
	SYNTAX  Counter32
	MAX-ACCESS  read-only
	STATUS  current
	DESCRIPTION
		"The number of IP datagrams successfully re-
		assembled."

	::= { csOrionVPNVRouterIpStatsEntry 12 }

    csOrionVPNVRouterIpReasmFails OBJECT-TYPE
	SYNTAX  Counter32
	MAX-ACCESS  read-only
	STATUS  current
	DESCRIPTION
		"The number of failures detected by the IP re-
		assembly algorithm (for whatever reason: timed
		out, errors, etc).  Note that this is not
		necessarily a count of discarded IP fragments
		since some algorithms (notably the algorithm in
		RFC 815) can lose track of the number of fragments
		by combining them as they are received."
	::= { csOrionVPNVRouterIpStatsEntry 13 }

    csOrionVPNVRouterIpFragOKs OBJECT-TYPE
	SYNTAX  Counter32
	MAX-ACCESS  read-only
	STATUS  current
	DESCRIPTION
		"The number of IP datagrams that have been
		successfully fragmented at this entity."
	::= { csOrionVPNVRouterIpStatsEntry 14 }

    csOrionVPNVRouterIpFragFails OBJECT-TYPE
	SYNTAX  Counter32
	MAX-ACCESS  read-only
	STATUS  current
	DESCRIPTION
		"The number of IP datagrams that have been
		discarded because they needed to be fragmented at
		this entity but could not be, e.g., because their
		Don't Fragment flag was set."
	::= { csOrionVPNVRouterIpStatsEntry 15 }

    csOrionVPNVRouterIpFragCreates OBJECT-TYPE
	SYNTAX  Counter32
	MAX-ACCESS  read-only
	STATUS  current
	DESCRIPTION
		"The number of IP datagram fragments that have
		been generated as a result of fragmentation at
		this entity."
	::= { csOrionVPNVRouterIpStatsEntry 16 }

------------------------------------------------------------------------------
--
--	       VPN Virtual Router IP address table 
--
------------------------------------------------------------------------------


	 -- The IP address table contains this entity's IP addressing
	 -- information.

    csOrionVPNVRouterIpAddrTable OBJECT-TYPE
	SYNTAX  SEQUENCE OF CsOrionVPNVRouterIpAddrEntry
	MAX-ACCESS  not-accessible
	STATUS  current
	DESCRIPTION
		"The table of addressing information relevant to
		Orion's IP addresses."
	::= { csOrionIp 2 }

    csOrionVPNVRouterIpAddrEntry OBJECT-TYPE
	SYNTAX	 CsOrionVPNVRouterIpAddrEntry
	MAX-ACCESS not-accessible
	STATUS	 current
	DESCRIPTION
		"The addressing information for one of this
		Orion's IP addresses."
	INDEX   { csOrionGlobalVPNIndex, 
		    csOrionVPNVRouterIndex, 
		    csOrionVPNVRouterIpAdEntAddr}
	::= { csOrionVPNVRouterIpAddrTable 1 }

    CsOrionVPNVRouterIpAddrEntry ::=
	SEQUENCE {
		csOrionVPNVRouterIpAdEntAddr
			IpAddress,
		csOrionVPNVRouterIpAdEntIfIndex
			Integer32,
		csOrionVPNVRouterIpAdEntNetMask
			IpAddress,
		csOrionVPNVRouterIpAdEntBcastAddr
			Integer32,
		csOrionVPNVRouterIpAdEntReasmMaxSize
			Integer32,
		csOrionVPNVRouterIpAdEntRowStatus
			RowStatus,
		csOrionVPNVRouterIpAdEntOperStatus
			OperStatus
	}

    csOrionVPNVRouterIpAdEntAddr OBJECT-TYPE
	SYNTAX  IpAddress
 	MAX-ACCESS not-accessible
	STATUS  current
	DESCRIPTION
		"The IP address to which this entry's addressing
		information pertains."
	::= { csOrionVPNVRouterIpAddrEntry 1 }

    csOrionVPNVRouterIpAdEntIfIndex OBJECT-TYPE
	SYNTAX 	 Integer32
	MAX-ACCESS read-only
	STATUS 	 current
	DESCRIPTION
		"The index value which uniquely identifies the
		interface to which this entry is applicable.  The
		interface identified by a particular value of this
		index is the same interface as identified by the
		same value of ifIndex."
	::= { csOrionVPNVRouterIpAddrEntry 2 }

    csOrionVPNVRouterIpAdEntNetMask OBJECT-TYPE
	SYNTAX 	 IpAddress
 	MAX-ACCESS read-create
	STATUS   current
	DESCRIPTION
		"The subnet mask associated with the IP address of
		this entry.  The value of the mask is an IP
		address with all the network bits set to 1 and all
		the hosts bits set to 0."
	::= { csOrionVPNVRouterIpAddrEntry 3 }

    csOrionVPNVRouterIpAdEntBcastAddr OBJECT-TYPE
	SYNTAX 	 Integer32
 	MAX-ACCESS read-create
	STATUS 	 current
	DESCRIPTION
		"The value of the least-significant bit in the IP
		broadcast address used for sending datagrams on
		the (logical) interface associated with the IP
		address of this entry.  For example, when the
		Internet standard all-ones broadcast address is
		used, the value will be 1.  This value applies to
		both the subnet and network broadcasts addresses
		used by the entity on this (logical) interface."
	::= { csOrionVPNVRouterIpAddrEntry 4 }

    csOrionVPNVRouterIpAdEntReasmMaxSize OBJECT-TYPE
	SYNTAX Integer32 (0..65535)
 	MAX-ACCESS read-create
	STATUS   current
	DESCRIPTION
		"The size of the largest IP datagram which this
		entity can re-assemble from incoming IP fragmented
		datagrams received on this interface."
	::= { csOrionVPNVRouterIpAddrEntry 5 }

    csOrionVPNVRouterIpAdEntRowStatus OBJECT-TYPE
	SYNTAX		RowStatus
	MAX-ACCESS	read-create
	STATUS		current
	DESCRIPTION
		"This object is used to add a row to the IP address table."
	::= { csOrionVPNVRouterIpAddrEntry 6 }


    csOrionVPNVRouterIpAdEntOperStatus OBJECT-TYPE
	SYNTAX	OperStatus
	MAX-ACCESS  read-only
	STATUS	current
	DESCRIPTION
		"This object is used to get the current operational 
		status of this row in the IP address table."
	::= { csOrionVPNVRouterIpAddrEntry 7 }


------------------------------------------------------------------------------
--
--	       VPN Virtual Router IP routing table 
--
------------------------------------------------------------------------------



    -- The IP routing table contains an entry for each route
    -- presently known to this entity.

    csOrionVPNVRouterIpRouteTable OBJECT-TYPE
	SYNTAX  SEQUENCE OF CsOrionVPNVRouterIpRouteEntry
	MAX-ACCESS  not-accessible
	STATUS  current
	DESCRIPTION
		"The table of addressing information relevant to
		Orion's IP addresses."
	::= { csOrionIp 3 }

    csOrionVPNVRouterIpRouteEntry OBJECT-TYPE
	SYNTAX CsOrionVPNVRouterIpRouteEntry
 			    MAX-ACCESS not-accessible
	STATUS  current
	DESCRIPTION
		"The addressing information for one of this
		Orion's IP addresses."
	INDEX   { csOrionGlobalVPNIndex,
			csOrionVPNVRouterIndex, 
			csOrionVPNVRouterIpRouteDest,
			csOrionVPNVRouterIpRouteMask,
			csOrionVPNVRouterIpRouteTos,
			csOrionVPNVRouterIpRouteNextHop }

	::= { csOrionVPNVRouterIpRouteTable 1 }

    CsOrionVPNVRouterIpRouteEntry ::=
	SEQUENCE {
	    csOrionVPNVRouterIpRouteDest
			IpAddress,
	    csOrionVPNVRouterIpRouteMask
			IpAddress, 
	    csOrionVPNVRouterIpRouteTos
			Integer32,
	    csOrionVPNVRouterIpRouteNextHop
			IpAddress,
	    csOrionVPNVRouterIpRouteIfIndex
			Integer32,
	    csOrionVPNVRouterIpRouteType
			INTEGER,
	    csOrionVPNVRouterIpRouteProto
			INTEGER,
	    csOrionVPNVRouterIpRouteAge
			Integer32,
	    csOrionVPNVRouterIpRouteInfo
			OBJECT IDENTIFIER,
	    csOrionVPNVRouterIpRouteNextHopAS
			Integer32,
	    csOrionVPNVRouterIpRouteMetric1
 			Integer32,
	    csOrionVPNVRouterIpRouteMetric2
			Integer32,
	    csOrionVPNVRouterIpRouteMetric3
			Integer32,
	    csOrionVPNVRouterIpRouteMetric4
			Integer32,
	    csOrionVPNVRouterIpRouteMetric5
			Integer32,
	    csOrionVPNVRouterIpRouteRowStatus
			RowStatus,
	    csOrionVPNVRouterIpRouteOperStatus
			OperStatus
	}

    csOrionVPNVRouterIpRouteDest OBJECT-TYPE
	SYNTAX  IpAddress
	MAX-ACCESS  not-accessible
	STATUS  current
	DESCRIPTION
		"The destination IP address of this route.  An
		entry with a value of 0.0.0.0 is considered a
		default route.  Multiple routes to a single
		destination can appear in the table, but access to
		such multiple entries is dependent on the table-
		access mechanisms defined by the network
		management protocol in use."
	::= { csOrionVPNVRouterIpRouteEntry 1 }

    csOrionVPNVRouterIpRouteMask OBJECT-TYPE
	SYNTAX  IpAddress
	MAX-ACCESS  not-accessible
	STATUS  current
	DESCRIPTION
		"Indicate the mask to be logical-ANDed with the
		destination address before being compared to the
		value in the csOrionVPNVRouterIpRouteDest field.  For those systems
		that do not support arbitrary subnet masks, an
		agent constructs the value of the csOrionVPNVRouterIpRouteMask by
		determining whether the value of the correspondent
		csOrionVPNVRouterIpRouteDest field belong to a class-A, B, or C
		network, and then using one of:

		       mask	   network
		       255.0.0.0	class-A
		       255.255.0.0    class-B
		       255.255.255.0  class-C
		If the value of the csOrionVPNVRouterIpRouteDest is 0.0.0.0 (a
		default route), then the mask value is also
		0.0.0.0.  It should be noted that all IP routing
		subsystems implicitly use this mechanism."
	::= { csOrionVPNVRouterIpRouteEntry 2 }

    csOrionVPNVRouterIpRouteTos OBJECT-TYPE
	SYNTAX Integer32
	MAX-ACCESS not-accessible
	STATUS   current
	DESCRIPTION
		"The policy specifier is the IP TOS Field.  The encoding
		of IP TOS is as specified  by  the  following convention.
		Zero indicates the default path if no more  specific
		policy applies.

		+-----+-----+-----+-----+-----+-----+-----+-----+
		|		 |	                    |     |
		|   PRECEDENCE    |    TYPE OF SERVICE    |  0  |
		|		 |	                    |     |
		+-----+-----+-----+-----+-----+-----+-----+-----+

				IP TOS	            IP TOS
			 Field     Policy	Field     Policy
			 Contents    Code	Contents    Code
			 0 0 0 0  ==>   0	0 0 0 1  ==>   2
			 0 0 1 0  ==>   4	0 0 1 1  ==>   6
			 0 1 0 0  ==>   8	0 1 0 1  ==>  10
			 0 1 1 0  ==>  12	0 1 1 1  ==>  14
			 1 0 0 0  ==>  16	1 0 0 1  ==>  18
			 1 0 1 0  ==>  20	1 0 1 1  ==>  22
			 1 1 0 0  ==>  24	1 1 0 1  ==>  26
			 1 1 1 0  ==>  28	1 1 1 1  ==>  30"
	    ::= { csOrionVPNVRouterIpRouteEntry 3 } 

    csOrionVPNVRouterIpRouteNextHop OBJECT-TYPE
	SYNTAX  IpAddress
	MAX-ACCESS  not-accessible
	STATUS  current
	DESCRIPTION
		"The IP address of the next hop of this route.
		(In the case of a route bound to an interface
		which is realized via a broadcast media, the value
		of this field is the agent's IP address on that
		interface.)"
	::= { csOrionVPNVRouterIpRouteEntry 4 }

    csOrionVPNVRouterIpRouteIfIndex OBJECT-TYPE
	SYNTAX Integer32
	MAX-ACCESS  read-create
	STATUS  current
	DESCRIPTION
		"The index value which uniquely identifies the
		local interface through which the next hop of this
		route should be reached.  The interface identified
		by a particular value of this index is the same
		interface as identified by the same value of
		ifIndex."
	::= { csOrionVPNVRouterIpRouteEntry 5 }

    csOrionVPNVRouterIpRouteType OBJECT-TYPE
	SYNTAX   INTEGER {
		other    (1), -- not specified by this MIB
		reject   (2), -- route which discards traffic
		local    (3), -- local interface
		remote   (4)  -- remote destination
	}
	MAX-ACCESS read-create
	STATUS   current
	DESCRIPTION
		"The type of route.  Note that local(3)  refers
		to  a route for which the next hop is the final
		destination; remote(4) refers to  a  route  for
		which  the  next  hop is not the final destina-
		tion.

		Routes which do not result in traffic forwarding or
		rejection should not be displayed even if the
		implementation keeps them stored internally.

		reject (2) refers to a route which, if matched, discards
		the message as unreachable. This is used in some
		protocols as a means of correctly aggregating routes."
		::= { csOrionVPNVRouterIpRouteEntry 6 }

    csOrionVPNVRouterIpRouteProto OBJECT-TYPE
	SYNTAX  INTEGER {
		other     (1),  -- not specified
		local     (2),  -- local interface
		netmgmt   (3),  -- static route
		icmp	(4),  -- result of ICMP Redirect
		
		-- the following are all dynamic
		-- routing protocols
		
		egp	(5),  -- Exterior Gateway Protocol, not supported
		ggp	(6),  -- Gateway-Gateway Protocol
		hello	(7),  -- FuzzBall HelloSpeak
		rip	(8),  -- Berkeley RIP or RIP-II
		isIs	(9),  -- Dual IS-IS
		esIs	(10), -- ISO 9542
		ciscoIgrp  (11), -- Cisco IGRP
		bbnSpfIgp  (12), -- BBN SPF IGP
		ospf	(13), -- Open Shortest Path First
		bgp	(14), -- Border Gateway Protocol
		idpr	(15), -- InterDomain Policy Routing
		ciscoEigrp (16)  -- Cisco EIGRP
	}
	MAX-ACCESS  read-only
	STATUS  current
	DESCRIPTION
		"The routing mechanism via which this route was
		learned.  Inclusion of values for gateway routing
		protocols is not intended to imply that hosts
		should support those protocols."
	::= { csOrionVPNVRouterIpRouteEntry 7 }

    csOrionVPNVRouterIpRouteAge OBJECT-TYPE
	SYNTAX Integer32
	MAX-ACCESS  read-only
	STATUS  current
	DESCRIPTION
		"The number of seconds since this route was last
		updated or otherwise determined to be correct.
		Note that no semantics of `too old' can be implied
		except through knowledge of the routing protocol
		by which the route was learned."
	::= { csOrionVPNVRouterIpRouteEntry 8 }

    csOrionVPNVRouterIpRouteInfo OBJECT-TYPE
	SYNTAX  OBJECT IDENTIFIER
	MAX-ACCESS  read-create
	STATUS  current
	DESCRIPTION
		"A reference to MIB definitions specific to the
		particular routing protocol which is responsible
		for this route, as determined by the value
		specified in the route's csOrionVPNVRouterIpRouteProto value.  If
		this information is not present, its value should
		be set to the OBJECT IDENTIFIER { 0 0 }, which is
		a syntatically valid object identifier, and any
		conformant implementation of ASN.1 and BER must be
		able to generate and recognize this value."
	::= { csOrionVPNVRouterIpRouteEntry 9 }

    csOrionVPNVRouterIpRouteNextHopAS OBJECT-TYPE
	SYNTAX   Integer32
	MAX-ACCESS read-create
	STATUS   current
	DESCRIPTION
		"The Autonomous System Number of the Next  Hop.
		The  semantics of this object are determined by
		the routing-protocol specified in  the  route's
		ipCidrRouteProto  value. When  this object is
		unknown or not relevant its value should be set
		to zero."
	DEFVAL { 0 }
	::= { csOrionVPNVRouterIpRouteEntry 10 }

    csOrionVPNVRouterIpRouteMetric1 OBJECT-TYPE
	SYNTAX Integer32
	MAX-ACCESS  read-create
	STATUS  current
	DESCRIPTION
		"The primary routing metric for this route.  The
		semantics of this metric are determined by the
		routing-protocol specified in the route's
		csOrionVPNVRouterIpRouteProto value.  If this metric is not used,
		its value should be set to -1."
	::= { csOrionVPNVRouterIpRouteEntry 11 }

    csOrionVPNVRouterIpRouteMetric2 OBJECT-TYPE
	SYNTAX Integer32
	MAX-ACCESS  read-create
	STATUS  current
	DESCRIPTION
		"An alternate routing metric for this route.  The
		semantics of this metric are determined by the
		routing-protocol specified in the route's
		csOrionVPNVRouterIpRouteProto value.  If this metric is not used,
		its value should be set to -1."
	::= { csOrionVPNVRouterIpRouteEntry 12 }

    csOrionVPNVRouterIpRouteMetric3 OBJECT-TYPE
	SYNTAX Integer32
	MAX-ACCESS  read-create
	STATUS  current
	DESCRIPTION
		"An alternate routing metric for this route.  The
		semantics of this metric are determined by the
		routing-protocol specified in the route's
		csOrionVPNVRouterIpRouteProto value.  If this metric is not used,
		its value should be set to -1."
	::= { csOrionVPNVRouterIpRouteEntry 13 }

    csOrionVPNVRouterIpRouteMetric4 OBJECT-TYPE
	SYNTAX  Integer32
	MAX-ACCESS  read-create
	STATUS  current
	DESCRIPTION
		"An alternate routing metric for this route.  The
		semantics of this metric are determined by the
		routing-protocol specified in the route's
		csOrionVPNVRouterIpRouteProto value.  If this metric is not used,
		its value should be set to -1."
	::= { csOrionVPNVRouterIpRouteEntry 14 }

    csOrionVPNVRouterIpRouteMetric5 OBJECT-TYPE
	SYNTAX Integer32
	MAX-ACCESS  read-create
	STATUS  current
	DESCRIPTION
		"An alternate routing metric for this route.  The
		semantics of this metric are determined by the
		routing-protocol specified in the route's
		csOrionVPNVRouterIpRouteProto value.  If this metric is not used,
		its value should be set to -1."
	::= { csOrionVPNVRouterIpRouteEntry 15 }

    csOrionVPNVRouterIpRouteRowStatus OBJECT-TYPE
	SYNTAX	RowStatus
	MAX-ACCESS  read-create
	STATUS	current
	DESCRIPTION
		"A row status type for the VPN Virtual Router."
	::= { csOrionVPNVRouterIpRouteEntry 16 }


    csOrionVPNVRouterIpRouteOperStatus OBJECT-TYPE
	SYNTAX	OperStatus
	MAX-ACCESS  read-only
	STATUS	current
	DESCRIPTION
		"A operational status for the Virtual Router of the VPN."
	::= { csOrionVPNVRouterIpRouteEntry 17 }



------------------------------------------------------------------------------
--
--	       VPN Virtual Router IP Address Translation Table
--
------------------------------------------------------------------------------

    csOrionVPNVRouterIpNetToMediaTable OBJECT-TYPE
	SYNTAX  SEQUENCE OF CsOrionVPNVRouterIpNetToMediaEntry
	MAX-ACCESS  not-accessible
	STATUS  current
	DESCRIPTION
		"The table of addressing information relevant to
		Orion's IP addresses."
    ::= { csOrionIp 4 }

    csOrionVPNVRouterIpNetToMediaEntry OBJECT-TYPE
	SYNTAX CsOrionVPNVRouterIpNetToMediaEntry
 		MAX-ACCESS not-accessible
	STATUS  current
	DESCRIPTION
		"The addressing information for one of this
		Orion's IP addresses."
	INDEX   { csOrionGlobalVPNIndex,
		    csOrionVPNVRouterIndex,
		    csOrionVPNVRouterIpNetToMediaIfIndex,
 		    csOrionVPNVRouterIpNetToMediaNetAddress }
	::= { csOrionVPNVRouterIpNetToMediaTable 1 }

    CsOrionVPNVRouterIpNetToMediaEntry ::=
	SEQUENCE {
	       csOrionVPNVRouterIpNetToMediaIfIndex
 			Integer32,
	       csOrionVPNVRouterIpNetToMediaPhysAddress
			PhysAddress,
	       csOrionVPNVRouterIpNetToMediaNetAddress
			IpAddress,
	       csOrionVPNVRouterIpNetToMediaType
 			INTEGER
	}

    csOrionVPNVRouterIpNetToMediaIfIndex OBJECT-TYPE
	SYNTAX  Integer32
	MAX-ACCESS  not-accessible
	STATUS  current
	DESCRIPTION
		"The interface on which this entry's equivalence
		is effective.  The interface identified by a
		particular value of this index is the same
		interface as identified by the same value of
		ifIndex."
	::= { csOrionVPNVRouterIpNetToMediaEntry 1 }

    csOrionVPNVRouterIpNetToMediaPhysAddress OBJECT-TYPE
	SYNTAX  PhysAddress
	MAX-ACCESS  read-create
	STATUS  current
	DESCRIPTION
		"The media-dependent `physical' address."
	::= { csOrionVPNVRouterIpNetToMediaEntry 2 }


    csOrionVPNVRouterIpNetToMediaNetAddress OBJECT-TYPE
	SYNTAX  IpAddress
	MAX-ACCESS  not-accessible
	STATUS  current
	DESCRIPTION
		"The IpAddress corresponding to the media-
		dependent `physical' address."
	::= { csOrionVPNVRouterIpNetToMediaEntry 3 }

    csOrionVPNVRouterIpNetToMediaType OBJECT-TYPE
	SYNTAX  INTEGER {
		      other(1),	-- none of the following
		      invalid(2),	-- an invalidated mapping
		      dynamic(3),
		      static(4)
		}
	MAX-ACCESS  read-create
	STATUS  current
	DESCRIPTION
		"The type of mapping.

		Setting this object to the value invalid(2) has
		the effect of invalidating the corresponding entry
		in the csOrionVPNVRouterIpNetToMediaTable.  That is, it effectively
		dissasociates the interface identified with said
		entry from the mapping identified with said entry.
		It is an implementation-specific matter as to
		whether the agent removes an invalidated entry
		from the table.  Accordingly, management stations
		must be prepared to receive tabular information
		from agents that corresponds to entries not
		currently in use.  Proper interpretation of such
		entries requires examination of the relevant
		csOrionVPNVRouterIpNetToMediaType object."
	::= { csOrionVPNVRouterIpNetToMediaEntry 4 }

------------------------------------------------------------------------------
--
--	       VPN Virtual Router IP Local Address Pool Table
--
------------------------------------------------------------------------------

    csOrionIpLocalAddrPoolTable OBJECT-TYPE
	SYNTAX  SEQUENCE OF CsOrionIpLocalAddrPoolEntry
	MAX-ACCESS  not-accessible
	STATUS  current
	DESCRIPTION
		"This table contains pools of IP addresses.  Clients can
		dynamically take addresses from a pool as they need them
		(and return them when finished)."
    ::= { csOrionIp 5 }

    csOrionIpLocalAddrPoolEntry OBJECT-TYPE
	SYNTAX CsOrionIpLocalAddrPoolEntry
	MAX-ACCESS not-accessible
	STATUS  current
	DESCRIPTION
		"Each entry represents a single pool of IP addresses."
	INDEX   { csOrionGlobalVPNIndex, csOrionVPNVRouterIndex,
 		    csOrionIpLocalAddrPoolName }
	::= { csOrionIpLocalAddrPoolTable 1 }

    CsOrionIpLocalAddrPoolEntry ::=
	SEQUENCE {
	       csOrionIpLocalAddrPoolName
 			DisplayString,
	       csOrionIpLocalAddrPoolStartRange
			IpAddress,
	       csOrionIpLocalAddrPoolEndRange
			IpAddress,
	       csOrionIpLocalAddrPoolRowStatus
 			RowStatus
	}

    csOrionIpLocalAddrPoolName OBJECT-TYPE
	SYNTAX  DisplayString (SIZE(1..80))
	MAX-ACCESS  not-accessible
	STATUS  current
	DESCRIPTION
		"The name of this address pool.  This is used
		to identify a specific address pool."
	::= { csOrionIpLocalAddrPoolEntry 1 }

    csOrionIpLocalAddrPoolStartRange OBJECT-TYPE
	SYNTAX  IpAddress
	MAX-ACCESS  read-create
	STATUS  current
	DESCRIPTION
		"The start of the range of IP addresses in this pool."
	::= { csOrionIpLocalAddrPoolEntry 2 }


    csOrionIpLocalAddrPoolEndRange OBJECT-TYPE
	SYNTAX  IpAddress
	MAX-ACCESS  read-create
	STATUS  current
	DESCRIPTION
		"The end of the range of IP addresses in this pool."
	::= { csOrionIpLocalAddrPoolEntry 3 }

    csOrionIpLocalAddrPoolRowStatus OBJECT-TYPE
	SYNTAX  RowStatus
	MAX-ACCESS  read-create
	STATUS  current
	DESCRIPTION
		"The RowStatus object for this table."
	::= { csOrionIpLocalAddrPoolEntry 4 }

------------------------------------------------------------------------------
--
--             VPN Virtual Router Managed (Static and other) IP Routes Table 
--
------------------------------------------------------------------------------

    -- The Managed Route table contains entries for all routes
    -- know to the system through management. These routes are
    -- are all those which are not owned/learned by dynamic
    -- routing protocols or the interface routes. These routes 
    -- are managed by the CoSine IP Routing object which interfaces 
    -- with the IP Routing/Fowarding table (FIB).

    csOrionVPNVRouterManagedIpRouteTable OBJECT-TYPE
        SYNTAX  SEQUENCE OF CsOrionVPNVRouterManagedIpRouteEntry
        MAX-ACCESS  not-accessible
        STATUS  current
        DESCRIPTION
                "The table of addressing information relevant to
                Orion's managed IP addresses."
        ::= { csOrionIp 6 }

    csOrionVPNVRouterManagedIpRouteEntry OBJECT-TYPE
        SYNTAX CsOrionVPNVRouterManagedIpRouteEntry
        MAX-ACCESS not-accessible
        STATUS  current
        DESCRIPTION
                "The addressing information for one of this
                Orion's managed IP addresses."
        INDEX   { csOrionGlobalVPNIndex,
                  csOrionVPNVRouterIndex, 
                  csOrionVPNVRouterManagedIpRouteOwner, 
                  csOrionVPNVRouterManagedIpRouteDest,
                  csOrionVPNVRouterManagedIpRouteMask,
                  csOrionVPNVRouterManagedIpRouteTos,
                  csOrionVPNVRouterManagedIpRouteNextHop, 
                  csOrionVPNVRouterManagedIpRouteIfIndex }

        ::= { csOrionVPNVRouterManagedIpRouteTable 1 }

    CsOrionVPNVRouterManagedIpRouteEntry ::=
        SEQUENCE {
	    csOrionVPNVRouterManagedIpRouteOwner
			INTEGER,
            csOrionVPNVRouterManagedIpRouteDest
                        IpAddress,
            csOrionVPNVRouterManagedIpRouteMask
                        IpAddress, 
            csOrionVPNVRouterManagedIpRouteTos
                        Integer32,
            csOrionVPNVRouterManagedIpRouteNextHop
                        IpAddress,
            csOrionVPNVRouterManagedIpRouteIfIndex
                        Integer32,
            csOrionVPNVRouterManagedIpRouteType
                        INTEGER,
            csOrionVPNVRouterManagedIpRouteProto
                        INTEGER,
            csOrionVPNVRouterManagedIpRouteAge
                        Integer32,
            csOrionVPNVRouterManagedIpRouteInfo
                        OBJECT IDENTIFIER,
            csOrionVPNVRouterManagedIpRouteNextHopAS
                        Integer32,
            csOrionVPNVRouterManagedIpRouteMetric1
                        Integer32,
            csOrionVPNVRouterManagedIpRouteMetric2
                        Integer32,
            csOrionVPNVRouterManagedIpRouteMetric3
                        Integer32,
            csOrionVPNVRouterManagedIpRouteMetric4
                        Integer32,
            csOrionVPNVRouterManagedIpRouteMetric5
                        Integer32,
            csOrionVPNVRouterManagedIpRoutePreference1
                        Integer32,
            csOrionVPNVRouterManagedIpRoutePreference2
                        Integer32,
            csOrionVPNVRouterManagedIpRouteColor1
                        Integer32,
            csOrionVPNVRouterManagedIpRouteColor2
                        Integer32,
            csOrionVPNVRouterManagedIpRouteActiveOption
                        INTEGER,
            csOrionVPNVRouterManagedIpRouteInstallOption
                        INTEGER,
            csOrionVPNVRouterManagedIpRouteAdvertiseOption
                        INTEGER,
            csOrionVPNVRouterManagedIpRouteRetainOption
                        INTEGER,
		    csOrionVPNVRouterManagedIpRouteRowStatus
                        RowStatus,
            csOrionVPNVRouterManagedIpRouteOperState
                        OperState

-- add Tag option
-- add AS Path options
-- add Community options

        }
	csOrionVPNVRouterManagedIpRouteOwner OBJECT-TYPE
        SYNTAX  INTEGER {
                other			 (1),  -- unspecified
				static			 (2),  -- static route
                aggregate        (3),  -- aggregate routes 
                generated        (4),  -- generated routes 
				rib				 (5),  -- routing information base 
				fib				 (6)  -- forwarding information base
                
        }
        MAX-ACCESS  not-accessible
        STATUS  current
        DESCRIPTION
                "The owner/manager of this route. 
				The well known route examples for managed routes are
                static and generated route managers which
                manage the routes of the respective types."
		::= { csOrionVPNVRouterManagedIpRouteEntry 1 }

    csOrionVPNVRouterManagedIpRouteDest OBJECT-TYPE
        SYNTAX  IpAddress
        MAX-ACCESS  not-accessible
        STATUS  current
        DESCRIPTION
                "The destination IP address of this route.  An
                entry with a value of 0.0.0.0 is considered a
                default route.  Multiple routes to a single
                destination can appear in the table, but access to
                such multiple entries is dependent on the table-
                access mechanisms defined by the network
                management protocol in use."
        ::= { csOrionVPNVRouterManagedIpRouteEntry 2 }

    csOrionVPNVRouterManagedIpRouteMask OBJECT-TYPE
        SYNTAX  IpAddress
        MAX-ACCESS  not-accessible
        STATUS  current
        DESCRIPTION
                "Indicate the mask to be logical-ANDed with the
                destination address before being compared to the
                value in the csOrionVPNVRouterManagedIpRouteDest field.  
                For those systems that do not support arbitrary subnet masks, 
                an agent constructs the value of the 
                csOrionVPNVRouterManagedIpRouteMask by determining whether the 
                value of the correspondent csOrionVPNVRouterManagedIpRouteDest 
                field belong to a class-A, B, or C network, and then using one 
                of:

                       mask        network
                       255.0.0.0      class-A
                       255.255.0.0    class-B
                       255.255.255.0  class-C
                If the value of the csOrionVPNVRouterManagedIpRouteDest is 
                0.0.0.0 (a default route), then the mask value is also
                0.0.0.0.  It should be noted that all IP routing
                subsystems implicitly use this mechanism."
        ::= { csOrionVPNVRouterManagedIpRouteEntry 3 }

    csOrionVPNVRouterManagedIpRouteTos OBJECT-TYPE
        SYNTAX Integer32
        MAX-ACCESS not-accessible
        STATUS   current
        DESCRIPTION
                "The policy specifier is the IP TOS Field.  The encoding
                of IP TOS is as specified  by  the  following convention.
                Zero indicates the default path if no more  specific
                policy applies.

                +-----+-----+-----+-----+-----+-----+-----+-----+
                |                |                          |     |
                |   PRECEDENCE    |    TYPE OF SERVICE    |  0  |
                |                |                          |     |
                +-----+-----+-----+-----+-----+-----+-----+-----+

                                IP TOS              IP TOS
                         Field     Policy       Field     Policy
                         Contents    Code       Contents    Code
                         0 0 0 0  ==>   0       0 0 0 1  ==>   2
                         0 0 1 0  ==>   4       0 0 1 1  ==>   6
                         0 1 0 0  ==>   8       0 1 0 1  ==>  10
                         0 1 1 0  ==>  12       0 1 1 1  ==>  14
                         1 0 0 0  ==>  16       1 0 0 1  ==>  18
                         1 0 1 0  ==>  20       1 0 1 1  ==>  22
                         1 1 0 0  ==>  24       1 1 0 1  ==>  26
                         1 1 1 0  ==>  28       1 1 1 1  ==>  30"
            ::= { csOrionVPNVRouterManagedIpRouteEntry 4 } 

    csOrionVPNVRouterManagedIpRouteNextHop OBJECT-TYPE
        SYNTAX  IpAddress
        MAX-ACCESS  not-accessible
        STATUS  current
        DESCRIPTION
                "The IP address of the next hop of this route.
                (In the case of a route bound to an interface
                which is realized via a broadcast media, the value
                of this field is the agent's IP address on that
                interface.)"
        ::= { csOrionVPNVRouterManagedIpRouteEntry 5 }

    csOrionVPNVRouterManagedIpRouteIfIndex OBJECT-TYPE
        SYNTAX Integer32
        MAX-ACCESS  not-accessible
        STATUS  current
        DESCRIPTION
                "The index value which uniquely identifies the
                local interface through which the next hop of this
                route should be reached.  The interface identified
                by a particular value of this index is the same
                interface as identified by the same value of
                ifIndex."
        ::= { csOrionVPNVRouterManagedIpRouteEntry 6 }

    csOrionVPNVRouterManagedIpRouteType OBJECT-TYPE
        SYNTAX   INTEGER {
                other      (1), -- not specified by this MIB
                reject     (2), -- route which discards traffic and sends icmp
                local      (3), -- local interface
                remote     (4),  -- remote destination
                discard    (1001),  -- route which discards traffic; no icmp sent
                receive    (1002)  -- use for receive only 
        }
        MAX-ACCESS read-create
        STATUS   current
        DESCRIPTION
                "The type of route.  Note that local(3)  refers
                to  a route for which the next hop is the final
                destination; remote(4) refers to  a  route  for
                which  the  next  hop is not the final destina-
                tion.

                reject (2) refers to a route which, if matched, discards
                the message as unreachable. An ICMP unreachable message is 
                sent to the originator of the packet. 
                discard (1001) refers to the case where an ICMP message 
                is not sent to the originator. These route types are used 
                by protocols as a means of correctly aggregating routes."
                ::= { csOrionVPNVRouterManagedIpRouteEntry 7 }

    csOrionVPNVRouterManagedIpRouteProto OBJECT-TYPE
        SYNTAX  INTEGER {
                other			(1),  -- not specified
                netmgmt			(3),  -- static route
                local           (2),  -- local interface
                icmp            (4),  -- result of ICMP Redirect
                egp             (5),  -- Exterior Gateway Protocol, not supported
				
				-- the following are all dynamic
				-- routing protocols
		
                ggp             (6),  -- Gateway-Gateway Protocol
                hello           (7),  -- FuzzBall HelloSpeak
                rip             (8),  -- Berkeley RIP or RIP-II
                isIs            (9),  -- Dual IS-IS
                esIs            (10), -- ISO 9542
                ciscoIgrp       (11), -- Cisco IGRP
                bbnSpfIgp       (12), -- BBN SPF IGP
                ospf            (13), -- Open Shortest Path First
                bgp             (14), -- Border Gateway Protocol
                idpr            (15), -- InterDomain Policy Routing
                ciscoEigrp      (16)  -- Cisco EIGRP
        }
        MAX-ACCESS  read-only
        STATUS  current
        DESCRIPTION
			"The routing mechanism via which this route was
		learned.  Inclusion of values for gateway routing
		protocols is not intended to imply that hosts
		should support those protocols."
        ::= { csOrionVPNVRouterManagedIpRouteEntry 8 }

    csOrionVPNVRouterManagedIpRouteAge OBJECT-TYPE
        SYNTAX  Integer32 
        MAX-ACCESS  read-only
        STATUS  current
        DESCRIPTION
               "If the route is added to the routing table, this field
                indicates the number of seconds  since  this  route  was
                last  updated  or  otherwise  determined  to be
                correct.  Note that no semantics of  `too  old'
                can  be implied except through knowledge of the
                routing  protocol  by  which  the   route   was
                learned."
        DEFVAL  { 0 }
        ::= { csOrionVPNVRouterManagedIpRouteEntry 9 }

    csOrionVPNVRouterManagedIpRouteInfo OBJECT-TYPE
        SYNTAX   OBJECT IDENTIFIER
        MAX-ACCESS read-create
        STATUS   current
        DESCRIPTION
                "A reference to MIB definitions specific to the
                particular  routing protocol/owner which is responsi-
                ble for this route, as determined by the  value
                specified  in the route's ipCidrRouteProto value.
                If this information is not present,  its  value
                should be set to the OBJECT IDENTIFIER { 0 0 },
                which is a syntactically valid object  identif-
                ier, and any implementation conforming to ASN.1
                and the Basic Encoding Rules must  be  able  to
                generate and recognize this value."
        ::= { csOrionVPNVRouterManagedIpRouteEntry 10 }

    csOrionVPNVRouterManagedIpRouteNextHopAS OBJECT-TYPE
        SYNTAX   Integer32
        MAX-ACCESS read-create
        STATUS   current
        DESCRIPTION
                "The Autonomous System Number of the Next Hop.
                The  semantics of this object are determined by
                the routing-protocol specified in  the  route's
                csOrionVPNVRouterManagedIpRouteProto  value. When  
                this object is unknown or not relevant its value 
                should be set to zero."
        DEFVAL { 0 }
        ::= { csOrionVPNVRouterManagedIpRouteEntry 11 }

    csOrionVPNVRouterManagedIpRouteMetric1 OBJECT-TYPE
        SYNTAX Integer32
        MAX-ACCESS  read-create
        STATUS  current
        DESCRIPTION
                "The primary routing  metric  for  this  route.
                The  semantics of this metric are determined by
                the routing-protocol/owner specified in  the  route's
                csOrionVPNVRouterManagedIpRouteProto value.   
                If  this metric is not used, its value should be set to -1."
        ::= { csOrionVPNVRouterManagedIpRouteEntry 12 }

    csOrionVPNVRouterManagedIpRouteMetric2 OBJECT-TYPE
        SYNTAX Integer32
        MAX-ACCESS  read-create
        STATUS  current
        DESCRIPTION
                "An alternate routing metric for this route.  The
                semantics of this metric are determined by the
                routing-protocol specified in the route's
                csOrionVPNVRouterManagedIpRouteProto value.  
                If this metric is not used,
                its value should be set to -1."
        ::= { csOrionVPNVRouterManagedIpRouteEntry 13 }

    csOrionVPNVRouterManagedIpRouteMetric3 OBJECT-TYPE
        SYNTAX Integer32
        MAX-ACCESS  read-create
        STATUS  current
        DESCRIPTION
                "An alternate routing metric for this route.  The
                semantics of this metric are determined by the
                routing-protocol specified in the route's
                csOrionVPNVRouterManagedIpRouteProto value.  
                If this metric is not used,
                its value should be set to -1."
        ::= { csOrionVPNVRouterManagedIpRouteEntry 14 }

    csOrionVPNVRouterManagedIpRouteMetric4 OBJECT-TYPE
        SYNTAX  Integer32
        MAX-ACCESS  read-create
        STATUS  current
        DESCRIPTION
                "An alternate routing metric for this route.  The
                semantics of this metric are determined by the
                routing-protocol specified in the route's
                csOrionVPNVRouterManagedIpRouteProto value.  
                If this metric is not used,
                its value should be set to -1."
        ::= { csOrionVPNVRouterManagedIpRouteEntry 15 }

    csOrionVPNVRouterManagedIpRouteMetric5 OBJECT-TYPE
        SYNTAX Integer32
        MAX-ACCESS  read-create
        STATUS  current
        DESCRIPTION
                "An alternate routing metric for this route.  The
                semantics of this metric are determined by the
                routing-protocol specified in the route's
                csOrionVPNVRouterManagedIpRouteProto value.  
                If this metric is not used,
                its value should be set to -1."
        ::= { csOrionVPNVRouterManagedIpRouteEntry 16 }

    csOrionVPNVRouterManagedIpRoutePreference1 OBJECT-TYPE
        SYNTAX Integer32
        MAX-ACCESS  read-create
        STATUS  current
        DESCRIPTION
                "The primary preference value for this route. 
                 The route preference value which is also referred to
                 as the Adminstrative Distance is used for selecting
                 a route when multiple routes from different routing protocols
                 exist. The route with a lower preference value is preferred.
                 Valid range is 1 through 255."
        ::= { csOrionVPNVRouterManagedIpRouteEntry 17 }

    csOrionVPNVRouterManagedIpRoutePreference2 OBJECT-TYPE
        SYNTAX Integer32
        MAX-ACCESS  read-create
        STATUS  current
        DESCRIPTION
                "The secondary preference value for this route. 
                The route preference value which is also referred to
                as the Adminstrative Distance is used for selecting
                a route when multiple routes from different routing protocols
                exist. The route with a lower preference value is preferred.
                Valid range is 1 through 255."
        ::= { csOrionVPNVRouterManagedIpRouteEntry 18 }

    csOrionVPNVRouterManagedIpRouteColor1 OBJECT-TYPE
        SYNTAX Integer32
        MAX-ACCESS  read-create
        STATUS  current
        DESCRIPTION
                "The primary color value for this route. The color is used
                a finer grain preference value. It should be applied for
                route select if preference1 and preference2 values match."
        ::= { csOrionVPNVRouterManagedIpRouteEntry 19 }

    csOrionVPNVRouterManagedIpRouteColor2 OBJECT-TYPE
        SYNTAX Integer32
        MAX-ACCESS  read-create
        STATUS  current
        DESCRIPTION
                "The secondary color value for this route. The color is used
                a finer grain preference value. It should be applied for
                route select if preference1 and preference2 values match."
        ::= { csOrionVPNVRouterManagedIpRouteEntry 20 }

    csOrionVPNVRouterManagedIpRouteActiveOption OBJECT-TYPE
        SYNTAX INTEGER {
                unspecified    (1),  -- not specified 
                active         (2),  -- passive route
                passive        (3)  -- passive route
        }
        MAX-ACCESS  read-create
        STATUS  current
        DESCRIPTION
                "Additional information for managed routes which is included
                with the route when it is installed in the routing table.

                unspecified (1) implies the default option for the route
                protocol should be used.

                active (2) routes are removed from the routing and forwarding
                table if they become inactive.

                passive (3) routes remain installed in the routing and 
                forwarding tables it the route becomes inactive. They are
                marked with reject next-hops when they are inactive."
		DEFVAL { unspecified }
        ::= { csOrionVPNVRouterManagedIpRouteEntry 21 }

    csOrionVPNVRouterManagedIpRouteInstallOption OBJECT-TYPE
        SYNTAX INTEGER {
                unspecified    (1),  -- not specified 
                install        (2),  -- eligible to install in forwarding table
                no-install     (3)  -- do not install in forwarding table
        }
        MAX-ACCESS  read-create
        STATUS  current
        DESCRIPTION
                "Additional information for managed routes which is included
                with the route when it is installed in the routing table.

                unspecified (1) implies the default option for the route
                protocol should be used.

                install (2) routes are eligibled to be installed into the
                roting and forwarding tables if selected.

                no-install (3) routes are not considered for selection of
                active routes and hence not installed in the forwarding 
                table."
		DEFVAL { unspecified }
        ::= { csOrionVPNVRouterManagedIpRouteEntry 22 }

    csOrionVPNVRouterManagedIpRouteAdvertiseOption OBJECT-TYPE
        SYNTAX INTEGER {
                unspecified    (1),  -- not specified 
                readvertise    (2), -- eligible for re-advertising
                no-readvertise (3) -- do not re-advertise 
        }
        MAX-ACCESS  read-create
        STATUS  current
        DESCRIPTION
                "Additional information for managed routes which is included
                with the route when it is installed in the routing table.

                unspecified (1) implies the default option for the route
                protocol should be used.

                readvertise (2) routes are eligibled to be readvertised by 
                by other routing protocols if the route is active.

                no-readvertise (3) routes are not considered for 
                readverisement by other protocols."
		DEFVAL { unspecified }
        ::= { csOrionVPNVRouterManagedIpRouteEntry 23 }


    csOrionVPNVRouterManagedIpRouteRetainOption OBJECT-TYPE
        SYNTAX INTEGER {
                unspecified    (1),  -- not specified 
                retain         (2), --  route remains in the route table after shutdown
                no-retain      (3) --  remove if routing process shuts down
        }
        MAX-ACCESS  read-create
        STATUS  current
        DESCRIPTION
                "Additional information for managed routes which is included
                with the route when it is installed in the routing table.

                unspecified (1) implies the default option for the route
                protocol should be used.

                retain (2) routes are retained in the forwarding table if the route 
				manager shuts down.

                no-retain (3) routes are removed from the routing table if the route
				manager shuts down."
		DEFVAL { unspecified }
        ::= { csOrionVPNVRouterManagedIpRouteEntry 24 }

    csOrionVPNVRouterManagedIpRouteRowStatus OBJECT-TYPE
        SYNTAX  RowStatus
        MAX-ACCESS  read-create
        STATUS  current
        DESCRIPTION
                "A row status type for the VPN Virtual Router."
        ::= { csOrionVPNVRouterManagedIpRouteEntry 25 }

    csOrionVPNVRouterManagedIpRouteOperState OBJECT-TYPE
        SYNTAX OperState 
        MAX-ACCESS  read-only
        STATUS  current
        DESCRIPTION
                "The operational state of this route. The state is ON
                 if the route is selecetd to the IP forwarding table.
                 Otherwise, the operational state is OFF."
        ::= { csOrionVPNVRouterManagedIpRouteEntry 26 }


--
--  OSPF (based on RFC1850)
--  The Area ID, in OSPF, has the same format as an IP Address,
--  but has the function of defining a summarization point for
--  Link State Advertisements

AreaID ::= TEXTUAL-CONVENTION
    STATUS	current
    DESCRIPTION
	"An OSPF Area Identifier."
    SYNTAX	IpAddress


--  The Router ID, in OSPF, has the same format as an IP Address,
--  but identifies the router independent of its IP Address.

RouterID ::= TEXTUAL-CONVENTION
    STATUS	current
    DESCRIPTION
	"A OSPF Router Identifier."
    SYNTAX	IpAddress


--  The OSPF Metric is defined as an unsigned value in the range

Metric ::= TEXTUAL-CONVENTION
    STATUS	current
    DESCRIPTION
	"The OSPF Internal Metric."
    SYNTAX	Integer32 (0..'FFFF'h)

BigMetric ::= TEXTUAL-CONVENTION
    STATUS	current
    DESCRIPTION
	"The OSPF External Metric."
    SYNTAX	Integer32 (0..'FFFFFF'h)

--  Status Values

Status ::= TEXTUAL-CONVENTION
    STATUS	current
    DESCRIPTION
	"The status of an interface: 'enabled' indicates that
	it is willing to communicate with other OSPF Routers,
	while 'disabled' indicates that it is not."
    SYNTAX	INTEGER { enabled (1), disabled (2) }

--  Time Durations measured in seconds

PositiveInteger ::= TEXTUAL-CONVENTION
    STATUS	current
    DESCRIPTION
	"A positive integer. Values in excess are precluded as
	unnecessary and prone to interoperability issues."
    SYNTAX	Integer32 (0..'7FFFFFFF'h)

HelloRange ::= TEXTUAL-CONVENTION
    STATUS	current
    DESCRIPTION
	"The range of intervals on which hello messages are
	exchanged."
    SYNTAX	Integer32 (1..'FFFF'h)

UpToMaxAge ::= TEXTUAL-CONVENTION
    STATUS	current
    DESCRIPTION
	"The values that one might find or configure for
	variables bounded by the maximum age of an LSA."
    SYNTAX	Integer32 (0..3600)


--  The range of ifIndex

InterfaceIndex ::= TEXTUAL-CONVENTION
    STATUS	current
    DESCRIPTION
	"The range of ifIndex."
    SYNTAX	Integer32


--  Potential Priorities for the Designated Router Election

DesignatedRouterPriority ::= TEXTUAL-CONVENTION
    STATUS	current
    DESCRIPTION
	"The values defined for the priority of a system for
	becoming the designated router."
    SYNTAX	Integer32 (0..'FF'h)

TOSType ::= TEXTUAL-CONVENTION
    STATUS	current
    DESCRIPTION
	"Type of Service is defined as a mapping to the IP Type of
	Service Flags as defined in the IP Forwarding Table MIB

	+-----+-----+-----+-----+-----+-----+-----+-----+
	|		|	                    |     |
	|   PRECEDENCE    |    TYPE OF SERVICE    |  0  |
	|		|	                    |     |
	+-----+-----+-----+-----+-----+-----+-----+-----+

		IP TOS		    IP TOS
	    Field     Policy	Field     Policy

	    Contents    Code	Contents    Code
	    0 0 0 0  ==>   0	0 0 0 1  ==>   2
	    0 0 1 0  ==>   4	0 0 1 1  ==>   6
	    0 1 0 0  ==>   8	0 1 0 1  ==>  10
	    0 1 1 0  ==>  12	0 1 1 1  ==>  14
	    1 0 0 0  ==>  16	1 0 0 1  ==>  18
	    1 0 1 0  ==>  20	1 0 1 1  ==>  22





	    1 1 0 0  ==>  24	1 1 0 1  ==>  26
	    1 1 1 0  ==>  28	1 1 1 1  ==>  30

	The remaining values are left for future definition."
    SYNTAX	Integer32 (0..30)


--  OSPF General Variables
--	These parameters apply globally to the Router's
--	OSPF Process.


    csOspfGeneralTable OBJECT-TYPE
	SYNTAX   SEQUENCE OF CsOspfGeneralEntry
	MAX-ACCESS   not-accessible
	STATUS   current
	DESCRIPTION
	    "Information describing the configured  parame-
	    ters  and cumulative statistics of the router's
	    attached areas."

	REFERENCE
	 "OSPF Version 2, Section 6  The Area Data Struc-
	 ture"
	::= { csOspfConf 1 }

    csOspfGeneralEntry OBJECT-TYPE
	SYNTAX   CsOspfGeneralEntry
	MAX-ACCESS   not-accessible
	STATUS   current
	DESCRIPTION
	    "Information describing the configured  parame-
	    ters  and  cumulative  statistics of one of the
	    router's attached areas."
	INDEX { csOrionGlobalVPNIndex, csOrionVPNVRouterIndex }
	::= { csOspfGeneralTable 1 }

    CsOspfGeneralEntry ::=
    SEQUENCE {
	csOspfRouterId
		RouterID,
	csOspfAdminStat
		Status,
	csOspfVersionNumber
		INTEGER,
	csOspfAreaBdrRtrStatus
		TruthValue,
	csOspfASBdrRtrStatus
		TruthValue,
	csOspfExternLsaCount
		Gauge32,
	csOspfExternLsaCksumSum
		Integer32,
	csOspfTOSSupport 
		TruthValue,
	csOspfOriginateNewLsas
		Counter32,
	csOspfRxNewLsas
		Counter32,
	csOspfExtLsdbLimit
		Integer32,
	csOspfMulticastExtensions 
		Integer32,
	csOspfExitOverflowInterval
		PositiveInteger,
	csOspfDemandExtensions 
		TruthValue,
	csOspfGeneralEntryRowStatus
		RowStatus
	        }

    csOspfRouterId OBJECT-TYPE
	SYNTAX   RouterID
	MAX-ACCESS   read-create
	STATUS   current
	DESCRIPTION
	    "A  32-bit  integer  uniquely  identifying  the
	    router in the Autonomous System.

	    By  convention,  to  ensure  uniqueness,   this
	    should  default  to  the  value  of  one of the
	    router's IP interface addresses."
	REFERENCE
	 "OSPF Version 2, C.1 Global parameters"
	::= { csOspfGeneralEntry 1 }

    csOspfAdminStat OBJECT-TYPE
	SYNTAX   Status
	MAX-ACCESS   read-create
	STATUS   current
	DESCRIPTION
	    "The administrative status of OSPF in the router.
	    The value 'enabled' denotes that the OSPF process is
	    active on the Virtual Router.  'disabled' disables it
	    on all interfaces on the Virtual Router."
	::= { csOspfGeneralEntry 2 }

    csOspfVersionNumber OBJECT-TYPE
	SYNTAX   INTEGER    { version2 (2) }
	MAX-ACCESS   read-only
	STATUS   current
	DESCRIPTION
	    "The current version number of the OSPF  protocol is 2."
	REFERENCE
	 "OSPF Version 2, Title"
	::= { csOspfGeneralEntry 3 }


    csOspfAreaBdrRtrStatus OBJECT-TYPE
	SYNTAX   TruthValue
	MAX-ACCESS   read-only
	STATUS   current
	DESCRIPTION
	    "A flag to note whether this router is an  area
	    border router."
	REFERENCE
	 "OSPF Version 2, Section 3 Splitting the AS into
	 Areas"
	::= { csOspfGeneralEntry 4 }


    csOspfASBdrRtrStatus OBJECT-TYPE
	SYNTAX   TruthValue
	MAX-ACCESS   read-create
	STATUS   current
	DESCRIPTION
	    "A flag to note whether this router is  config-
	    ured as an Autonomous System border router."
	REFERENCE
	 "OSPF Version 2, Section 3.3  Classification  of
	 routers"
	::= { csOspfGeneralEntry 5 }

    csOspfExternLsaCount OBJECT-TYPE
	SYNTAX   Gauge32
	MAX-ACCESS   read-only
	STATUS   current
	DESCRIPTION
	    "The number of external (LS type 5)  link-state
	    advertisements in the link-state database."
	REFERENCE
	 "OSPF Version 2, Appendix A.4.5 AS external link
	 advertisements"
	::= { csOspfGeneralEntry 6 }


    csOspfExternLsaCksumSum OBJECT-TYPE
	SYNTAX   Integer32
	MAX-ACCESS   read-only
	STATUS   current
	DESCRIPTION
	    "The 32-bit unsigned sum of the LS checksums of
	    the  external  link-state  advertisements  con-
	    tained in the link-state  database.   This  sum
	    can  be  used  to determine if there has been a
	    change in a router's link state  database,  and
	    to  compare  the  link-state  database  of  two
	    routers."
	::= { csOspfGeneralEntry 7 }


    csOspfTOSSupport OBJECT-TYPE
	SYNTAX   TruthValue
	MAX-ACCESS   read-create
	STATUS   current
	DESCRIPTION
	    "The router's support for type-of-service rout-
	    ing."
	REFERENCE
	 "OSPF Version 2,  Appendix  F.1.2  Optional  TOS
	 support"
	::= { csOspfGeneralEntry 8 }

    csOspfOriginateNewLsas OBJECT-TYPE
	SYNTAX   Counter32
	MAX-ACCESS   read-only
	STATUS   current
	DESCRIPTION
	    "The number of  new  link-state  advertisements
	    that  have been originated.  This number is in-
	    cremented each time the router originates a new
	    LSA."
	::= { csOspfGeneralEntry 9 }


    csOspfRxNewLsas OBJECT-TYPE
	SYNTAX   Counter32
	MAX-ACCESS   read-only
	STATUS   current
	DESCRIPTION
	    "The number of  link-state  advertisements  re-
	    ceived  determined  to  be  new instantiations.
	    This number does not include  newer  instantia-
	    tions  of self-originated link-state advertise-
	    ments."
	::= { csOspfGeneralEntry 10 }

    csOspfExtLsdbLimit OBJECT-TYPE
	SYNTAX   Integer32 (-1..'7FFFFFFF'h)
	MAX-ACCESS   read-create
	STATUS   current
	DESCRIPTION
	    "The  maximum   number   of   non-default   AS-
	    external-LSAs entries that can be stored in the
	    link-state database.  If the value is -1,  then
	    there is no limit.

	    When the number of non-default AS-external-LSAs
	    in   a  router's  link-state  database  reaches
	    csOspfExtLsdbLimit, the router  enters  Overflow-
	    State.   The   router  never  holds  more  than
	    csOspfExtLsdbLimit  non-default  AS-external-LSAs
	    in  its  database. csOspfExtLsdbLimit MUST be set
	    identically in all routers attached to the OSPF
	    backbone  and/or  any regular OSPF area. (i.e.,
	    OSPF stub areas and NSSAs are excluded)."
	DEFVAL { -1 }
	::= { csOspfGeneralEntry 11 }

    csOspfMulticastExtensions OBJECT-TYPE
	SYNTAX   Integer32
	MAX-ACCESS   read-create
	STATUS   current
	DESCRIPTION
	    "A Bit Mask indicating whether  the  router  is
	    forwarding  IP  multicast  (Class  D) datagrams
	    based on the algorithms defined in  the  Multi-
	    cast Extensions to OSPF.

	    Bit 0, if set, indicates that  the  router  can
	    forward  IP multicast datagrams in the router's
	    directly attached areas (called intra-area mul-
	    ticast routing).

	    Bit 1, if set, indicates that  the  router  can
	    forward  IP  multicast  datagrams  between OSPF
	    areas (called inter-area multicast routing).

	    Bit 2, if set, indicates that  the  router  can
	    forward  IP  multicast  datagrams between Auto-
	    nomous Systems (called inter-AS multicast rout-
	    ing).

	    Only certain combinations of bit  settings  are
	    allowed,  namely: 0 (no multicast forwarding is
	    enabled), 1 (intra-area multicasting  only),  3
	    (intra-area  and  inter-area  multicasting),  5
	    (intra-area and inter-AS  multicasting)  and  7
	    (multicasting  everywhere). By default, no mul-
	    ticast forwarding is enabled."
	DEFVAL { 0 }
	::= { csOspfGeneralEntry 12 }

    csOspfExitOverflowInterval OBJECT-TYPE
	SYNTAX   PositiveInteger
	MAX-ACCESS   read-create
	STATUS   current
	DESCRIPTION
	    "The number of  seconds  that,  after  entering
	    OverflowState,  a  router will attempt to leave
	    OverflowState. This allows the router to  again
	    originate  non-default  AS-external-LSAs.  When
	    set to 0, the router will not  leave  Overflow-
	    State until restarted."
	DEFVAL { 0 }
	::= { csOspfGeneralEntry 13 }

    csOspfDemandExtensions OBJECT-TYPE
	SYNTAX   TruthValue
	MAX-ACCESS   read-create
	STATUS   current
	DESCRIPTION
	    "The router's support for demand routing."
	REFERENCE
	 "OSPF Version 2, Appendix on Demand Routing"
	::= { csOspfGeneralEntry 14 }
		
	csOspfGeneralEntryRowStatus OBJECT-TYPE
	SYNTAX		RowStatus 
	MAX-ACCESS	read-create
	STATUS		current
	DESCRIPTION
	       "A row status type for the OSPF General Table."
	::= { csOspfGeneralEntry 15 }


--	The OSPF Area Data Structure contains information
--	regarding the various areas. The interfaces and
--	virtual links are configured as part of these areas.
--	Area 0.0.0.0, by definition, is the Backbone Area


    csOspfAreaTable OBJECT-TYPE
	SYNTAX   SEQUENCE OF CsOspfAreaEntry
	MAX-ACCESS   not-accessible
	STATUS   current
	DESCRIPTION
	    "Information describing the configured  parame-
	    ters of the router's attached areas."
	REFERENCE
	 "OSPF Version 2, Section 6  The Area Data Structure"
	::= { csOspfConf 2 }

    csOspfAreaEntry OBJECT-TYPE
	SYNTAX   CsOspfAreaEntry
	MAX-ACCESS   not-accessible
	STATUS   current
	DESCRIPTION
	      "Information describing the configured  parame-
	      ters  and  cumulative  statistics of one of the
	      router's attached areas."
	INDEX { csOrionGlobalVPNIndex, csOrionVPNVRouterIndex, csOspfAreaId }
	::= { csOspfAreaTable 1 }

    CsOspfAreaEntry ::=
	SEQUENCE {
	csOspfAreaId
		AreaID,
	csOspfAreaName
		DisplayString,
	csOspfImportAsExtern
		INTEGER,
	csOspfSpfRuns
		Counter32,
	csOspfAreaBdrRtrCount
		Gauge32,
	csOspfAsBdrRtrCount
		Gauge32,
	csOspfAreaLsaCount
		Gauge32,
	csOspfAreaLsaCksumSum
		Integer32,
	csOspfAreaSummary
		INTEGER,
	csOspfAreaAuthType
		INTEGER,
	csOspfAreaRowStatus
		RowStatus,
	csOspfAreaOperStatus
		OperStatus 
	}

    csOspfAreaId OBJECT-TYPE
	SYNTAX   AreaID
	MAX-ACCESS   not-accessible
	STATUS   current
	DESCRIPTION
	    "A 32-bit integer uniquely identifying an area.
	    Area ID 0.0.0.0 is used for the OSPF backbone."
	REFERENCE
	 "OSPF Version 2, Appendix C.2 Area parameters"
	::= { csOspfAreaEntry 1 }

    csOspfAreaName OBJECT-TYPE
	SYNTAX   DisplayString (SIZE(0..80))
	MAX-ACCESS   read-create
	STATUS   current
	DESCRIPTION
	    "A descriptive name for this area."
	DEFVAL { "" }
	::= { csOspfAreaEntry 2 }

    csOspfImportAsExtern OBJECT-TYPE
        SYNTAX   INTEGER    {
		importExternal (1),
		importNoExternal (2),
		importNssa (3)
        }
        MAX-ACCESS   read-create
        STATUS   current
        DESCRIPTION
           "The area's support for importing  AS  external
           link- state advertisements."
       REFERENCE
          "OSPF Version 2, Appendix C.2 Area parameters"
      DEFVAL { importExternal }
      ::= { csOspfAreaEntry 3 }

    csOspfSpfRuns OBJECT-TYPE
	SYNTAX   Counter32
	MAX-ACCESS   read-only
	STATUS   current
	DESCRIPTION
	    "The number of times that the intra-area  route
	    table  has  been  calculated  using this area's
	    link-state database.  This  is  typically  done
	    using Dijkstra's algorithm."
	::= { csOspfAreaEntry 4 }


    csOspfAreaBdrRtrCount OBJECT-TYPE
	SYNTAX   Gauge32
	MAX-ACCESS   read-only
	STATUS   current
	DESCRIPTION
	    "The total number of area border routers reach-
	    able within this area.  This is initially zero,
	    and is calculated in each SPF Pass."
	::= { csOspfAreaEntry 5 }

    csOspfAsBdrRtrCount OBJECT-TYPE
	SYNTAX   Gauge32
	MAX-ACCESS   read-only
	STATUS   current
	DESCRIPTION
	    "The total number of Autonomous  System  border
	    routers  reachable  within  this area.  This is
	    initially zero, and is calculated in  each  SPF
	    Pass."
	::= { csOspfAreaEntry 6 }


    csOspfAreaLsaCount OBJECT-TYPE
	SYNTAX   Gauge32
	MAX-ACCESS   read-only
	STATUS   current
	DESCRIPTION
	    "The total number of link-state  advertisements
	    in  this  area's link-state database, excluding
	    AS External LSA's."
	::= { csOspfAreaEntry 7 }


    csOspfAreaLsaCksumSum OBJECT-TYPE
	SYNTAX   Integer32
	MAX-ACCESS   read-only
	STATUS   current
	DESCRIPTION
	    "The 32-bit unsigned sum of the link-state  ad-
	    vertisements'  LS  checksums  contained in this
	    area's link-state database.  This sum  excludes
	    external (LS type 5) link-state advertisements.
	    The sum can be used to determine if  there  has
	    been  a  change  in a router's link state data-
	    base, and to compare the link-state database of
	    two routers."
	DEFVAL   { 0 }
	::= { csOspfAreaEntry 8 }

    csOspfAreaSummary OBJECT-TYPE
        SYNTAX   INTEGER    {
		noAreaSummary (1),
		sendAreaSummary (2)
        }
        MAX-ACCESS   read-create
        STATUS   current
        DESCRIPTION
           "The variable csOspfAreaSummary controls the  im-
           port  of  summary LSAs into stub areas.  It has
           no effect on other areas.

           If it is noAreaSummary, the router will neither
           originate  nor  propagate summary LSAs into the
           stub area.  It will rely entirely  on  its  de-
           fault route.

           If it is sendAreaSummary, the router will  both
           summarize and propagate summary LSAs."
       DEFVAL   { noAreaSummary }
       ::= { csOspfAreaEntry 9 }

	csOspfAreaAuthType OBJECT-TYPE
	SYNTAX	INTEGER {
		none	       (0),
		simplePassword (1),
		md5	       (2)
	}
	MAX-ACCESS  read-create
	STATUS   current
	DESCRIPTION
	      "The authentication type specified for this area."
	REFERENCE
	      "OSPF Version 2, Appendix E Authentication"
	DEFVAL { none }	 -- no authentication, by default
	::= { csOspfAreaEntry 10 }

    csOspfAreaRowStatus OBJECT-TYPE
	SYNTAX		RowStatus 
	MAX-ACCESS	read-create
	STATUS		current
	DESCRIPTION
	       "A row status type for the OSPF Area Table."
	::= { csOspfAreaEntry 11 }

    csOspfAreaOperStatus OBJECT-TYPE
	SYNTAX		OperStatus
	MAX-ACCESS	read-only
	STATUS		current
	DESCRIPTION
	       "A operational status for the OSPF Area Table."
	::= { csOspfAreaEntry 12 }



--  OSPF Area Default Metric Table

--      The OSPF Area Default Metric Table describes the metrics
--      that a default Area Border Router will advertise into a
--      Stub area.


    csOspfStubAreaTable OBJECT-TYPE
        SYNTAX   SEQUENCE OF CsOspfStubAreaEntry
        MAX-ACCESS   not-accessible
        STATUS   current
        DESCRIPTION
           "The set of metrics that will be advertised  by
           a default Area Border Router into a stub area."
       REFERENCE
          "OSPF Version 2, Appendix C.2, Area Parameters"
      ::= { csOspfConf 3 }


    csOspfStubAreaEntry OBJECT-TYPE
        SYNTAX   CsOspfStubAreaEntry
        MAX-ACCESS   not-accessible
        STATUS   current
        DESCRIPTION
           "The metric for a given Type  of  Service  that
           will  be  advertised  by  a default Area Border
           Router into a stub area."
       REFERENCE
          "OSPF Version 2, Appendix C.2, Area Parameters"
	INDEX { csOrionGlobalVPNIndex, csOrionVPNVRouterIndex, csOspfStubAreaId, csOspfStubTOS }
      ::= { csOspfStubAreaTable 1 }

CsOspfStubAreaEntry ::=
    SEQUENCE {
        csOspfStubAreaId
            AreaID,
        csOspfStubTOS
            TOSType,
        csOspfStubMetric
            BigMetric,
        csOspfStubStatus
            RowStatus,
        csOspfStubMetricType
            INTEGER
              }

    csOspfStubAreaId OBJECT-TYPE
        SYNTAX   AreaID
        MAX-ACCESS   not-accessible
        STATUS   current
        DESCRIPTION
           "The 32 bit identifier for the Stub  Area.   On
           creation,  this  can  be  derived  from the in-
           stance."
       ::= { csOspfStubAreaEntry 1 }

    csOspfStubTOS OBJECT-TYPE
        SYNTAX   TOSType
        MAX-ACCESS   not-accessible
        STATUS   current
        DESCRIPTION
           "The  Type  of  Service  associated  with   the
           metric.   On creation, this can be derived from
           the instance."
       ::= { csOspfStubAreaEntry 2 }


    csOspfStubMetric OBJECT-TYPE
        SYNTAX   BigMetric
        MAX-ACCESS   read-create
        STATUS   current
        DESCRIPTION
           "The metric value applied at the indicated type
           of  service.  By default, this equals the least
           metric at the type of service among the  inter-
           faces to other areas."
       ::= { csOspfStubAreaEntry 3 }


    csOspfStubStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { csOspfStubAreaEntry 4 }

    csOspfStubMetricType OBJECT-TYPE
        SYNTAX   INTEGER    {
                    ospfMetric (1),                -- OSPF Metric
                    comparableCost (2),        -- external type 1
                    nonComparable  (3)        -- external type 2
                  }
        MAX-ACCESS   read-create
        STATUS   current
        DESCRIPTION
           "This variable displays the type of metric  ad-
           vertised as a default route."
       DEFVAL   { ospfMetric }
       ::= { csOspfStubAreaEntry 5 }



    --
    --  OSPF Link State Database
    --	The Link State Database contains the Link State
    --	Advertisements from throughout the areas that the
    --	device is attached to.
    --


    csOspfLsdbTable OBJECT-TYPE
	SYNTAX   SEQUENCE OF CsOspfLsdbEntry
	MAX-ACCESS   not-accessible
	STATUS   current
	DESCRIPTION
	    "The OSPF Process's Link State Database."
	REFERENCE
	 "OSPF Version 2, Section 12  Link  State  Adver-
	 tisements"
	::= { csOspfConf 4 }

    csOspfLsdbEntry OBJECT-TYPE
	SYNTAX   CsOspfLsdbEntry
	MAX-ACCESS   not-accessible
	STATUS   current
	DESCRIPTION
	    "A single Link State Advertisement."
	INDEX { csOrionGlobalVPNIndex, csOrionVPNVRouterIndex,
		csOspfLsdbAreaId, csOspfLsdbType,
		csOspfLsdbLsid, csOspfLsdbRouterId }
	::= { csOspfLsdbTable 1 }

    CsOspfLsdbEntry ::=
	SEQUENCE {
	csOspfLsdbAreaId
	      AreaID,
	csOspfLsdbType
	      INTEGER,
	csOspfLsdbLsid
	      IpAddress,
	csOspfLsdbRouterId
	      RouterID,
	csOspfLsdbSequence
	      Integer32,
	csOspfLsdbAge
	      Integer32,
	csOspfLsdbChecksum
	      Integer32,
	csOspfLsdbAdvertisement
	      OCTET STRING
	}


    csOspfLsdbAreaId OBJECT-TYPE
	SYNTAX   AreaID
	MAX-ACCESS   not-accessible
	STATUS   current
	DESCRIPTION
	    "The 32 bit identifier of the Area  from  which
	    the LSA was received."
	REFERENCE
	 "OSPF Version 2, Appendix C.2 Area parameters"
	::= { csOspfLsdbEntry 1 }

-- External Link State Advertisements are permitted
-- for backward compatibility, but should be displayed in
-- the csOspfExtLsdbTable rather than here.

    csOspfLsdbType OBJECT-TYPE
	SYNTAX   INTEGER    {
		      routerLink (1),
		      networkLink (2),
		      summaryLink (3),
		      asSummaryLink (4),
		      asExternalLink (5), -- but see csOspfExtLsdbTable
		      multicastLink (6),
		      nssaExternalLink (7)
		 }
	MAX-ACCESS   not-accessible
	STATUS   current
	DESCRIPTION
	    "The type  of  the  link  state  advertisement.
	    Each  link state type has a separate advertise-
	    ment format."
	REFERENCE
	 "OSPF Version 2, Appendix A.4.1 The  Link  State
	 Advertisement header"
	::= { csOspfLsdbEntry 2 }

    csOspfLsdbLsid OBJECT-TYPE
	SYNTAX   IpAddress
	MAX-ACCESS   not-accessible
	STATUS   current
	DESCRIPTION
	    "The Link State ID is an LS Type Specific field
	    containing either a Router ID or an IP Address;
	    it identifies the piece of the  routing  domain
	    that is being described by the advertisement."
	REFERENCE
	 "OSPF Version 2, Section 12.1.4 Link State ID"
	::= { csOspfLsdbEntry 3 }


    csOspfLsdbRouterId OBJECT-TYPE
	SYNTAX   RouterID
	MAX-ACCESS   not-accessible
	STATUS   current
	DESCRIPTION
	    "The 32 bit number that uniquely identifies the
	    originating router in the Autonomous System."
	REFERENCE
	 "OSPF Version 2, Appendix C.1 Global parameters"
	::= { csOspfLsdbEntry 4 }

--  Note that the OSPF Sequence Number is a 32 bit signed
--  integer.  It starts with the value '80000001'h,
--  or -'7FFFFFFF'h, and increments until '7FFFFFFF'h
--  Thus, a typical sequence number will be very negative.

    csOspfLsdbSequence OBJECT-TYPE
	SYNTAX   Integer32
	MAX-ACCESS   read-only
	STATUS   current
	DESCRIPTION
	    "The sequence number field is a  signed  32-bit
	    integer.   It  is used to detect old and dupli-
	    cate link state advertisements.  The  space  of
	    sequence  numbers  is  linearly  ordered.   The
	    larger the sequence number the more recent  the
	    advertisement."
	REFERENCE
	 "OSPF Version  2,  Section  12.1.6  LS  sequence
	 number"
	::= { csOspfLsdbEntry 5 }


    csOspfLsdbAge OBJECT-TYPE
	SYNTAX   Integer32    -- Should be 0..MaxAge
	MAX-ACCESS   read-only
	STATUS   current
	DESCRIPTION
	    "This field is the age of the link state adver-
	    tisement in seconds."
	REFERENCE
	 "OSPF Version 2, Section 12.1.1 LS age"
	::= { csOspfLsdbEntry 6 }

    csOspfLsdbChecksum OBJECT-TYPE
	SYNTAX   Integer32
	MAX-ACCESS   read-only
	STATUS   current
	DESCRIPTION
	    "This field is the  checksum  of  the  complete
	    contents  of  the  advertisement, excepting the
	    age field.  The age field is excepted  so  that
	    an   advertisement's  age  can  be  incremented
	    without updating the  checksum.   The  checksum
	    used  is  the same that is used for ISO connec-
	    tionless datagrams; it is commonly referred  to
	    as the Fletcher checksum."
	REFERENCE
	 "OSPF Version 2, Section 12.1.7 LS checksum"
	::= { csOspfLsdbEntry 7 }


    csOspfLsdbAdvertisement OBJECT-TYPE
	SYNTAX   OCTET STRING (SIZE (1..65535))
	MAX-ACCESS   read-only
	STATUS   current
	DESCRIPTION
	    "The entire Link State Advertisement, including
	    its header."
	REFERENCE
	 "OSPF Version 2, Section 12  Link  State  Adver-
	 tisements"
	::= { csOspfLsdbEntry 8 }


--  OSPF Host Table

--	The Host/Metric Table indicates what hosts are directly
--	attached to the Router, and what metrics and types of
--	service should be advertised for them.

    csOspfHostTable OBJECT-TYPE
	SYNTAX   SEQUENCE OF CsOspfHostEntry
	MAX-ACCESS   not-accessible
	STATUS   current
	DESCRIPTION
	    "The list of Hosts, and their metrics, that the
	    router will advertise as host routes."
	REFERENCE
	 "OSPF Version 2, Appendix C.6  Host route param-
	 eters"
	::= { csOspfConf 5 }

    csOspfHostEntry OBJECT-TYPE
	SYNTAX   CsOspfHostEntry
	MAX-ACCESS   not-accessible
	STATUS   current
	DESCRIPTION
	    "A metric to be advertised, for a given type of
	    service, when a given host is reachable."
	INDEX { csOrionGlobalVPNIndex, csOrionVPNVRouterIndex,
		csOspfHostIpAddress, csOspfHostTOS }
	::= { csOspfHostTable 1 }

CsOspfHostEntry ::=
    SEQUENCE {
	csOspfHostIpAddress
	      IpAddress,
	csOspfHostTOS
	      TOSType,
	csOspfHostMetric
	      Metric,
	csOspfHostStatus
	      RowStatus,
	csOspfHostAreaID
	      AreaID
	        }

    csOspfHostIpAddress OBJECT-TYPE
	SYNTAX   IpAddress
	MAX-ACCESS   not-accessible
	STATUS   current
	DESCRIPTION
	    "The IP Address of the Host."
	REFERENCE
	 "OSPF Version 2, Appendix C.6 Host route parame-
	 ters"
	::= { csOspfHostEntry 1 }


    csOspfHostTOS OBJECT-TYPE
	SYNTAX   TOSType
	MAX-ACCESS   not-accessible
	STATUS   current
	DESCRIPTION
	    "The Type of Service of the route being config-
	    ured."
	REFERENCE
	 "OSPF Version 2, Appendix C.6 Host route parame-
	 ters"
	::= { csOspfHostEntry 2 }


    csOspfHostMetric OBJECT-TYPE
	SYNTAX   Metric
	MAX-ACCESS   read-create
	STATUS   current
	DESCRIPTION
	    "The Metric to be advertised."
	REFERENCE
	 "OSPF Version 2, Appendix C.6 Host route parame-
	 ters"
	::= { csOspfHostEntry 3 }

    csOspfHostStatus OBJECT-TYPE
	SYNTAX   RowStatus
	MAX-ACCESS   read-create
	STATUS   current
	DESCRIPTION
	    "This variable displays the status of  the  en-
	    try.  Setting it to 'invalid' has the effect of
	    rendering it inoperative.  The internal  effect
	    (row removal) is implementation dependent."
	::= { csOspfHostEntry 4 }


    csOspfHostAreaID OBJECT-TYPE
	SYNTAX   AreaID
	MAX-ACCESS   read-only
	STATUS   current
	DESCRIPTION
	    "The Area the Host Entry is to be found within.
	    By  default, the area that a subsuming OSPF in-
	    terface is in, or 0.0.0.0"
	REFERENCE
	 "OSPF Version 2, Appendix C.2 Area parameters"
	::= { csOspfHostEntry 5 }

--  OSPF Interface Table
--	The OSPF Interface Table augments the ipAddrTable
--	       with OSPF specific information.

    csOspfIfTable OBJECT-TYPE
	SYNTAX   SEQUENCE OF CsOspfIfEntry
	MAX-ACCESS   not-accessible
	STATUS   current
	DESCRIPTION
	    "The OSPF Interface Table describes the  inter-
	    faces from the viewpoint of OSPF."
	REFERENCE
	 "OSPF Version 2, Appendix C.3  Router  interface
	 parameters"
	::= { csOspfConf 6 }

    csOspfIfEntry OBJECT-TYPE
	SYNTAX   CsOspfIfEntry
	MAX-ACCESS   not-accessible
	STATUS   current
	DESCRIPTION
	    "The OSPF Interface Entry describes one  inter-
	    face from the viewpoint of OSPF."
	INDEX { csOrionGlobalVPNIndex, csOrionVPNVRouterIndex, csOspfIfIpAddress, csOspfAddressLessIf }
	::= { csOspfIfTable 1 }

    CsOspfIfEntry ::=
	SEQUENCE {
	csOspfIfIpAddress
		IpAddress,
	csOspfAddressLessIf
		Integer32,
	csOspfIfAreaId
		AreaID,
	csOspfIfType
		INTEGER,
	csOspfIfAdminStatus
		Status,
	csOspfIfRtrPriority
		DesignatedRouterPriority,
	csOspfIfTransitDelay
		UpToMaxAge,
	csOspfIfRetransInterval
		UpToMaxAge,
	csOspfIfHelloInterval
		HelloRange,
	csOspfIfRtrDeadInterval
		PositiveInteger,
	csOspfIfPollInterval
		PositiveInteger,
	csOspfIfState
		INTEGER,
	csOspfIfDesignatedRouter
		IpAddress,
	csOspfIfBackupDesignatedRouter
		IpAddress,
	csOspfIfEvents
		Counter32,
	csOspfIfAuthType
		INTEGER,
	csOspfIfAuthKey
		OCTET STRING,
	csOspfIfMulticastForwarding
		INTEGER,
	csOspfIfDemand
		TruthValue,
	csOspfIfMetric
		Metric,
	csOspfIfAdvertiseSubnet
		INTEGER,
	csOspfIfStatus
		RowStatus
	}

    csOspfIfIpAddress OBJECT-TYPE
	SYNTAX   IpAddress
	MAX-ACCESS   not-accessible
	STATUS   current
	DESCRIPTION
           "The IP address of this OSPF interface."
	::= { csOspfIfEntry 1 }

    csOspfAddressLessIf OBJECT-TYPE
	SYNTAX   Integer32
	MAX-ACCESS   not-accessible
	STATUS   current
	DESCRIPTION
           "For the purpose of easing  the  instancing  of
           addressed   and  addressless  interfaces;  This
           variable takes the value 0 on  interfaces  with
           IP  Addresses,  and  the corresponding value of
           ifIndex for interfaces having no IP Address."
	::= { csOspfIfEntry 2 }

    csOspfIfAreaId OBJECT-TYPE
	SYNTAX   AreaID
	MAX-ACCESS   read-create
	STATUS   current
	DESCRIPTION
	    "A 32-bit integer uniquely identifying the area
	    to  which  the  interface  connects.   Area  ID
	    0.0.0.0 is used for the OSPF backbone."
	DEFVAL   { '00000000'H }    -- 0.0.0.0
	::= { csOspfIfEntry 3 }

    csOspfIfType OBJECT-TYPE
	SYNTAX   INTEGER    {
		      broadcast (1),
		      nbma (2),
		      pointToPoint (3),
		      pointToMultipoint (5),
		      loopback		(6)
		 }
	MAX-ACCESS   read-create
	STATUS   current
	DESCRIPTION
	    "The OSPF interface type.

	    By way of a default, this field may be intuited
	    from the corresponding value of ifType.  Broad-
	    cast LANs, such as  Ethernet  and  IEEE  802.5,
	    take  the  value  'broadcast', X.25 and similar
	    technologies take the value 'nbma',  and  links
	    that  are  definitively point to point take the
	    value 'pointToPoint'."
	::= { csOspfIfEntry 4 }


    csOspfIfAdminStatus OBJECT-TYPE
	SYNTAX   Status
	MAX-ACCESS   read-create
	STATUS   current
	DESCRIPTION
	    "The OSPF  interface's  administrative  status.
	    The  value formed on the interface, and the in-
	    terface will be advertised as an internal route
	    to  some  area.   The  value 'disabled' denotes
	    that the interface is external to OSPF."
	DEFVAL { enabled }
	::= { csOspfIfEntry 5 }

    csOspfIfRtrPriority OBJECT-TYPE
	SYNTAX   DesignatedRouterPriority
	MAX-ACCESS   read-create
	STATUS   current
	DESCRIPTION
	    "The  priority  of  this  interface.   Used  in
	    multi-access  networks,  this  field is used in
	    the designated router election algorithm.   The
	    value 0 signifies that the router is not eligi-
	    ble to become the  designated  router  on  this
	    particular  network.   In the event of a tie in
	    this value, routers will use their Router ID as
	    a tie breaker."
	DEFVAL { 1 }
	::= { csOspfIfEntry 6 }


    csOspfIfTransitDelay OBJECT-TYPE
	SYNTAX   UpToMaxAge
	MAX-ACCESS   read-create
	STATUS   current
	DESCRIPTION
           "The estimated number of seconds  it  takes  to
           transmit  a  link state update packet over this
           interface."
	DEFVAL { 1 }
	::= { csOspfIfEntry 7 }



    csOspfIfRetransInterval OBJECT-TYPE
	SYNTAX   UpToMaxAge
	MAX-ACCESS   read-create
	STATUS   current
	DESCRIPTION
	    "The number of seconds between  link-state  ad-
	    vertisement  retransmissions,  for  adjacencies
	    belonging to this  interface.   This  value  is
	    also used when retransmitting database descrip-
	    tion and link-state request packets."
	DEFVAL { 5 }
	::= { csOspfIfEntry 8 }

    csOspfIfHelloInterval OBJECT-TYPE
	SYNTAX		HelloRange
	MAX-ACCESS	read-create
	STATUS		current
	DESCRIPTION
	      "The length of time, in  seconds,  between  the
	      Hello  packets that the routers within this area send 
	       on the interface.  This value must be the same  for  all
	      routers attached to a common network."
	DEFVAL { 10 }
	::= { csOspfIfEntry 9 }

    csOspfIfRtrDeadInterval OBJECT-TYPE
	SYNTAX		PositiveInteger
	MAX-ACCESS	read-create
	STATUS		current
	DESCRIPTION
	    "The number of seconds that  a  router's  Hello
	    packets  have  not been seen before it's neigh-
	    bors declare the router down.  This  should  be
	    some  multiple  of  the  Hello  interval.  This
	    value must be the same for all routers attached
	    to a common network."
	DEFVAL { 40 }
	::= { csOspfIfEntry 10 }

    csOspfIfPollInterval OBJECT-TYPE
	SYNTAX   PositiveInteger
	MAX-ACCESS   read-create
	STATUS   current
	DESCRIPTION
           "The larger time interval, in seconds,  between
           the  Hello  packets  sent  to  an inactive non-
           broadcast multi- access neighbor."
	DEFVAL { 120 }
	::= { csOspfIfEntry 11 }

    csOspfIfState OBJECT-TYPE
        SYNTAX   INTEGER    {
                    down (1),
                    loopback (2),
                    waiting (3),
                    pointToPoint (4),
                    designatedRouter (5),
                    backupDesignatedRouter (6),
                    otherDesignatedRouter (7)
                  }
        MAX-ACCESS   read-only
        STATUS   current
        DESCRIPTION
           "The OSPF Interface State."
       DEFVAL { down }
       ::= { csOspfIfEntry 12 }


    csOspfIfDesignatedRouter OBJECT-TYPE
	SYNTAX   IpAddress
	MAX-ACCESS   read-only
	STATUS   current
	DESCRIPTION
	    "The IP Address of the Designated Router."
	DEFVAL   { '00000000'H }    -- 0.0.0.0
	::= { csOspfIfEntry 13 }


    csOspfIfBackupDesignatedRouter OBJECT-TYPE
	SYNTAX   IpAddress
	MAX-ACCESS   read-only
	STATUS   current
	DESCRIPTION
	    "The  IP  Address  of  the  Backup   Designated
	    Router."
	DEFVAL   { '00000000'H }    -- 0.0.0.0
	::= { csOspfIfEntry 14 }

    csOspfIfEvents OBJECT-TYPE
	SYNTAX   Counter32
	MAX-ACCESS   read-only
	STATUS   current
	DESCRIPTION
	    "The number of times this  OSPF  interface  has
	    changed its state, or an error has occurred."
	::= { csOspfIfEntry 15 }

	csOspfIfAuthType OBJECT-TYPE
	SYNTAX	INTEGER {
		none	       (0),
		simplePassword (1),
		md5	       (2)
	}
	MAX-ACCESS  read-create
	STATUS   current
	DESCRIPTION
	      "The authentication type specified for this area."
	REFERENCE
	      "OSPF Version 2, Appendix E Authentication"
	DEFVAL { none }	 -- no authentication, by default
	::= { csOspfIfEntry 16 }

	csOspfIfAuthKey OBJECT-TYPE
	SYNTAX   OCTET STRING (SIZE (0..256))
	MAX-ACCESS   read-create
	STATUS   current
	DESCRIPTION
		   "The Authentication Key.  If the Area's Author-
           ization  Type  is  simplePassword,  and the key
           length is shorter than 8 octets, the agent will
           left adjust and zero fill to 8 octets.

           Note that unauthenticated  interfaces  need  no
           authentication key, and simple password authen-
           tication cannot use a key of more  than  8  oc-
           tets.  Larger keys are useful only with authen-
           tication mechanisms not specified in this docu-
           ment.

           When read, csOspfIfAuthKey always returns an  Oc-
           tet String of length zero."
	REFERENCE
          "OSPF Version 2, Section 9  The  Interface  Data
          Structure"
	DEFVAL   { '0000000000000000'H }  -- 0.0.0.0.0.0.0.0
	::= { csOspfIfEntry 17 }

--
-- This object has been removed
--
--    csOspfIfStatus OBJECT-TYPE
--

    csOspfIfMulticastForwarding OBJECT-TYPE
	SYNTAX   INTEGER    {
			       blocked (1),	  -- no multicast forwarding
			       multicast (2),	  -- using multicast address
			       unicast (3)	  -- to each OSPF neighbor
		 }
	MAX-ACCESS   read-create
	STATUS   current
	DESCRIPTION
	    "The way multicasts should  forwarded  on  this
	    interface;  not  forwarded,  forwarded  as data
	    link multicasts, or forwarded as data link uni-
	    casts.   Data link multicasting is not meaning-
	    ful on point to point and NBMA interfaces,  and
	    setting csOspfMulticastForwarding to 0 effective-
	    ly disables all multicast forwarding."
	DEFVAL { blocked }
	::= { csOspfIfEntry 18 }


    csOspfIfDemand OBJECT-TYPE
        SYNTAX   TruthValue
        MAX-ACCESS   read-create
        STATUS   current
        DESCRIPTION
           "Indicates whether Demand OSPF procedures (hel-
           lo supression to FULL neighbors and setting the
           DoNotAge flag on proogated LSAs) should be per-
           formed on this interface."
       DEFVAL { false }
       ::= { csOspfIfEntry 19 }

    csOspfIfMetric OBJECT-TYPE
        SYNTAX   Metric
        MAX-ACCESS   read-create
        STATUS   current
        DESCRIPTION
           "The metric of using this type  of  service  on
           this interface.  The default value of the TOS 0
           Metric is 10^8 / ifSpeed. 
		   Note: this is added for the support of TOS 0 Metric value,
		   It will be deprecated later when TOS is supported and 
		   the csOspfIfMetricTable is being used."
      ::= { csOspfIfEntry 20 }

	csOspfIfAdvertiseSubnet OBJECT-TYPE
	SYNTAX   INTEGER {
			enabled (1),
			disabled (2)
			}
	MAX-ACCESS   read-create
	STATUS   current
	DESCRIPTION
	    " Enable/Disable advertise-subnet capability."
	DEFVAL   { enabled }
	::= { csOspfIfEntry 21 }
		
	csOspfIfStatus OBJECT-TYPE
	SYNTAX		RowStatus 
	MAX-ACCESS	read-create
	STATUS		current
	DESCRIPTION
	       "A row status type for the OSPF Interface Table."
	::= { csOspfIfEntry 22 }

--  OSPF Interface MD5 Authentication Table

    csOspfIfMd5Table OBJECT-TYPE
	SYNTAX   SEQUENCE OF CsOspfIfMd5Entry
	MAX-ACCESS   not-accessible
	STATUS   current
	DESCRIPTION
	    "The OSPF Interface MD5 table contains a list of MD5 authentication 
	 	 structures and the corresponding MD5 authentication IDs for the inter-
	     faces from the viewpoint of OSPF."
	REFERENCE
	 "OSPF Version 2, Appendix D.3  Cryptographic authentication"
	::= { csOspfConf 15 }

    csOspfIfMd5Entry OBJECT-TYPE
	SYNTAX   CsOspfIfMd5Entry
	MAX-ACCESS   not-accessible
	STATUS   current
	DESCRIPTION
	    "The OSPF Interface Entry contains the MD5 authentication structure
		corresponding to one  inter-face from the viewpoint of OSPF."
	INDEX { csOrionGlobalVPNIndex, csOrionVPNVRouterIndex, csOspfIfIpAddress, csOspfAddressLessIf, csOspfIfMd5MessageDigestKeyId }
	::= { csOspfIfMd5Table 1 }


    CsOspfIfMd5Entry ::=
	SEQUENCE {
	csOspfIfMd5MessageDigestKeyId
		Integer32,
	csOspfIfMd5Key
		OCTET STRING,     	    				
	csOspfIfMd5RowStatus            
		RowStatus
	}

	csOspfIfMd5MessageDigestKeyId OBJECT-TYPE
	SYNTAX   Integer32
	MAX-ACCESS   not-accessible
	STATUS   current
	DESCRIPTION
          	"Message-digest authentication key.
	   	A shared secret key that is configured on all routers to specify the 
	   	decryption algorithm to be used."
	DEFVAL { 0 }
	::= { csOspfIfMd5Entry 1 }

	csOspfIfMd5Key OBJECT-TYPE
	SYNTAX   OCTET STRING (SIZE (0..256))
	MAX-ACCESS   read-create
	STATUS   current
	DESCRIPTION
		"Message-digest authentication string for this interface. The 
		string is encrypted using an algorithm specified by a shared secret
		key."
	REFERENCE
		"OSPF Version 2, Section D.3  Cryptographic authentication"
		
	DEFVAL   { '0000000000000000'H }  -- 0.0.0.0.0.0.0.0
	::= { csOspfIfMd5Entry 2 }

    csOspfIfMd5RowStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { csOspfIfMd5Entry 3 }

--  OSPF Interface Metric Table

--      The Metric Table describes the metrics to be advertised
--      for a specified interface at the various types of service.
--      As such, this table is an adjunct of the OSPF Interface
--      Table. This table is not being used now since there is only 
--      one type of service supported (TOS 0) . It will be used 
--	later when the multiple TOSs are supported.

-- Types of service, as defined by RFC 791, have the ability
-- to request low delay, high bandwidth, or reliable linkage.

-- For the purposes of this specification, the measure of
-- bandwidth

--      Metric = 10^8 / ifSpeed

-- is the default value.  For multiple link interfaces, note
-- that ifSpeed is the sum of the individual link speeds.
-- This yields a number having the following typical values:

--      Network Type/bit rate   Metric

--      >= 100 MBPS                 1
--      Ethernet/802.3             10
--      E1                         48
--      T1 (ESF)                   65
--       64 KBPS                 1562
--       56 KBPS                 1785
--       19.2 KBPS               5208
--        9.6 KBPS              10416

-- Routes that are not specified use the default (TOS 0) metric

    csOspfIfMetricTable OBJECT-TYPE
        SYNTAX   SEQUENCE OF CsOspfIfMetricEntry
        MAX-ACCESS   not-accessible
        STATUS   current
        DESCRIPTION
           "The TOS metrics for  a  non-virtual  interface
           identified by the interface index."
       REFERENCE
          "OSPF Version 2, Appendix C.3  Router  interface
          parameters"
      ::= { csOspfConf 7 }

    csOspfIfMetricEntry OBJECT-TYPE
        SYNTAX   CsOspfIfMetricEntry
        MAX-ACCESS   not-accessible
        STATUS   current
        DESCRIPTION
           "A particular TOS metric for a non-virtual  in-
           terface identified by the interface index."
       REFERENCE
          "OSPF Version 2, Appendix C.3  Router  interface
          parameters"
      INDEX { csOrionGlobalVPNIndex, csOrionVPNVRouterIndex, 
	csOspfIfMetricIpAddress, csOspfIfMetricAddressLessIf, csOspfIfMetricTOS }
      ::= { csOspfIfMetricTable 1 }

CsOspfIfMetricEntry ::=
    SEQUENCE {
        csOspfIfMetricIpAddress
            IpAddress,
        csOspfIfMetricAddressLessIf
            Integer32,
        csOspfIfMetricTOS
            TOSType,
        csOspfIfMetricValue
            Metric,
        csOspfIfMetricStatus
            RowStatus
              }

    csOspfIfMetricIpAddress OBJECT-TYPE
        SYNTAX   IpAddress
        MAX-ACCESS   not-accessible
        STATUS   current
        DESCRIPTION
           "The IP address of this OSPF interface.  On row
           creation,  this  can  be  derived  from the in-
           stance."
       ::= { csOspfIfMetricEntry 1 }

    csOspfIfMetricAddressLessIf OBJECT-TYPE
        SYNTAX   Integer32
        MAX-ACCESS   not-accessible
        STATUS   current
        DESCRIPTION
           "For the purpose of easing  the  instancing  of
           addressed   and  addressless  interfaces;  This
           variable takes the value 0 on  interfaces  with
           IP  Addresses, and the value of ifIndex for in-
           terfaces having no IP Address.   On  row  crea-
           tion, this can be derived from the instance."
       ::= { csOspfIfMetricEntry 2 }


    csOspfIfMetricTOS OBJECT-TYPE
        SYNTAX   TOSType
        MAX-ACCESS   not-accessible
        STATUS   current
        DESCRIPTION
           "The type of service metric  being  referenced.
           On  row  creation, this can be derived from the
           instance."
       ::= { csOspfIfMetricEntry 3 }


    csOspfIfMetricValue OBJECT-TYPE
        SYNTAX   Metric
        MAX-ACCESS   read-create
        STATUS   current
        DESCRIPTION
           "The metric of using this type  of  service  on
           this interface.  The default value of the TOS 0
           Metric is 10^8 / ifSpeed."
       ::= { csOspfIfMetricEntry 4 }

    csOspfIfMetricStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { csOspfIfMetricEntry 5 }


--  OSPF Virtual Interface Table

--	The Virtual Interface Table describes the virtual
--	links that the OSPF Process is configured to
--	carry on.

    csOspfVirtIfTable OBJECT-TYPE
	SYNTAX   SEQUENCE OF CsOspfVirtIfEntry
	MAX-ACCESS   not-accessible
	STATUS   current
	DESCRIPTION
	    "Information about this router's virtual inter-
	    faces."
	REFERENCE
	 "OSPF Version  2,  Appendix  C.4   Virtual  link
	 parameters"
	::= { csOspfConf 8 }


    csOspfVirtIfEntry OBJECT-TYPE
	SYNTAX   CsOspfVirtIfEntry
	MAX-ACCESS   not-accessible
	STATUS   current
	DESCRIPTION
	    "Information about a single Virtual Interface."
	INDEX { csOrionGlobalVPNIndex, csOrionVPNVRouterIndex, 
		csOspfVirtIfAreaId, csOspfVirtIfNeighbor }
	::= { csOspfVirtIfTable 1 }

CsOspfVirtIfEntry ::=
    SEQUENCE {
	csOspfVirtIfAreaId
	      AreaID,
	csOspfVirtIfNeighbor
	      RouterID,
	csOspfVirtIfTransitDelay
	      UpToMaxAge,
	csOspfVirtIfRetransInterval
	      UpToMaxAge,
	csOspfVirtIfHelloInterval
	      HelloRange,
	csOspfVirtIfRtrDeadInterval
	      PositiveInteger,
	csOspfVirtIfState
	      INTEGER,
	csOspfVirtIfEvents
	      Counter32,
	csOspfVirtIfAuthType
	      INTEGER,
	csOspfVirtIfAuthKey
	      OCTET STRING,
	csOspfVirtIfStatus
	      RowStatus
	        }

    csOspfVirtIfAreaId OBJECT-TYPE
	SYNTAX   AreaID
	MAX-ACCESS   not-accessible
	STATUS   current
	DESCRIPTION
	    "The  Transit  Area  that  the   Virtual   Link
	    traverses.  By definition, this is not 0.0.0.0"
	::= { csOspfVirtIfEntry 1 }


    csOspfVirtIfNeighbor OBJECT-TYPE
	SYNTAX   RouterID
	MAX-ACCESS   not-accessible
	STATUS   current
	DESCRIPTION
	    "The Router ID of the Virtual Neighbor."
	::= { csOspfVirtIfEntry 2 }


    csOspfVirtIfTransitDelay OBJECT-TYPE
	SYNTAX   UpToMaxAge
	MAX-ACCESS   read-create
	STATUS   current
	DESCRIPTION
	    "The estimated number of seconds  it  takes  to
	    transmit  a link- state update packet over this
	    interface."
	DEFVAL { 1 }
	::= { csOspfVirtIfEntry 3 }


    csOspfVirtIfRetransInterval OBJECT-TYPE
	SYNTAX   UpToMaxAge
	MAX-ACCESS   read-create
	STATUS   current
	DESCRIPTION
	    "The number of seconds between  link-state  ad-
	    vertisement  retransmissions,  for  adjacencies
	    belonging to this  interface.   This  value  is
	    also used when retransmitting database descrip-
	    tion  and  link-state  request  packets.   This
	    value  should  be well over the expected round-
	    trip time."
	DEFVAL { 5 }
	::= { csOspfVirtIfEntry 4 }


    csOspfVirtIfHelloInterval OBJECT-TYPE
	SYNTAX   HelloRange
	MAX-ACCESS   read-create
	STATUS   current
	DESCRIPTION
	    "The length of time, in  seconds,  between  the
	    Hello  packets that the router sends on the in-
	    terface.  This value must be the same  for  the
	    virtual neighbor."
	DEFVAL { 10 }
	::= { csOspfVirtIfEntry 5 }


    csOspfVirtIfRtrDeadInterval OBJECT-TYPE
	SYNTAX   PositiveInteger
	MAX-ACCESS   read-create
	STATUS   current
	DESCRIPTION
	    "The number of seconds that  a  router's  Hello
	    packets  have  not been seen before it's neigh-
	    bors declare the router down.  This  should  be
	    some  multiple  of  the  Hello  interval.  This
	    value must be the same for the  virtual  neigh-
	    bor."
	DEFVAL { 60 }
	::= { csOspfVirtIfEntry 6 }


    csOspfVirtIfState OBJECT-TYPE
	SYNTAX   INTEGER    {
		      down (1),	     -- these use the same encoding
		      pointToPoint (4)     -- as the csOspfIfTable
		 }
	MAX-ACCESS   read-only
	STATUS   current
	DESCRIPTION
	    "OSPF virtual interface states."
	DEFVAL   { down }
	::= { csOspfVirtIfEntry 7 }


    csOspfVirtIfEvents OBJECT-TYPE
	SYNTAX   Counter32
	MAX-ACCESS   read-only
	STATUS   current
	DESCRIPTION
	    "The number of state changes or error events on
	    this Virtual Link"
	::= { csOspfVirtIfEntry 8 }

    csOspfVirtIfAuthType OBJECT-TYPE
	SYNTAX   INTEGER (0..255)
		      -- none (0),
		      -- simplePassword (1)
		      -- md5 (2)
		      -- reserved for specification by IANA (> 2)
	MAX-ACCESS   read-create
	STATUS   current
	DESCRIPTION
	    "The authentication type specified for a virtu-
	    al  interface.  Additional authentication types
	    may be assigned locally."
	REFERENCE
	 "OSPF Version 2, Appendix E Authentication"
	DEFVAL { 0 }	-- no authentication, by default
	::= { csOspfVirtIfEntry 9 }

    csOspfVirtIfAuthKey OBJECT-TYPE
	SYNTAX   OCTET STRING (SIZE(0..256))
	MAX-ACCESS   read-create
	STATUS   current
	DESCRIPTION
	    "If Authentication Type is simplePassword,  the
	    device  will left adjust and zero fill to 8 oc-
	    tets.

	    Note that unauthenticated  interfaces  need  no
	    authentication key, and simple password authen-
	    tication cannot use a key of more  than  8  oc-
	    tets.  Larger keys are useful only with authen-
	    tication mechanisms not specified in this docu-
	    ment.

	    When  read,  csOspfVifAuthKey  always  returns  a
	    string of length zero."
	REFERENCE
	 "OSPF Version 2, Section 9  The  Interface  Data
	 Structure"
	DEFVAL   { '0000000000000000'H }    -- 0.0.0.0.0.0.0.0
	::= { csOspfVirtIfEntry 10 }


    csOspfVirtIfStatus OBJECT-TYPE
	SYNTAX   RowStatus
	MAX-ACCESS   read-create
	STATUS   current
	DESCRIPTION
	    "This variable displays the status of  the  en-
	    try.  Setting it to 'invalid' has the effect of
	    rendering it inoperative.  The internal  effect
	    (row removal) is implementation dependent."
	::= { csOspfVirtIfEntry 11 }




--  OSPF Neighbor Table

--	The OSPF Neighbor Table describes all neighbors in
--	the locality of the subject router.

    csOspfNbrTable OBJECT-TYPE
	SYNTAX   SEQUENCE OF CsOspfNbrEntry
	MAX-ACCESS   not-accessible
	STATUS   current
	DESCRIPTION
	    "A table of non-virtual neighbor information."
	REFERENCE
	 "OSPF Version 2, Section 10  The  Neighbor  Data
	 Structure"
	::= { csOspfConf 9 }


    csOspfNbrEntry OBJECT-TYPE
	SYNTAX   CsOspfNbrEntry
	MAX-ACCESS   not-accessible
	STATUS   current
	DESCRIPTION
	    "The information regarding a single neighbor."
	REFERENCE
	 "OSPF Version 2, Section 10  The  Neighbor  Data
	 Structure"
	INDEX { csOrionGlobalVPNIndex, csOrionVPNVRouterIndex,
		csOspfNbrIpAddr, csOspfNbrAddressLessIndex }
	::= { csOspfNbrTable 1 }

CsOspfNbrEntry ::=
    SEQUENCE {
	csOspfNbrIpAddr
	      IpAddress,
	csOspfNbrAddressLessIndex
	      InterfaceIndex,
	csOspfNbrRtrId
	      RouterID,
	csOspfNbrOptions
	      Integer32,
	csOspfNbrPriority
	      DesignatedRouterPriority,
	csOspfNbrState
	      INTEGER,
	csOspfNbrEvents
	      Counter32,
	csOspfNbrLsRetransQLen
	      Gauge32,
	csOspfNbmaNbrStatus
	      RowStatus,
	csOspfNbmaNbrPermanence
	      INTEGER,
	csOspfNbrHelloSuppressed
	      TruthValue
	        }

    csOspfNbrIpAddr OBJECT-TYPE
	SYNTAX   IpAddress
	MAX-ACCESS   not-accessible
	STATUS   current
	DESCRIPTION
	    "The IP address this neighbor is using  in  its
	    IP  Source  Address.  Note that, on addressless
	    links, this will not be 0.0.0.0,  but  the  ad-
	    dress of another of the neighbor's interfaces."
	::= { csOspfNbrEntry 1 }


    csOspfNbrAddressLessIndex OBJECT-TYPE
	SYNTAX   InterfaceIndex
	MAX-ACCESS   not-accessible
	STATUS   current
	DESCRIPTION
	    "On an interface having an  IP  Address,  zero.
	    On  addressless  interfaces,  the corresponding
	    value of ifIndex in the Internet Standard  MIB.
	    On  row  creation, this can be derived from the
	    instance."
	::= { csOspfNbrEntry 2 }


    csOspfNbrRtrId OBJECT-TYPE
	SYNTAX   RouterID
	MAX-ACCESS   read-only
	STATUS   current
	DESCRIPTION
	    "A 32-bit integer (represented as a type  IpAd-
	    dress)  uniquely  identifying  the  neighboring
	    router in the Autonomous System."
	DEFVAL   { '00000000'H }    -- 0.0.0.0
	::= { csOspfNbrEntry 3 }


    csOspfNbrOptions OBJECT-TYPE
	SYNTAX   Integer32
	MAX-ACCESS   read-only
	STATUS   current
	DESCRIPTION
	    "A Bit Mask corresponding to the neighbor's op-
	    tions field.

	    Bit 0, if set, indicates that the  system  will
	    operate  on  Type of Service metrics other than
	    TOS 0.  If zero, the neighbor will  ignore  all
	    metrics except the TOS 0 metric.

	    Bit 1, if set, indicates  that  the  associated
	    area  accepts and operates on external informa-
	    tion; if zero, it is a stub area.

	    Bit 2, if set, indicates that the system is ca-
	    pable  of routing IP Multicast datagrams; i.e.,
	    that it implements the Multicast Extensions  to
	    OSPF.

	    Bit 3, if set, indicates  that  the  associated
	    area  is  an  NSSA.  These areas are capable of
	    carrying type 7 external advertisements,  which
	    are  translated into type 5 external advertise-
	    ments at NSSA borders."
	REFERENCE
	 "OSPF Version 2, Section 12.1.2 Options"
	DEFVAL { 0 }
	::= { csOspfNbrEntry 4 }


    csOspfNbrPriority OBJECT-TYPE
	SYNTAX   DesignatedRouterPriority
	MAX-ACCESS   read-create
	STATUS   current
	DESCRIPTION
	    "The priority of this neighbor in the designat-
	    ed router election algorithm.  The value 0 sig-
	    nifies that the neighbor is not eligible to be-
	    come  the  designated router on this particular
	    network."
	DEFVAL { 1 }
	::= { csOspfNbrEntry 5 }


    csOspfNbrState OBJECT-TYPE
	SYNTAX   INTEGER    {
		      down (1),
		      attempt (2),
		      init (3),
		      twoWay (4),
		      exchangeStart (5),
		      exchange (6),
		      loading (7),
		      full (8)
		 }
	MAX-ACCESS   read-only
	STATUS   current
	DESCRIPTION
	    "The State of the relationship with this Neigh-
	    bor."
	REFERENCE
	 "OSPF Version 2, Section 10.1 Neighbor States"
	DEFVAL   { down }
	::= { csOspfNbrEntry 6 }


    csOspfNbrEvents OBJECT-TYPE
	SYNTAX   Counter32
	MAX-ACCESS   read-only
	STATUS   current
	DESCRIPTION
	    "The number of times this neighbor relationship
	    has changed state, or an error has occurred."
	::= { csOspfNbrEntry 7 }


    csOspfNbrLsRetransQLen OBJECT-TYPE
	SYNTAX   Gauge32
	MAX-ACCESS   read-only
	STATUS   current
	DESCRIPTION
	    "The  current  length  of  the   retransmission
	    queue."
	::= { csOspfNbrEntry 8 }


    csOspfNbmaNbrStatus OBJECT-TYPE
	SYNTAX   RowStatus
	MAX-ACCESS   read-create
	STATUS   current
	DESCRIPTION
	    "This variable displays the status of  the  en-
	    try.  Setting it to 'invalid' has the effect of
	    rendering it inoperative.  The internal  effect
	    (row removal) is implementation dependent."
	::= { csOspfNbrEntry 9 }


    csOspfNbmaNbrPermanence OBJECT-TYPE
	SYNTAX   INTEGER    {
		      dynamic (1),	 -- learned through protocol
		      permanent (2)	-- configured address
		 }
	MAX-ACCESS   read-only
	STATUS   current
	DESCRIPTION
	    "This variable displays the status of  the  en-
	    try.   'dynamic'  and  'permanent' refer to how
	    the neighbor became known."
	DEFVAL { permanent }
	::= { csOspfNbrEntry 10 }


    csOspfNbrHelloSuppressed OBJECT-TYPE
	SYNTAX   TruthValue
	MAX-ACCESS   read-only
	STATUS   current
	DESCRIPTION
	    "Indicates whether Hellos are being  suppressed
	    to the neighbor"
	::= { csOspfNbrEntry 11 }


--  OSPF Virtual Neighbor Table

--	This table describes all virtual neighbors.
--	Since Virtual Links are configured in the
--	virtual interface table, this table is read-only.

    csOspfVirtNbrTable OBJECT-TYPE
	SYNTAX   SEQUENCE OF CsOspfVirtNbrEntry
	MAX-ACCESS   not-accessible
	STATUS   current
	DESCRIPTION
	    "A table of virtual neighbor information."
	REFERENCE
	 "OSPF Version 2, Section 15  Virtual Links"
	::= { csOspfConf 10 }


    csOspfVirtNbrEntry OBJECT-TYPE
	SYNTAX   CsOspfVirtNbrEntry
	MAX-ACCESS   not-accessible
	STATUS   current
	DESCRIPTION
	    "Virtual neighbor information."
	INDEX { csOrionGlobalVPNIndex, csOrionVPNVRouterIndex,
		csOspfVirtNbrArea, csOspfVirtNbrRtrId }
	::= { csOspfVirtNbrTable 1 }

CsOspfVirtNbrEntry ::=
    SEQUENCE {
	csOspfVirtNbrArea
	      AreaID,
	csOspfVirtNbrRtrId
	      RouterID,
	csOspfVirtNbrIpAddr
	      IpAddress,
	csOspfVirtNbrOptions
	      Integer32,
	csOspfVirtNbrState
	      INTEGER,
	csOspfVirtNbrEvents
	      Counter32,
	csOspfVirtNbrLsRetransQLen
	      Gauge32,
	csOspfVirtNbrHelloSuppressed
		TruthValue
	        }

    csOspfVirtNbrArea OBJECT-TYPE
	SYNTAX   AreaID
	MAX-ACCESS   not-accessible
	STATUS   current
	DESCRIPTION
	    "The Transit Area Identifier."
	::= { csOspfVirtNbrEntry 1 }


    csOspfVirtNbrRtrId OBJECT-TYPE
	SYNTAX   RouterID
	MAX-ACCESS   not-accessible
	STATUS   current
	DESCRIPTION
	    "A  32-bit  integer  uniquely  identifying  the
	    neighboring router in the Autonomous System."
	::= { csOspfVirtNbrEntry 2 }


    csOspfVirtNbrIpAddr OBJECT-TYPE
	SYNTAX   IpAddress
	MAX-ACCESS   read-only
	STATUS   current
	DESCRIPTION
	    "The IP address this Virtual  Neighbor  is  us-
	    ing."
	::= { csOspfVirtNbrEntry 3 }


    csOspfVirtNbrOptions OBJECT-TYPE
	SYNTAX   Integer32
	MAX-ACCESS   read-only
	STATUS   current
	DESCRIPTION
	    "A Bit Mask corresponding to the neighbor's op-
	    tions field.

	    Bit 1, if set, indicates that the  system  will
	    operate  on  Type of Service metrics other than
	    TOS 0.  If zero, the neighbor will  ignore  all
	    metrics except the TOS 0 metric.

	    Bit 2, if set, indicates  that  the  system  is
	    Network  Multicast  capable; ie, that it imple-
	    ments OSPF Multicast Routing."
	::= { csOspfVirtNbrEntry 4 }


    csOspfVirtNbrState OBJECT-TYPE
	SYNTAX   INTEGER    {
		      down (1),
		      attempt (2),
		      init (3),
		      twoWay (4),
		      exchangeStart (5),
		      exchange (6),
		      loading (7),
		      full (8)
		 }
	MAX-ACCESS   read-only
	STATUS   current
	DESCRIPTION
	    "The state of the  Virtual  Neighbor  Relation-
	    ship."
	::= { csOspfVirtNbrEntry 5 }


    csOspfVirtNbrEvents OBJECT-TYPE
	SYNTAX   Counter32
	MAX-ACCESS   read-only
	STATUS   current
	DESCRIPTION
	    "The number of  times  this  virtual  link  has
	    changed its state, or an error has occurred."
	::= { csOspfVirtNbrEntry 6 }


    csOspfVirtNbrLsRetransQLen OBJECT-TYPE
	SYNTAX   Gauge32
	MAX-ACCESS   read-only
	STATUS   current
	DESCRIPTION
	    "The  current  length  of  the   retransmission
	    queue."
	::= { csOspfVirtNbrEntry 7 }


    csOspfVirtNbrHelloSuppressed OBJECT-TYPE
	SYNTAX   TruthValue
	MAX-ACCESS   read-only
	STATUS   current
	DESCRIPTION
	    "Indicates whether Hellos are being  suppressed
	    to the neighbor"
	::= { csOspfVirtNbrEntry 8 }


--  OSPF Link State Database, External

--	The Link State Database contains the Link State
--	Advertisements from throughout the areas that the
--	device is attached to.

--	       This table is identical to the OSPF LSDB Table in
--	format, but contains only External Link State
--	       Advertisements.  The purpose is to allow external
--	LSAs to be displayed once for the router rather
--	than once in each non-stub area.

    csOspfExtLsdbTable OBJECT-TYPE
	SYNTAX   SEQUENCE OF CsOspfExtLsdbEntry
	MAX-ACCESS   not-accessible
	STATUS   current
	DESCRIPTION
	    "The OSPF Process's Links State Database."
	REFERENCE
	 "OSPF Version 2, Section 12  Link  State  Adver-
	 tisements"
	::= { csOspfConf 11 }


    csOspfExtLsdbEntry OBJECT-TYPE
	SYNTAX   CsOspfExtLsdbEntry
	MAX-ACCESS   not-accessible
	STATUS   current
	DESCRIPTION
	    "A single Link State Advertisement."
	INDEX { csOrionGlobalVPNIndex, csOrionVPNVRouterIndex,
		csOspfExtLsdbType, csOspfExtLsdbLsid, csOspfExtLsdbRouterId }
	::= { csOspfExtLsdbTable 1 }

CsOspfExtLsdbEntry ::=
    SEQUENCE {
	csOspfExtLsdbType
	      INTEGER,
	csOspfExtLsdbLsid
	      IpAddress,
	csOspfExtLsdbRouterId
	      RouterID,
	csOspfExtLsdbSequence
	      Integer32,
	csOspfExtLsdbAge
	      Integer32,
	csOspfExtLsdbChecksum
	      Integer32,
	csOspfExtLsdbAdvertisement
	      OCTET STRING
	        }

    csOspfExtLsdbType OBJECT-TYPE
	SYNTAX   INTEGER    {
		      asExternalLink (5)
		 }
	MAX-ACCESS   not-accessible
	STATUS   current
	DESCRIPTION
	    "The type  of  the  link  state  advertisement.
	    Each  link state type has a separate advertise-
	    ment format."
	REFERENCE
	 "OSPF Version 2, Appendix A.4.1 The  Link  State
	 Advertisement header"
	::= { csOspfExtLsdbEntry 1 }


    csOspfExtLsdbLsid OBJECT-TYPE
	SYNTAX   IpAddress
	MAX-ACCESS   not-accessible
	STATUS   current
	DESCRIPTION
	    "The Link State ID is an LS Type Specific field
	    containing either a Router ID or an IP Address;
	    it identifies the piece of the  routing  domain
	    that is being described by the advertisement."
	REFERENCE
	 "OSPF Version 2, Section 12.1.4 Link State ID"
	::= { csOspfExtLsdbEntry 2 }


    csOspfExtLsdbRouterId OBJECT-TYPE
	SYNTAX   RouterID
	MAX-ACCESS   not-accessible
	STATUS   current
	DESCRIPTION
	    "The 32 bit number that uniquely identifies the
	    originating router in the Autonomous System."
	REFERENCE
	 "OSPF Version 2, Appendix C.1 Global parameters"
	::= { csOspfExtLsdbEntry 3 }

--  Note that the OSPF Sequence Number is a 32 bit signed
--  integer.  It starts with the value '80000001'h,
--  or -'7FFFFFFF'h, and increments until '7FFFFFFF'h
--  Thus, a typical sequence number will be very negative.


    csOspfExtLsdbSequence OBJECT-TYPE
	SYNTAX   Integer32
	MAX-ACCESS   read-only
	STATUS   current
	DESCRIPTION
	    "The sequence number field is a  signed  32-bit
	    integer.   It  is used to detect old and dupli-
	    cate link state advertisements.  The  space  of
	    sequence  numbers  is  linearly  ordered.   The
	    larger the sequence number the more recent  the
	    advertisement."
	REFERENCE
	 "OSPF Version  2,  Section  12.1.6  LS  sequence
	 number"
	::= { csOspfExtLsdbEntry 4 }


    csOspfExtLsdbAge OBJECT-TYPE
	SYNTAX   Integer32    -- Should be 0..MaxAge
	MAX-ACCESS   read-only
	STATUS   current
	DESCRIPTION
	    "This field is the age of the link state adver-
	    tisement in seconds."
	REFERENCE
	 "OSPF Version 2, Section 12.1.1 LS age"
	::= { csOspfExtLsdbEntry 5 }


    csOspfExtLsdbChecksum OBJECT-TYPE
	SYNTAX   Integer32
	MAX-ACCESS   read-only
	STATUS   current
	DESCRIPTION
	    "This field is the  checksum  of  the  complete
	    contents  of  the  advertisement, excepting the
	    age field.  The age field is excepted  so  that
	    an   advertisement's  age  can  be  incremented
	    without updating the  checksum.   The  checksum
	    used  is  the same that is used for ISO connec-
	    tionless datagrams; it is commonly referred  to
	    as the Fletcher checksum."
	REFERENCE
	 "OSPF Version 2, Section 12.1.7 LS checksum"
	::= { csOspfExtLsdbEntry 6 }


    csOspfExtLsdbAdvertisement OBJECT-TYPE
	SYNTAX   OCTET STRING (SIZE(36))
	MAX-ACCESS   read-only
	STATUS   current
	DESCRIPTION
	    "The entire Link State Advertisement, including
	    its header."
	REFERENCE
	 "OSPF Version 2, Section 12  Link  State  Adver-
	 tisements"
	::= { csOspfExtLsdbEntry 7 }


--
--      The OSPF Area Aggregate Table
--
--      This table replaces the OSPF Area Summary Table, being an
--      extension of that for CIDR routers.

    csOspfAreaAggregateTable OBJECT-TYPE
        SYNTAX   SEQUENCE OF CsOspfAreaAggregateEntry
        MAX-ACCESS   not-accessible
        STATUS   current
        DESCRIPTION
           "A range of IP addresses  specified  by  an  IP
           address/IP  network  mask  pair.   For example,
           class B address range of X.X.X.X with a network
           mask  of  255.255.0.0 includes all IP addresses
           from X.X.0.0  to  X.X.255.255.   Note  that  if
           ranges  are configured such that one range sub-
           sumes  another  range  (e.g.,   10.0.0.0   mask
           255.0.0.0  and  10.1.0.0 mask 255.255.0.0), the
           most specific match is the preferred one."
       REFERENCE
          "OSPF Version 2, Appendix C.2  Area parameters"
      ::= { csOspfConf 12 }


    csOspfAreaAggregateEntry OBJECT-TYPE
        SYNTAX   CsOspfAreaAggregateEntry
        MAX-ACCESS   not-accessible
        STATUS   current
        DESCRIPTION
           "A range of IP addresses  specified  by  an  IP
           address/IP  network  mask  pair.   For example,
           class B address range of X.X.X.X with a network
           mask  of  255.255.0.0 includes all IP addresses
           from X.X.0.0  to  X.X.255.255.   Note  that  if
           ranges are range configured such that one range
           subsumes another  range  (e.g.,  10.0.0.0  mask
           255.0.0.0  and  10.1.0.0 mask 255.255.0.0), the
           most specific match is the preferred one."
       REFERENCE
          "OSPF Version 2, Appendix C.2  Area parameters"
      INDEX { csOrionGlobalVPNIndex, csOrionVPNVRouterIndex,
	csOspfAreaAggregateAreaID, csOspfAreaAggregateLsdbType,
	csOspfAreaAggregateNet, csOspfAreaAggregateMask }
      ::= { csOspfAreaAggregateTable 1 }


CsOspfAreaAggregateEntry ::=
    SEQUENCE {
        csOspfAreaAggregateAreaID
            AreaID,
        csOspfAreaAggregateLsdbType
            INTEGER,
        csOspfAreaAggregateNet
            IpAddress,
        csOspfAreaAggregateMask
            IpAddress,
        csOspfAreaAggregateStatus
            RowStatus,
        csOspfAreaAggregateEffect
            INTEGER
              }

    csOspfAreaAggregateAreaID OBJECT-TYPE
        SYNTAX   AreaID
        MAX-ACCESS   not-accessible
        STATUS   current
        DESCRIPTION
           "The Area the Address Aggregate is to be  found
           within."
       REFERENCE
          "OSPF Version 2, Appendix C.2 Area parameters"
      ::= { csOspfAreaAggregateEntry 1 }


    csOspfAreaAggregateLsdbType OBJECT-TYPE
        SYNTAX   INTEGER    {
                    summaryLink (3),
                    nssaExternalLink (7)
                  }
        MAX-ACCESS   not-accessible
        STATUS   current
        DESCRIPTION
           "The type of the Address Aggregate.  This field
           specifies  the  Lsdb type that this Address Ag-
           gregate applies to."
       REFERENCE
          "OSPF Version 2, Appendix A.4.1 The  Link  State
          Advertisement header"
      ::= { csOspfAreaAggregateEntry 2 }


    csOspfAreaAggregateNet OBJECT-TYPE
        SYNTAX   IpAddress
        MAX-ACCESS   not-accessible
        STATUS   current
        DESCRIPTION
           "The IP Address of the Net or Subnet  indicated
           by the range."
       REFERENCE
          "OSPF Version 2, Appendix C.2 Area parameters"
      ::= { csOspfAreaAggregateEntry 3 }


    csOspfAreaAggregateMask OBJECT-TYPE
        SYNTAX   IpAddress
        MAX-ACCESS   not-accessible
        STATUS   current
        DESCRIPTION
           "The Subnet Mask that pertains to  the  Net  or
           Subnet."
       REFERENCE
          "OSPF Version 2, Appendix C.2 Area parameters"
      ::= { csOspfAreaAggregateEntry 4 }


    csOspfAreaAggregateStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { csOspfAreaAggregateEntry 5 }


    csOspfAreaAggregateEffect OBJECT-TYPE
        SYNTAX   INTEGER    {
                    advertiseMatching (1),
                    doNotAdvertiseMatching (2)
                  }
        MAX-ACCESS   read-create
        STATUS   current
        DESCRIPTION
           "Subnets subsumed by ranges either trigger  the
           advertisement  of  the indicated aggregate (ad-
           vertiseMatching), or result in the subnet's not
           being advertised at all outside the area."
       DEFVAL   { advertiseMatching }
       ::= { csOspfAreaAggregateEntry 6 }

--
--      The OSPF Import Policy Table
--	this table identifies the import policies that are applied by ospf
--

    csOspfImpPolTable OBJECT-TYPE
        SYNTAX   SEQUENCE OF CsOspfImpPolEntry
        MAX-ACCESS   not-accessible
        STATUS   current
        DESCRIPTION
           "A set of Import Policies (see csImpPolTable) that
           are applied by ospf."
      ::= { csOspfConf 13 }

    csOspfImpPolEntry OBJECT-TYPE
        SYNTAX   CsOspfImpPolEntry
        MAX-ACCESS   not-accessible
        STATUS   current
        DESCRIPTION
           "Each entry represents a single import policy
           applied by the ospf layer on a Virtual Router."
      INDEX { csOrionGlobalVPNIndex, csOrionVPNVRouterIndex, csOspfImpPolId }
      ::= { csOspfImpPolTable 1 }


    CsOspfImpPolEntry ::=
	SEQUENCE {
	csOspfImpPolId
		Integer32,
	csOspfImpPolStatus
		RowStatus
	}

    csOspfImpPolId OBJECT-TYPE
	SYNTAX   Integer32
	MAX-ACCESS   not-accessible
	STATUS   current
	DESCRIPTION
		"The Import Policy (see the corresponding entry in 
		csImpPolTable) that is applied to this Virtual Router."
    ::= { csOspfImpPolEntry 1 }

    csOspfImpPolStatus OBJECT-TYPE
	SYNTAX  RowStatus
	MAX-ACCESS  read-create
	STATUS  current
	DESCRIPTION
		"The RowStatus object for this table.  This is used to
		add and delete entries from this table."
    ::= { csOspfImpPolEntry 2 }

--
--      The OSPF Export Policy Table
--	this table identifies the import policies that are applied by ospf
--

    csOspfExpPolTable OBJECT-TYPE
        SYNTAX   SEQUENCE OF CsOspfExpPolEntry
        MAX-ACCESS   not-accessible
        STATUS   current
        DESCRIPTION
           "A set of Export Policies (see csExpPolTable) that
           are applied by ospf."
      ::= { csOspfConf 14 }

    csOspfExpPolEntry OBJECT-TYPE
        SYNTAX   CsOspfExpPolEntry
        MAX-ACCESS   not-accessible
        STATUS   current
        DESCRIPTION
           "Each entry represents a single import policy
           applied by the ospf layer on a Virtual Router."
      INDEX { csOrionGlobalVPNIndex, csOrionVPNVRouterIndex, csOspfExpPolId }
      ::= { csOspfExpPolTable 1 }


    CsOspfExpPolEntry ::=
	SEQUENCE {
	csOspfExpPolId
		Integer32,
	csOspfExpPolStatus
		RowStatus
	}

    csOspfExpPolId OBJECT-TYPE
	SYNTAX   Integer32
	MAX-ACCESS   not-accessible
	STATUS   current
	DESCRIPTION
		"The Export Policy (see the corresponding entry in 
		csExpPolTable) that is applied to this Virtual Router."
    ::= { csOspfExpPolEntry 1 }

    csOspfExpPolStatus OBJECT-TYPE
	SYNTAX  RowStatus
	MAX-ACCESS  read-create
	STATUS  current
	DESCRIPTION
		"The RowStatus object for this table.  This is used to
		add and delete entries from this table."
    ::= { csOspfExpPolEntry 2 }

--
-- Trap Support Objects
--         The following are support objects for the OSPF traps.

csOspfTrapControl OBJECT IDENTIFIER ::= { csOspfTrap 1 }

    csOspfSetTrap OBJECT-TYPE
        SYNTAX   OCTET STRING (SIZE(4))
        MAX-ACCESS   read-write
        STATUS   current
        DESCRIPTION
           "A four-octet string serving as a bit  map  for
           the trap events defined by the OSPF traps. This
           object is used to enable and  disable  specific
           OSPF   traps   where  a  1  in  the  bit  field
           represents enabled.  The right-most bit  (least
           significant) represents trap 0."
       ::= { csOspfTrapControl 1 }


    csOspfConfigErrorType OBJECT-TYPE
        SYNTAX   INTEGER   {
                    badVersion (1),
                    areaMismatch (2),
                    unknownNbmaNbr (3), -- Router is Dr eligible
                    unknownVirtualNbr (4),
                    authTypeMismatch(5),
                    authFailure (6),
                    netMaskMismatch (7),
                    helloIntervalMismatch (8),
                    deadIntervalMismatch (9),
                    optionMismatch (10) }
        MAX-ACCESS   read-only
        STATUS   current
        DESCRIPTION
           "Potential types  of  configuration  conflicts.
           Used  by the csOspfConfigError and csOspfConfigVir-
           tError traps."
   ::= { csOspfTrapControl 2 }


    csOspfPacketType OBJECT-TYPE
        SYNTAX   INTEGER   {
                    hello (1),
                    dbDescript (2),
                    lsReq (3),
                    lsUpdate (4),
                    lsAck (5) }
        MAX-ACCESS   read-only
        STATUS   current
        DESCRIPTION
           "OSPF packet types."
   ::= { csOspfTrapControl 3 }


    csOspfPacketSrc OBJECT-TYPE
        SYNTAX   IpAddress
        MAX-ACCESS   read-only
        STATUS   current
        DESCRIPTION
           "The IP address of an inbound packet that  can-
           not be identified by a neighbor instance."
       ::= { csOspfTrapControl 4 }




--
--  RIP Management Information Base
--
--  RIP Global Stats Table
--

    csRipGlobalStatTable OBJECT-TYPE
	SYNTAX   SEQUENCE OF CsRipGlobalStatEntry
	MAX-ACCESS   not-accessible
	STATUS   current
	DESCRIPTION
	 "This table contains per-VR level stats for RIP.  These
	 counters are intended to facilitate debugging quickly changing
	 routes or failing neighbors." 
	::= { csRipStats 1 }

    csRipGlobalStatEntry OBJECT-TYPE
	SYNTAX   CsRipGlobalStatEntry
	MAX-ACCESS   not-accessible
	STATUS   current
	DESCRIPTION
	 "Each entry contains a set of statistics for a specific Virtual 
	 Router."
	INDEX { csOrionGlobalVPNIndex, csOrionVPNVRouterIndex }
	::= { csRipGlobalStatTable 1 }

    CsRipGlobalStatEntry ::=
	SEQUENCE {
	      csRipGlobalRouteChanges
		Counter32,
	      csRipGlobalQueries
		Counter32
    }

    csRipGlobalRouteChanges OBJECT-TYPE
	SYNTAX   Counter32
	MAX-ACCESS   read-only
	STATUS   current
	DESCRIPTION
	    "The number of route changes made to the IP Route
	    Database by RIP.  This does not include the refresh
	    of a route's age."
	::= { csRipGlobalStatEntry 1 }

    csRipGlobalQueries OBJECT-TYPE
	SYNTAX   Counter32
	MAX-ACCESS   read-only
	STATUS   current
	DESCRIPTION
	    "The number of responses sent to RIP queries
	    from other systems."
	::= { csRipGlobalStatEntry 2 }

--
-- The RIP Interface Stats Table.
--

    csRipIfStatTable OBJECT-TYPE
	SYNTAX   SEQUENCE OF CsRipIfStatEntry
	MAX-ACCESS   not-accessible
	STATUS   current
	DESCRIPTION
	    "A list of subnets which require separate
	    status monitoring in RIP."
	::= { csRipStats 2 }

    csRipIfStatEntry OBJECT-TYPE
	SYNTAX   CsRipIfStatEntry
	MAX-ACCESS   not-accessible
	STATUS   current
	DESCRIPTION
	 "A Single Routing Domain in a single Subnet."
	INDEX { csOrionGlobalVPNIndex, csOrionVPNVRouterIndex,
		csOrionVIfIndex	 }
	::= { csRipIfStatTable 1 }

    CsRipIfStatEntry ::=
	SEQUENCE {
	      csRipIfStatRcvBadPackets
		Counter32,
	      csRipIfStatRcvBadRoutes
		Counter32,
	      csRipIfStatSentUpdates
		Counter32
    }

    csRipIfStatRcvBadPackets OBJECT-TYPE
	SYNTAX   Counter32
	MAX-ACCESS   read-only
	STATUS   current
	DESCRIPTION
	    "The number of RIP response packets received by
	    the RIP process which were subsequently discarded
	    for any reason (e.g. a version 0 packet, or an
	    unknown command type)."
	::= { csRipIfStatEntry 1 }

    csRipIfStatRcvBadRoutes OBJECT-TYPE
	SYNTAX   Counter32
	MAX-ACCESS   read-only
	STATUS   current
	DESCRIPTION
	    "The number of routes, in valid RIP packets,
	    which were ignored for any reason (e.g. unknown
	    address family, or invalid metric)."
	::= { csRipIfStatEntry 2 }

    csRipIfStatSentUpdates OBJECT-TYPE
	SYNTAX   Counter32
	MAX-ACCESS   read-only
	STATUS   current
	DESCRIPTION
	    "The number of triggered RIP updates actually
	    sent on this interface.  This explicitly does
	    NOT include full updates sent containing new
	    information."
	::= { csRipIfStatEntry 3 }

--
-- The RIP Global Configuration Table
--

    csRipGlobalConfTable OBJECT-TYPE
	SYNTAX  SEQUENCE OF CsRipGlobalConfEntry
	MAX-ACCESS  not-accessible
	STATUS  current
	DESCRIPTION
	    "A table of virtual router-specific configuration parameters."
	::= { csRipConf 1 }

    csRipGlobalConfEntry OBJECT-TYPE
	SYNTAX  CsRipGlobalConfEntry
	MAX-ACCESS  not-accessible
	STATUS  current
	DESCRIPTION
	    "Each entry contains a set of configuration specific to a 
	    single virtual router."
	INDEX { csOrionGlobalVPNIndex, csOrionVPNVRouterIndex }
	::= { csRipGlobalConfTable 1 }

    CsRipGlobalConfEntry ::=
	SEQUENCE {
	csRipGlobalConfStatus
		INTEGER,
	csRipGlobalConfAgeTime
		INTEGER,
	csRipGlobalConfPerUpdateInt
		INTEGER,
	csRipGlobalConfJitterUpdateStatus
		INTEGER,
	csRipGlobalConfRfc1058CalcStatus
		INTEGER,
	csRipGlobalConfReqOnStartup
		INTEGER,
	csRipGlobalConfRowStatus
		RowStatus,
	csRipGlobalConfLogAreaFlag
		Unsigned32,
	csRipGlobalConfLogLevelFlag
		Unsigned32
	}

    csRipGlobalConfStatus OBJECT-TYPE
	SYNTAX	INTEGER {
		enable  (1),
		disable (2)
	}
	MAX-ACCESS	read-create
	STATUS		current
	DESCRIPTION
	    "Enable/Disable the use of RIP on this Virtual Router."
	DEFVAL { enable }
	::= { csRipGlobalConfEntry 1 }

    csRipGlobalConfAgeTime OBJECT-TYPE
	SYNTAX	INTEGER (1..10000)   -- need range
	MAX-ACCESS	read-create
	STATUS		current
	DESCRIPTION
	    ""
	::= { csRipGlobalConfEntry 2 }

    csRipGlobalConfPerUpdateInt OBJECT-TYPE
	SYNTAX	INTEGER (1..10000)   -- need range
	MAX-ACCESS	read-create
	STATUS		current
	DESCRIPTION
	    ""
	::= { csRipGlobalConfEntry 3 }

    csRipGlobalConfJitterUpdateStatus OBJECT-TYPE
	SYNTAX	INTEGER {
		enable  (1),
		disable (2)
	}
	MAX-ACCESS	read-create
	STATUS		current
	DESCRIPTION
	    "Enable/Disable the use of the Jitter Update feature"
	DEFVAL { enable }
	::= { csRipGlobalConfEntry 4 }

    csRipGlobalConfRfc1058CalcStatus OBJECT-TYPE
	SYNTAX	INTEGER {
		enable  (1),
		disable (2)
	}
	MAX-ACCESS	read-create
	STATUS		current
	DESCRIPTION
	    "Enable/Disable the use of the route metric calculation
	    defined in rfc1058."
	DEFVAL { enable }
	::= { csRipGlobalConfEntry 5 }

    csRipGlobalConfReqOnStartup OBJECT-TYPE
	SYNTAX	INTEGER {
		enable  (1),
		disable (2)
	}
	MAX-ACCESS	read-create
	STATUS		current
	DESCRIPTION
	    "Enable/Disable the use of the request on startup feature."
	DEFVAL { enable }
	::= { csRipGlobalConfEntry 6 }

	csRipGlobalConfRowStatus OBJECT-TYPE
	SYNTAX		RowStatus
	MAX-ACCESS	read-create
	STATUS		current
	DESCRIPTION
		"The RowStatus object for this object. This is used to 
		add/delete rows from this table. Setting it to create and
		go creates RIP on this Virtual Router.  Setting it to destroy 
		removes RIP from this Virtual Router."
	::= { csRipGlobalConfEntry 7 }

	csRipGlobalConfLogAreaFlag OBJECT-TYPE
	SYNTAX		Unsigned32
	MAX-ACCESS	read-create
	STATUS		current
	DESCRIPTION
		"Each bit within this object enables loggin for a specific
		area within RIP.  Below is a list of the different areas
		available for logging within RIP and their corresponding 
		bits identifiers.

			area				bit
		------------------------------------------------------
			packet                0
			policy                1 

		end of description."
	DEFVAL { 0 }
	::= { csRipGlobalConfEntry 8 }

	csRipGlobalConfLogLevelFlag OBJECT-TYPE
	SYNTAX		Unsigned32
	MAX-ACCESS	read-create
	STATUS		current
	DESCRIPTION
		"Each bit within this object enables logging at a specific
		level for RIP.  Below is a list of the different log levels
		available and their corresponding bits identifiers.

			area				bit
		------------------------------------------------------
			critical              0
			error                 1 
			warning               2
			information           3
			debug                 4
		end of description."
	DEFVAL { 0 }
	::= { csRipGlobalConfEntry 9 }

--
-- The RIP Interface Configuration Table.
--

    csRipIfConfTable OBJECT-TYPE
	SYNTAX   SEQUENCE OF CsRipIfConfEntry
	MAX-ACCESS   not-accessible
	STATUS   current
	DESCRIPTION
	    "A list of virtual interfaces which require separate
	    configuration in RIP."
	::= { csRipConf 2 }

   csRipIfConfEntry OBJECT-TYPE
	SYNTAX   CsRipIfConfEntry
	MAX-ACCESS   not-accessible
	STATUS   current
	DESCRIPTION
	 "A Single Routing Domain in a single Subnet."
	INDEX { csOrionGlobalVPNIndex, csOrionVPNVRouterIndex,
		csOrionVIfIndex	 }
	::= { csRipIfConfTable 1 }

    CsRipIfConfEntry ::=
	SEQUENCE {
	csRipIfConfStatus
		INTEGER,
	csRipIfConfSend
		INTEGER,
	csRipIfConfReceiveV1
		INTEGER,
	csRipIfConfReceiveV2
		INTEGER,
	csRipIfConfSendDefRoute
		INTEGER,
	csRipIfConfRcvDefRoute 
		INTEGER,
	csRipIfConfSplitHorizon 
		INTEGER,
	csRipIfConfPoisonReverse 
		INTEGER,
	csRipIfConfFlashUpdate 
		INTEGER,
	csRipIfConfRipV1Compatibility 
		INTEGER,
	csRipIfConfAuthPassword 
		DisplayString,
	csRipIfConfRowStatus
		RowStatus
	}

    csRipIfConfStatus OBJECT-TYPE
	SYNTAX	INTEGER {
		enable  (1),
		disable (2)
	}
	MAX-ACCESS	read-create
	STATUS		current
	DESCRIPTION
	    "Enable/Disable the use of RIP on this Virtual Interface."
	DEFVAL { disable }
	::= { csRipIfConfEntry 1 }

    csRipIfConfSend OBJECT-TYPE
	SYNTAX	INTEGER {
		enable  (1),
		disable (2)
		}
	MAX-ACCESS	read-create
	STATUS		current
	DESCRIPTION
	    "Enable/Disable the sending of RIP advertisements on this
	     Virtual Interface."
	DEFVAL { enable }
	::= { csRipIfConfEntry 2 }

    csRipIfConfReceiveV1 OBJECT-TYPE
	SYNTAX	INTEGER {
		enable  (1),
		disable (2)
	}
	MAX-ACCESS	read-create
	STATUS		current
	DESCRIPTION
	    "Enable/Disable the receiving of RIP V1 advertisements on this
	    Virtual Interface."
	DEFVAL { enable }
	::= { csRipIfConfEntry 3 }

    csRipIfConfReceiveV2 OBJECT-TYPE
	SYNTAX	INTEGER {
		enable  (1),
		disable (2)
	}
	MAX-ACCESS	read-create
	STATUS		current
	DESCRIPTION
	    "Enable/Disable the receiving of RIP V2 advertisements on this
	    Virtual Interface."
	DEFVAL { enable }
	::= { csRipIfConfEntry 4 }

    csRipIfConfSendDefRoute OBJECT-TYPE
	SYNTAX	INTEGER {
		enable  (1),
		disable (2)
	}
	MAX-ACCESS	read-create
	STATUS		current
	DESCRIPTION
	    "Enable/Disable the advertisement of default routes."
	DEFVAL { enable }
	::= { csRipIfConfEntry 5 }

    csRipIfConfRcvDefRoute OBJECT-TYPE
	SYNTAX	INTEGER {
		enable  (1),
		disable (2)
	}
	MAX-ACCESS	read-create
	STATUS		current
	DESCRIPTION
	    "Enable/Disable the acceptance of advertised default routes."
	DEFVAL { enable }
	::= { csRipIfConfEntry 6 }

    csRipIfConfSplitHorizon OBJECT-TYPE
	SYNTAX	INTEGER {
		enable  (1),
		disable (2)
	}
	MAX-ACCESS	read-create
	STATUS		current
	DESCRIPTION
	    "Enable/Disable the Split Horizon feature."
	DEFVAL { enable }
	::= { csRipIfConfEntry 7 }

    csRipIfConfPoisonReverse OBJECT-TYPE
	SYNTAX	INTEGER {
		enable  (1),
		disable (2)
	}
	MAX-ACCESS	read-create
	STATUS		current
	DESCRIPTION
	    "Enable/Disable the Poison Reverse feature."
	DEFVAL { enable }
	::= { csRipIfConfEntry 8 }

    csRipIfConfFlashUpdate OBJECT-TYPE
	SYNTAX	INTEGER {
		enable  (1),
		disable (2)
	}
	MAX-ACCESS	read-create
	STATUS		current
	DESCRIPTION
	    "Enable/Disable the Flash Update feature."
	DEFVAL { enable }
	::= { csRipIfConfEntry 9 }

    csRipIfConfRipV1Compatibility OBJECT-TYPE
	SYNTAX	INTEGER {
		enable  (1),
		disable (2)
	}
	MAX-ACCESS	read-create
	STATUS		current
	DESCRIPTION
	    "Enable/Disable compatibility with RIPv1 routers."
	DEFVAL { enable }
	::= { csRipIfConfEntry 10 }

    csRipIfConfAuthPassword OBJECT-TYPE
	SYNTAX DisplayString
	MAX-ACCESS	read-create
	STATUS		current
	DESCRIPTION
	    "The password used in RIPv2 authentication.  This object
	    will return a zero length string in response to GET or
	    GETNEXT requests."
	::= { csRipIfConfEntry 11 }

	csRipIfConfRowStatus OBJECT-TYPE
	SYNTAX		RowStatus
	MAX-ACCESS	read-create
	STATUS		current
	DESCRIPTION
		"RowStatus for this object. This is used to add/delete rows 
		from this table. Setting it to create and go creates RIP on 
		this Virtual Interface.  Setting it to destroy removes RIP 
		from this Virtual Interface."
	::= { csRipIfConfEntry 12 }
--
--      The Rip Import Policy Table
--	this table identifies the import policies that are applied by rip
--

    csRipImpPolTable OBJECT-TYPE
        SYNTAX   SEQUENCE OF CsRipImpPolEntry
        MAX-ACCESS   not-accessible
        STATUS   current
        DESCRIPTION
           "A set of Export Policies (see csExpPolTable) that
           are applied by rip."
      ::= { csRipConf 3 }

    csRipImpPolEntry OBJECT-TYPE
        SYNTAX   CsRipImpPolEntry
        MAX-ACCESS   not-accessible
        STATUS   current
        DESCRIPTION
           "Each entry represents a single import policy
           applied by the rip layer on a Virtual Router."
      INDEX { csOrionGlobalVPNIndex, csOrionVPNVRouterIndex, csRipImpPolId }
      ::= { csRipImpPolTable 1 }


    CsRipImpPolEntry ::=
	SEQUENCE {
	csRipImpPolId
		Integer32,
	csRipImpPolStatus
		RowStatus
	}

    csRipImpPolId OBJECT-TYPE
	SYNTAX   Integer32 (1..65535)
	MAX-ACCESS   not-accessible
	STATUS   current
	DESCRIPTION
		"The Import Policy (see the corresponding entry in 
		csImpPolTable) that is applied to this Virtual Router."
    ::= { csRipImpPolEntry 1 }

    csRipImpPolStatus OBJECT-TYPE
	SYNTAX  RowStatus
	MAX-ACCESS  read-create
	STATUS  current
	DESCRIPTION
		"The RowStatus object for this table.  This is used to
		add and delete entries from this table."
    ::= { csRipImpPolEntry 2 }


--
--      The RIP Export Policy Table
--	this table identifies the import policies that are applied by rip
--

    csRipExpPolTable OBJECT-TYPE
        SYNTAX   SEQUENCE OF CsRipExpPolEntry
        MAX-ACCESS   not-accessible
        STATUS   current
        DESCRIPTION
           "A set of Export Policies (see csExpPolTable) that
           are applied by rip."
      ::= { csRipConf 4 }

    csRipExpPolEntry OBJECT-TYPE
        SYNTAX   CsRipExpPolEntry
        MAX-ACCESS   not-accessible
        STATUS   current
        DESCRIPTION
           "Each entry represents a single import policy
           applied by the rip layer on a Virtual Router."
      INDEX { csOrionGlobalVPNIndex, csOrionVPNVRouterIndex, csRipExpPolId }
      ::= { csRipExpPolTable 1 }


    CsRipExpPolEntry ::=
	SEQUENCE {
	csRipExpPolId
		Integer32,
	csRipExpPolStatus
		RowStatus
	}

    csRipExpPolId OBJECT-TYPE
	SYNTAX   Integer32 (1..65535)
	MAX-ACCESS   not-accessible
	STATUS   current
	DESCRIPTION
		"The Export Policy (see the corresponding entry in 
		csExpPolTable) that is applied to this Virtual Router."
    ::= { csRipExpPolEntry 1 }

    csRipExpPolStatus OBJECT-TYPE
	SYNTAX  RowStatus
	MAX-ACCESS  read-create
	STATUS  current
	DESCRIPTION
		"The RowStatus object for this table.  This is used to
		add and delete entries from this table."
    ::= { csRipExpPolEntry 2 }


--
-- the TCP generic table
--

    csOrionVPNVRouterTcpTable OBJECT-TYPE
	SYNTAX  SEQUENCE OF CsOrionVPNVRouterTcpEntry
	MAX-ACCESS  not-accessible
	STATUS  current
	DESCRIPTION
		"The table of TCP Parameters."
	::= { csOrionTcp 1 }

    csOrionVPNVRouterTcpEntry OBJECT-TYPE
	SYNTAX CsOrionVPNVRouterTcpEntry
 		    MAX-ACCESS not-accessible
	STATUS  current
	DESCRIPTION
	    "The entry of the table of TCP Parameters."
	INDEX   { csOrionGlobalVPNIndex, csOrionVPNVRouterIndex }
	::= { csOrionVPNVRouterTcpTable 1 }

    CsOrionVPNVRouterTcpEntry ::=
	SEQUENCE {
 	csOrionVPNVRouterTcpRtoAlgorithm	
		INTEGER,
 	csOrionVPNVRouterTcpRtoMin
     		Integer32,
	csOrionVPNVRouterTcpRtoMax
		Integer32,
	csOrionVPNVRouterTcpMaxConn
		Integer32,
	csOrionVPNVRouterTcpActiveOpens
		Counter32,
	csOrionVPNVRouterTcpPassiveOpens
		Counter32,
	csOrionVPNVRouterTcpAttemptFails
		Counter32,
	csOrionVPNVRouterTcpEstabResets
		Counter32,
	csOrionVPNVRouterTcpCurrEstab
		Gauge32,
	csOrionVPNVRouterTcpInSegs
		Counter32,
	csOrionVPNVRouterTcpOutSegs
		Counter32,
	csOrionVPNVRouterTcpRetransSegs
		Counter32,
	csOrionVPNVRouterTcpInErrs
		Counter32,
	csOrionVPNVRouterTcpOutRsts
		Counter32

	}

    csOrionVPNVRouterTcpRtoAlgorithm OBJECT-TYPE
	SYNTAX  INTEGER {
		      other(1),    -- none of the following

		      constant(2), -- a constant rto
		      rsre(3),     -- MIL-STD-1778, Appendix B
		      vanj(4)	-- Van Jacobson's algorithm [10]
		}
	MAX-ACCESS  read-only
	STATUS  current
	DESCRIPTION
		"The algorithm used to determine the timeout value
		used for retransmitting unacknowledged octets."
	::= { csOrionVPNVRouterTcpEntry 1 }

    csOrionVPNVRouterTcpRtoMin OBJECT-TYPE
	SYNTAX Integer32
	MAX-ACCESS  read-only
	STATUS  current
	DESCRIPTION
		"The minimum value permitted by a TCP
		implementation for the retransmission timeout,
		measured in milliseconds.  More refined semantics
		for objects of this type depend upon the algorithm
		used to determine the retransmission timeout.  In
		particular, when the timeout algorithm is rsre(3),
		an object of this type has the semantics of the
		LBOUND quantity described in RFC 793."

	::= { csOrionVPNVRouterTcpEntry 2 }


    csOrionVPNVRouterTcpRtoMax OBJECT-TYPE
	SYNTAX Integer32
	MAX-ACCESS  read-only
	STATUS  current
	DESCRIPTION
		"The maximum value permitted by a TCP
		implementation for the retransmission timeout,
		measured in milliseconds.  More refined semantics
		for objects of this type depend upon the algorithm
		used to determine the retransmission timeout.  In
		particular, when the timeout algorithm is rsre(3),
		an object of this type has the semantics of the
		UBOUND quantity described in RFC 793."
	::= { csOrionVPNVRouterTcpEntry 3 }

    csOrionVPNVRouterTcpMaxConn OBJECT-TYPE
	SYNTAX Integer32
	MAX-ACCESS  read-only
	STATUS  current
	DESCRIPTION
		"The limit on the total number of TCP connections
		the entity can support.  In entities where the
		maximum number of connections is dynamic, this
		object should contain the value -1."
	::= { csOrionVPNVRouterTcpEntry 4 }

    csOrionVPNVRouterTcpActiveOpens OBJECT-TYPE
	SYNTAX  Counter32
	MAX-ACCESS  read-only
	STATUS  current
	DESCRIPTION
		"The number of times TCP connections have made a
		direct transition to the SYN-SENT state from the
		CLOSED state."
	::= { csOrionVPNVRouterTcpEntry 5 }

    csOrionVPNVRouterTcpPassiveOpens OBJECT-TYPE
	SYNTAX  Counter32
	MAX-ACCESS  read-only
	STATUS  current
	DESCRIPTION
		"The number of times TCP connections have made a
		direct transition to the SYN-RCVD state from the
		LISTEN state."
	::= { csOrionVPNVRouterTcpEntry 6 }


    csOrionVPNVRouterTcpAttemptFails OBJECT-TYPE
	SYNTAX  Counter32
	MAX-ACCESS  read-only
	STATUS  current
	DESCRIPTION
		"The number of times TCP connections have made a
		direct transition to the CLOSED state from either
		the SYN-SENT state or the SYN-RCVD state, plus the
		number of times TCP connections have made a direct
		transition to the LISTEN state from the SYN-RCVD
		state."
	::= { csOrionVPNVRouterTcpEntry 7 }

    csOrionVPNVRouterTcpEstabResets OBJECT-TYPE
	SYNTAX  Counter32
	MAX-ACCESS  read-only
	STATUS  current
	DESCRIPTION
		"The number of times TCP connections have made a
		direct transition to the CLOSED state from either
		the ESTABLISHED state or the CLOSE-WAIT state."
	::= { csOrionVPNVRouterTcpEntry 8 }

    csOrionVPNVRouterTcpCurrEstab OBJECT-TYPE
	SYNTAX  Gauge32
	MAX-ACCESS  read-only
	STATUS  current
	DESCRIPTION
		"The number of TCP connections for which the
		current state is either ESTABLISHED or CLOSE-
		WAIT."
	::= { csOrionVPNVRouterTcpEntry 9 }

    csOrionVPNVRouterTcpInSegs OBJECT-TYPE
	SYNTAX  Counter32
	MAX-ACCESS  read-only
	STATUS  current
	DESCRIPTION
		"The total number of segments received, including
		those received in error.  This count includes
		segments received on currently established
		connections."
	::= { csOrionVPNVRouterTcpEntry 10 }

    csOrionVPNVRouterTcpOutSegs OBJECT-TYPE
	SYNTAX  Counter32
	MAX-ACCESS  read-only
	STATUS  current
  		DESCRIPTION
		"The total number of segments sent, including
		those on current connections but excluding those
		containing only retransmitted octets."
	::= { csOrionVPNVRouterTcpEntry 11 }

    csOrionVPNVRouterTcpRetransSegs OBJECT-TYPE
	SYNTAX  Counter32
	MAX-ACCESS  read-only
	STATUS  current
	DESCRIPTION
		"The total number of segments retransmitted - that
		is, the number of TCP segments transmitted
		containing one or more previously transmitted
		octets."
	::= { csOrionVPNVRouterTcpEntry 12 }


   	csOrionVPNVRouterTcpInErrs OBJECT-TYPE
	SYNTAX  Counter32
	MAX-ACCESS  read-only
	STATUS  current
	DESCRIPTION
		"The total number of segments received in error
		(e.g., bad TCP checksums)."
	::= { csOrionVPNVRouterTcpEntry 13 }

    csOrionVPNVRouterTcpOutRsts OBJECT-TYPE
	SYNTAX  Counter32
	MAX-ACCESS  read-only
	STATUS  current
	DESCRIPTION
		"The number of TCP segments sent containing the
		RST flag."
	::= { csOrionVPNVRouterTcpEntry 14 }


-- the TCP Connection table

    csOrionVPNVRouterTcpConnTable OBJECT-TYPE
	SYNTAX  SEQUENCE OF CsOrionVPNVRouterTcpConnEntry
	MAX-ACCESS  not-accessible
	STATUS  current
	DESCRIPTION
		"The table of addressing information relevant to
		Orion's IP addresses."
	::= { csOrionTcp 2 }

    csOrionVPNVRouterTcpConnEntry OBJECT-TYPE
	SYNTAX CsOrionVPNVRouterTcpConnEntry
	MAX-ACCESS not-accessible
	STATUS  current
	DESCRIPTION
		"The addressing information for one of this
		Orion's IP addresses."
	INDEX   { 	csOrionGlobalVPNIndex,
		csOrionVPNVRouterIndex,
		csOrionVPNVRouterTcpConnLocalAddress,
		csOrionVPNVRouterTcpConnLocalPort ,
		csOrionVPNVRouterTcpConnRemAddress,
		csOrionVPNVRouterTcpConnRemPort }

	::= { csOrionVPNVRouterTcpConnTable 1 }


    CsOrionVPNVRouterTcpConnEntry ::=
	SEQUENCE {
	csOrionVPNVRouterTcpConnState
		INTEGER,
	csOrionVPNVRouterTcpConnLocalAddress
		IpAddress,
	csOrionVPNVRouterTcpConnLocalPort
		Integer32 (0..65535),
	csOrionVPNVRouterTcpConnRemAddress
		IpAddress,
	csOrionVPNVRouterTcpConnRemPort
 		Integer32 (0..65535)
	}

    csOrionVPNVRouterTcpConnState OBJECT-TYPE
	SYNTAX  INTEGER {
		closed(1),
		listen(2),
		synSent(3),
		synReceived(4),
		established(5),
		finWait1(6),
		finWait2(7),
		closeWait(8),
		lastAck(9),
		closing(10),
		timeWait(11),
		deleteTCB(12)
	}
	MAX-ACCESS  read-write
	STATUS  current
	DESCRIPTION
		"The state of this TCP connection.
		The only value which may be set by a management
		station is deleteTCB(12).  Accordingly, it is
		appropriate for an agent to return a `badValue'
		response if a management station attempts to set
		this object to any other value.

		If a management station sets this object to the
		value deleteTCB(12), then this has the effect of
		deleting the TCB (as defined in RFC 793) of the
		corresponding connection on the managed node,
		resulting in immediate termination of the
		connection.

		As an implementation-specific option, a RST
		segment may be sent from the managed node to the
		other TCP endpoint (note however that RST egments
		are not sent reliably)."
	::= { csOrionVPNVRouterTcpConnEntry 1 }

    csOrionVPNVRouterTcpConnLocalAddress OBJECT-TYPE
	SYNTAX  IpAddress
	MAX-ACCESS  read-only
	STATUS  current
	DESCRIPTION
		"The local IP address for this TCP connection.  In
		the case of a connection in the listen state which
		is willing to accept connections for any IP
		interface associated with the node, the value
		0.0.0.0 is used."
	        ::= { csOrionVPNVRouterTcpConnEntry 2 }

    csOrionVPNVRouterTcpConnLocalPort OBJECT-TYPE
	SYNTAX Integer32 (0..65535)
	MAX-ACCESS  read-only
	STATUS  current
	DESCRIPTION
		"The local port number for this TCP connection."
	::= { csOrionVPNVRouterTcpConnEntry 3 }

    csOrionVPNVRouterTcpConnRemAddress OBJECT-TYPE
	SYNTAX  IpAddress
	MAX-ACCESS  read-only
	STATUS  current
	DESCRIPTION
		"The remote IP address for this TCP connection."
	::= { csOrionVPNVRouterTcpConnEntry 4 }

    csOrionVPNVRouterTcpConnRemPort OBJECT-TYPE
	SYNTAX Integer32 (0..65535)
	MAX-ACCESS  read-only
	STATUS  current
	DESCRIPTION
		"The remote port number for this TCP connection."
	::= { csOrionVPNVRouterTcpConnEntry 5 }


------------------------------------------------------------------------------
--
--	       This set of objects instrument the UDP layer within each VR
--
------------------------------------------------------------------------------

-- the UDP Stats table

    csOrionVPNVRouterUdpTable OBJECT-TYPE
	SYNTAX  SEQUENCE OF CsOrionVPNVRouterUdpEntry
	MAX-ACCESS  not-accessible
	STATUS  current
	DESCRIPTION
		"The table of addressing information relevant to
		Orion's IP addresses."
	::= { csOrionUdp 1 }

    csOrionVPNVRouterUdpEntry OBJECT-TYPE
	SYNTAX CsOrionVPNVRouterUdpEntry
	MAX-ACCESS not-accessible
	STATUS  current
	DESCRIPTION
		"The addressing information for one of this
		Orion's IP addresses."
	INDEX   { csOrionGlobalVPNIndex, csOrionVPNVRouterIndex }
	::= { csOrionVPNVRouterUdpTable 1 }

    CsOrionVPNVRouterUdpEntry ::=
	SEQUENCE {
	csOrionVPNVRouterUdpInDatagrams
		Counter32,
	csOrionVPNVRouterUdpNoPorts
		Counter32,
	csOrionVPNVRouterUdpInErrors
		Counter32,
	csOrionVPNVRouterUdpOutDatagrams
		Counter32
	}

    csOrionVPNVRouterUdpInDatagrams OBJECT-TYPE
	SYNTAX  Counter32
	MAX-ACCESS  read-only
	STATUS  current
	DESCRIPTION
		"The total number of UDP datagrams delivered to
		UDP users."
	::= { csOrionVPNVRouterUdpEntry 1 }

    csOrionVPNVRouterUdpNoPorts OBJECT-TYPE
	SYNTAX  Counter32
	MAX-ACCESS  read-only
	STATUS  current
	DESCRIPTION
		"The total number of received UDP datagrams for
		which there was no application at the destination
		port."
	::= { csOrionVPNVRouterUdpEntry 2 }

    csOrionVPNVRouterUdpInErrors OBJECT-TYPE
	SYNTAX  Counter32
	MAX-ACCESS  read-only
	STATUS  current
	DESCRIPTION
		"The number of received UDP datagrams that could
		not be delivered for reasons other than the lack
		of an application at the destination port."
	::= { csOrionVPNVRouterUdpEntry 3 }

    csOrionVPNVRouterUdpOutDatagrams OBJECT-TYPE
	SYNTAX  Counter32
	MAX-ACCESS  read-only
	STATUS  current
	DESCRIPTION
		"The total number of UDP datagrams sent from this
		entity."
	::= { csOrionVPNVRouterUdpEntry 4 }

-- the UDP Listener table

    csOrionVPNVRouterUdpListenerTable OBJECT-TYPE
	SYNTAX  SEQUENCE OF CsOrionVPNVRouterUdpListenerEntry
	MAX-ACCESS  not-accessible
	STATUS  current
	DESCRIPTION
		"The table of addressing information relevant to
		Orion's IP addresses."
	::= { csOrionUdp 2 }

    csOrionVPNVRouterUdpListenerEntry OBJECT-TYPE
	SYNTAX CsOrionVPNVRouterUdpListenerEntry
	MAX-ACCESS not-accessible
	STATUS  current
	DESCRIPTION
		"The addressing information for one of this
		Orion's IP addresses."
	INDEX   { csOrionGlobalVPNIndex,
		    csOrionVPNVRouterIndex,
		    csOrionVPNVRouterUdpListenerLocalAddress,
		    csOrionVPNVRouterUdpListenerLocalPort }
	::= { csOrionVPNVRouterUdpListenerTable 1 }

    CsOrionVPNVRouterUdpListenerEntry ::=
	SEQUENCE {
	csOrionVPNVRouterUdpListenerLocalAddress
		IpAddress,
	csOrionVPNVRouterUdpListenerLocalPort
		Integer32 (0..65535)
	}

    csOrionVPNVRouterUdpListenerLocalAddress OBJECT-TYPE
	SYNTAX  IpAddress
	MAX-ACCESS  read-only
	STATUS  current
	DESCRIPTION
		"The local IP address for this UDP listener.  In
		the case of a UDP listener which is willing to
		accept datagrams for any IP interface associated
		with the node, the value 0.0.0.0 is used."
	::= { csOrionVPNVRouterUdpListenerEntry 1 }

    csOrionVPNVRouterUdpListenerLocalPort OBJECT-TYPE
	SYNTAX Integer32 (0..65535)
	MAX-ACCESS  read-only
	STATUS  current
	DESCRIPTION
		"The local port number for this UDP listener."
	::= { csOrionVPNVRouterUdpListenerEntry 2 }


------------------------------------------------------------------------------
--
--	      This set of objects manages the BGP protocol 
--
------------------------------------------------------------------------------

-- the Bgp General table

    csBgpGenTable OBJECT-TYPE
	SYNTAX  SEQUENCE OF CsBgpGenEntry
	MAX-ACCESS  not-accessible
	STATUS  current
	DESCRIPTION
		"This table contains general, virtual router specific,
		BGP information."
	::= { csBgpGen 1 }

    csBgpGenEntry OBJECT-TYPE
	SYNTAX CsBgpGenEntry
	MAX-ACCESS not-accessible
	STATUS  current
	DESCRIPTION
		"Each entry contains general, virtual router specific
		BGP information for a single virtual router."
	INDEX   { csOrionGlobalVPNIndex, csOrionVPNVRouterIndex }
	::= { csBgpGenTable 1 }

    CsBgpGenEntry ::=
	SEQUENCE {
	csBgpGenStatus
		INTEGER,
	csBgpGenLocalAS
		Integer32,
	csBgpGenClearConn
		IpAddress,
	csBgpGenDefaultMetric
		Integer32,
	csBgpGenDefaultLocalPref
		Integer32,
	csBgpGenConfedId
		Integer32,
	csBgpGenDampEnable
		INTEGER,
	csBgpGenDampHalfLife
		Integer32,
	csBgpGenDampReuse
		Integer32,
	csBgpGenDampSuppress
		Integer32,
	csBgpGenDampMaxSuppress
		Integer32,
	csBgpGenRowStatus
		RowStatus,
        csBgpGenLogAreaFlag
                Unsigned32,
        csBgpGenLogLevelFlag
                Unsigned32
	}

    csBgpGenStatus OBJECT-TYPE
	SYNTAX  INTEGER {
		enable  (1),
		disable (2)
	}
	MAX-ACCESS  read-create
	STATUS  current
	DESCRIPTION
		"This object controls the operation of BGP as a whole
		on this virtual router."
	::= { csBgpGenEntry 1 }

    csBgpGenLocalAS OBJECT-TYPE
	SYNTAX  Integer32 (1..65535)
	MAX-ACCESS  read-create
	STATUS  current
	DESCRIPTION
		"The local autonomous system number of this virtual router.

		 This object will have a value of 0 if bgp is disabled.
		 If bgp is enabled, this object cannot be set to 0."
	::= { csBgpGenEntry 2 }

    csBgpGenClearConn OBJECT-TYPE
	SYNTAX  IpAddress
	MAX-ACCESS  read-create
	STATUS  current
	DESCRIPTION
		"This object is used to clear one of the existing BGP
		connections.  To clear a single connection, enter the
		ip address of the remote end of the connection.  

		When this object is read (get, getnext),
		the value 0.0.0.0 will be returned."
	::= { csBgpGenEntry 3 }

    csBgpGenDefaultMetric OBJECT-TYPE
	SYNTAX  Integer32 (-1..65535) 
	MAX-ACCESS  read-create
	STATUS  current
	DESCRIPTION
		"The default metric used by the system.
		 default value is -1 which indicates that
		 the metric is not configured"
        DEFVAL { -1 } 
	::= { csBgpGenEntry 4 }

    csBgpGenDefaultLocalPref OBJECT-TYPE
	SYNTAX  Integer32 (0..255)
	MAX-ACCESS  read-create
	STATUS  current
	DESCRIPTION
		"Default local preference of this BGP speaker
		 default value is 100."
	DEFVAL { 100 }
	::= { csBgpGenEntry 5 }

    csBgpGenConfedId OBJECT-TYPE
	SYNTAX  Integer32 (-1 | 1..65535)
	MAX-ACCESS  read-create
	STATUS  current
	DESCRIPTION
		"The ConfedId of this system.
		 -1 indicates no confedId has been configured."
	DEFVAL { -1 }
	::= { csBgpGenEntry 6 }

    csBgpGenDampEnable OBJECT-TYPE
        SYNTAX  INTEGER {
			enable (1),
			disable (2)
	}
        MAX-ACCESS  read-create
        STATUS  current
        DESCRIPTION
                "This attribute is used to enable/disable
		 route flap damping on this virtual router."
        DEFVAL { disable }
        ::= { csBgpGenEntry 7 }

    csBgpGenDampHalfLife OBJECT-TYPE
        SYNTAX  Integer32
        MAX-ACCESS  read-create
        STATUS  current
        DESCRIPTION
                "The time in seconds after which the penalty
                 associated with a flapping route is reduced by one half.
                 default value is 15 mintues."
        DEFVAL { 900 }
        ::= { csBgpGenEntry 8 }

    csBgpGenDampReuse OBJECT-TYPE
        SYNTAX  Integer32
        MAX-ACCESS  read-create
        STATUS  current
        DESCRIPTION
                "If the penalty of a flapping route that has been
                 suppressed falls below the value configured by this
                 attribute, then the route is unsuppressed. Default is 2."
	DEFVAL { 2 }
        ::= { csBgpGenEntry 9 }

    csBgpGenDampSuppress OBJECT-TYPE
        SYNTAX  Integer32
        MAX-ACCESS  read-create
        STATUS  current
        DESCRIPTION
                "If the penalty of a flapping route exceeds the
                 value configured by this atttribute, the route
                 is suppressed. Default is 3."
        DEFVAL { 3 }
        ::= { csBgpGenEntry 10 }

    csBgpGenDampMaxSuppress OBJECT-TYPE
        SYNTAX  Integer32
        MAX-ACCESS  read-create
        STATUS  current
        DESCRIPTION
                "The maximum time that the route can be suppressed.
                 Default is 16."
	DEFVAL { 16 }
        ::= { csBgpGenEntry 11 }

    csBgpGenRowStatus OBJECT-TYPE
	SYNTAX  RowStatus
	MAX-ACCESS  read-create
	STATUS  current
	DESCRIPTION
		"The RowStatus object for this table.  This is
		used to add & remove rows from this table."
	::= { csBgpGenEntry 12 }

     csBgpGenLogAreaFlag OBJECT-TYPE
        SYNTAX          Unsigned32
        MAX-ACCESS      read-create
        STATUS          current
        DESCRIPTION
                "Each bit within this object enables loggin for a specific
                area within BGP.  Below is a list of the different areas
                available for logging within BGP and their corresponding
                bits identifiers.

                        area                            bit
                ------------------------------------------------------
                        packet                0

                end of description."
        DEFVAL { 0 }
        ::= { csBgpGenEntry 13 }

     csBgpGenLogLevelFlag OBJECT-TYPE
        SYNTAX          Unsigned32
        MAX-ACCESS      read-create
        STATUS          current
        DESCRIPTION
                "Each bit within this object enables logging at a specific
                level for BGP.  Below is a list of the different log levels
                available and their corresponding bits identifiers.

                        area                            bit
                ------------------------------------------------------
                        critical              0
                        error                 1
                        warning               2
                        information           3
                        debug                 4
                end of description. "
        DEFVAL { 0 }
        ::= { csBgpGenEntry 14 }



--
-- The BGP Neighbor Table
--

    csBgpNbrTable OBJECT-TYPE
	SYNTAX  SEQUENCE OF CsBgpNbrEntry
	MAX-ACCESS  not-accessible
	STATUS  current
	DESCRIPTION
		"This table contains information about the BGP Neighbors
		on each virtual router."
	::= { csBgpNbr 1 }

    csBgpNbrEntry OBJECT-TYPE
	SYNTAX CsBgpNbrEntry
	MAX-ACCESS not-accessible
	STATUS  current
	DESCRIPTION
		"Each entry contains information about a single neighbor
		on a single virtual router."
	INDEX   { csOrionGlobalVPNIndex, csOrionVPNVRouterIndex, csBgpNbrAddr }
	::= { csBgpNbrTable 1 }

    CsBgpNbrEntry ::=
	SEQUENCE {
	csBgpNbrAddr
		IpAddress,
	csBgpNbrId
		IpAddress,
	csBgpNbrState
		INTEGER,
	csBgpNbrAdminStatus
		INTEGER,
	csBgpNbrRemoteAS
		INTEGER,
	csBgpNbrMd5Password
		OCTET STRING,
	csBgpNbrRowStatus
		RowStatus,
 	csBgpNbrGroupNm
		DisplayString,
	csBgpNbrHoldTimeConfigured
		Integer32,
	csBgpNbrLocalAddr
		IpAddress,
	csBgpNbrNextHopSelf
		INTEGER,
	csBgpNbrMhopGw
		IpAddress,
	csBgpNbrPassive
		INTEGER
	}

    csBgpNbrAddr OBJECT-TYPE
	SYNTAX IpAddress
	MAX-ACCESS  not-accessible
	STATUS  current
	DESCRIPTION
		"The remote IP address of this entry's BGP neighbor."
	::= { csBgpNbrEntry 1 }

    csBgpNbrId OBJECT-TYPE
	SYNTAX  IpAddress
	MAX-ACCESS  read-only
	STATUS  current
	DESCRIPTION
		"The BGP Identifier of this entry's BGP neighbor."
	::= { csBgpNbrEntry 2 }

    csBgpNbrState OBJECT-TYPE
	SYNTAX  INTEGER {
		idle	(1),
		connect (2),
		active	(3),
		opensent (4),
		openconfirm (5),
		established (6)
	}
	MAX-ACCESS  read-only
	STATUS  current
	DESCRIPTION
		"The BGP Peer connection state."
	::= { csBgpNbrEntry 3 }

    csBgpNbrAdminStatus OBJECT-TYPE
	SYNTAX  INTEGER {
		stop  (1),
		start (2)
	}
	MAX-ACCESS  read-create
	STATUS  current
	DESCRIPTION
		"The desired state of the BGP connection.
		A transition from 'stop' to 'start' will
		cause the BGP Start Event to be generated.
		A transition from 'start' to 'stop' will
		cause the BGP Stop Event to be generated.
		This parameter can be used to restart BGP
		peer connections."
	DEFVAL { start }
	::= { csBgpNbrEntry 4 }

    csBgpNbrRemoteAS OBJECT-TYPE
	SYNTAX  INTEGER (1..65535)
	MAX-ACCESS  read-create
	STATUS  current
	DESCRIPTION
		"The remote autonomous system number."
	::= { csBgpNbrEntry 5 }

    csBgpNbrMd5Password OBJECT-TYPE
	SYNTAX  OCTET STRING (SIZE(0..255))
	MAX-ACCESS  read-create
	STATUS  current
	DESCRIPTION
		"The Md5 password used to authenticate messages
		exchanged with this neighbor. 
		If the neighbor belongs to a NbrGroup and
		this attribute is not configured, the Nbr inherits
		the group level value of this attribute."
	DEFVAL { "" }
	::= { csBgpNbrEntry 6 }

    csBgpNbrRowStatus OBJECT-TYPE
	SYNTAX  RowStatus
	MAX-ACCESS  read-create
	STATUS  current
	DESCRIPTION
		"The RowStatus object for this table.  This is
		used to add & remove rows from this table."
	::= { csBgpNbrEntry 7 }

    csBgpNbrGroupNm OBJECT-TYPE
        SYNTAX  DisplayString ( SIZE(0..31))
        MAX-ACCESS  read-create
        STATUS  current
        DESCRIPTION
                "The Group to which the peer belongs. If the
		 peer is not configured to any group an
		 empty string is returned."
        ::= { csBgpNbrEntry 8 }


    csBgpNbrHoldTimeConfigured OBJECT-TYPE
	SYNTAX  Integer32 (-1 | 20..65534)
	MAX-ACCESS  read-create
	STATUS  current
	DESCRIPTION
		"The configured holdtime to use with this Neighbor
		 default value of -1 indicates that this attribute
		 has not been configured (default value used will
		 be 180 seconds). 
		 If the neighbor belongs to a NbrGroup and this
		 attribute is not set, the Nbr inherits the
		 group level value of this attribute."
	DEFVAL { -1 }
	::= { csBgpNbrEntry 9 }

    csBgpNbrLocalAddr OBJECT-TYPE
	SYNTAX  IpAddress
	MAX-ACCESS  read-create
	STATUS  current
	DESCRIPTION
		"The IpAddress to be used at the local end of the
		 connection with the bgp peer. If set to 0.0.0.0
	         it indicates that the LocalAddr is not configured.
		 If the Nbr belongs to a NbrGroup, group level 
		 value of this attribute will override any value
		 configured here."
	DEFVAL { 0 }
	::= { csBgpNbrEntry 10 }

    csBgpNbrNextHopSelf OBJECT-TYPE
	SYNTAX  INTEGER { notconfigured (-1),
			  enable(1),
			  disable (2) }
	MAX-ACCESS  read-create
	STATUS  current
	DESCRIPTION
		"To enable/disable this system to be the next
		 hopself for an ebgp session with this peer.
		 default is -1 which indicates not configured.
		 If the neighbor belongs to a NbrGroup and this
		 attribute is not set, the Nbr inherits the
		 group level value of this attribute."
	DEFVAL { notconfigured }
	::= { csBgpNbrEntry 11 }

    csBgpNbrMhopGw OBJECT-TYPE
	SYNTAX  IpAddress
	MAX-ACCESS  read-create
	STATUS  current
	DESCRIPTION
		" To specify the gateway address if this ebgp
		  neighbor is not directly connected to this
		  system. If the MhopGw is set to 0.0.0.0, it
		  indicates that the MhopGw is not configured.
		  If the Nbr belongs to a NbrGroup and this
		  attribute is not set, the Nbr inherits the
		  group level value of this attribute."  
	DEFVAL { 0 }
	::= { csBgpNbrEntry 12 }


    csBgpNbrPassive OBJECT-TYPE
	SYNTAX  INTEGER {
			enable (1),
			disable (2)
	 } 	
	MAX-ACCESS  read-create
	STATUS  current
	DESCRIPTION
		" If this attribute is set to enable then this BGP speaker
		  will not try to open a connection with the neighbor. Instead
		  it will wait for the neighbor to initiate a connection."
        DEFVAL {disable}
	::= { csBgpNbrEntry 13 }

--
-- The BGP Neighbor Import policy table
--

    csBgpNbrImpPolTable OBJECT-TYPE
	SYNTAX  SEQUENCE OF CsBgpNbrImpPolEntry
	MAX-ACCESS  not-accessible
	STATUS  current
	DESCRIPTION
		"This table is used to configure the import policies applied 
		to each BGP neighbor on each virtual router."
	::= { csBgpNbr 2 }

    csBgpNbrImpPolEntry OBJECT-TYPE
	SYNTAX CsBgpNbrImpPolEntry
	MAX-ACCESS not-accessible
	STATUS  current
	DESCRIPTION
		"Each entry contains information about a single policy
		applied to a single virtual router's BGP neighbor."
	INDEX   { csOrionGlobalVPNIndex, csOrionVPNVRouterIndex, 
		csBgpNbrAddr, csBgpNbrImpPolId }
	::= { csBgpNbrImpPolTable 1 }

    CsBgpNbrImpPolEntry ::=
	SEQUENCE {
	csBgpNbrImpPolId
		Integer32,
	csBgpNbrImpPolRowStatus
		RowStatus
	}

    csBgpNbrImpPolId OBJECT-TYPE
	SYNTAX  Integer32 (1..65535)
	MAX-ACCESS  not-accessible
	STATUS  current
	DESCRIPTION
		"The identifier of the policy to apply to this neighbor.
		This identifies an entry in either the csBgpImpImpPolTable
		or the csBgpExpImpPolTable. If the Nbr belongs to a Group
		any import policies defined at the neighbor level overrides	
	        group level import policies. If no import policies are
	        defined at the neighbor level group level policies are
		inherited."
	::= { csBgpNbrImpPolEntry 1 }

    csBgpNbrImpPolRowStatus OBJECT-TYPE
	SYNTAX  RowStatus
	MAX-ACCESS  read-create
	STATUS  current
	DESCRIPTION
		"The RowStatus object for this table.  This is
		used to add & remove rows from this table."
	::= { csBgpNbrImpPolEntry 2 }

--
-- The BGP Neighbor Export policy table
--

    csBgpNbrExpPolTable OBJECT-TYPE
	SYNTAX  SEQUENCE OF CsBgpNbrExpPolEntry
	MAX-ACCESS  not-accessible
	STATUS  current
	DESCRIPTION
		"This table is used to configure the import policies applied 
		to each BGP neighbor on each virtual router."
	::= { csBgpNbr 3 }

    csBgpNbrExpPolEntry OBJECT-TYPE
	SYNTAX CsBgpNbrExpPolEntry
	MAX-ACCESS not-accessible
	STATUS  current
	DESCRIPTION
		"Each entry contains information about a single policy
		applied to a single virtual router's BGP neighbor."
	INDEX   { csOrionGlobalVPNIndex, csOrionVPNVRouterIndex, 
		csBgpNbrAddr, csBgpNbrExpPolId }
	::= { csBgpNbrExpPolTable 1 }

    CsBgpNbrExpPolEntry ::=
	SEQUENCE {
	csBgpNbrExpPolId
		Integer32,
	csBgpNbrExpPolRowStatus
		RowStatus
	}

    csBgpNbrExpPolId OBJECT-TYPE
	SYNTAX  Integer32 (1..65535)
	MAX-ACCESS  not-accessible
	STATUS  current
	DESCRIPTION
		"The identifier of the policy to apply to this neighbor.
		This identifies an entry in either the csBgpExpExpPolTable
		or the csBgpExpExpPolTable. 
		If the Nbr belongs to a NbrGroup then any Export policies
		configured to this Nbr are ignored.i.e. Export policies
		defined at the group level takes precedence"
	::= { csBgpNbrExpPolEntry 1 }

    csBgpNbrExpPolRowStatus OBJECT-TYPE
	SYNTAX  RowStatus
	MAX-ACCESS  read-create
	STATUS  current
	DESCRIPTION
		"The RowStatus object for this table.  This is
		used to add & remove rows from this table."
	::= { csBgpNbrExpPolEntry 2 }

--
-- The BGP Confederation AS table
--

    csBgpConfedASTable OBJECT-TYPE
        SYNTAX  SEQUENCE OF CsBgpConfedASEntry
        MAX-ACCESS  not-accessible
        STATUS  current
        DESCRIPTION
		" This table maintains a list of AS's which belong
		  to the same confederation as this virtual router."
        ::= { csBgpConfed 1 }


    csBgpConfedASEntry OBJECT-TYPE
        SYNTAX CsBgpConfedASEntry
        MAX-ACCESS not-accessible
        STATUS  current
        DESCRIPTION
		" Each entry contains as AS number which belongs to the
		  same confederation as this virtual router."
        INDEX   { csOrionGlobalVPNIndex, csOrionVPNVRouterIndex,
                  csBgpConfedAS }
        ::= { csBgpConfedASTable 1 }

    CsBgpConfedASEntry ::=
        SEQUENCE {
	csBgpConfedAS
		Integer32,
	csBgpConfedASRowStatus
                RowStatus
        }

    csBgpConfedAS OBJECT-TYPE
        SYNTAX  Integer32 (1..65535)
        MAX-ACCESS  not-accessible
        STATUS  current
        DESCRIPTION
		"This attribute identifies the AS which belongs to the
		 same confederation as this virtual router."
        ::= { csBgpConfedASEntry 1 }

    csBgpConfedASRowStatus OBJECT-TYPE
        SYNTAX  RowStatus
        MAX-ACCESS  read-create
        STATUS  current
        DESCRIPTION
                "The RowStatus object for this table.  This is
                used to add & remove rows from this table."
        ::= { csBgpConfedASEntry 2 }

--
-- The BGP Network table
--

    csBgpNetworkTable OBJECT-TYPE
        SYNTAX  SEQUENCE OF CsBgpNetworkEntry
        MAX-ACCESS  not-accessible
        STATUS  current
        DESCRIPTION
                " This table maintains a list of IP Address/Mask which 
		  can be distributed from IGP into BGP."
        ::= { csBgpNetwork 1 }


    csBgpNetworkEntry OBJECT-TYPE
        SYNTAX CsBgpNetworkEntry
        MAX-ACCESS not-accessible
        STATUS  current
        DESCRIPTION
                " Each entry contains an IP Address/Mask that need
		  to be sent via BGP."
        INDEX   { csOrionGlobalVPNIndex, csOrionVPNVRouterIndex,
                  csBgpNetworkAddr, csBgpNetworkMask }
        ::= { csBgpNetworkTable 1 }

    CsBgpNetworkEntry ::=
        SEQUENCE {  
	csBgpNetworkAddr
		IpAddress,
	csBgpNetworkMask
		IpAddress,
        csBgpNetworkRowStatus
		RowStatus
        }

    csBgpNetworkAddr OBJECT-TYPE
        SYNTAX  IpAddress
        MAX-ACCESS  not-accessible
        STATUS  current
        DESCRIPTION
                "The IP Address that needs to be redistrubted to BGP."
        ::= { csBgpNetworkEntry 1 }

    csBgpNetworkMask OBJECT-TYPE
        SYNTAX  IpAddress
        MAX-ACCESS  not-accessible
        STATUS  current
        DESCRIPTION
                "The IP Mask of the csBgpNetworkAddr that needs to 
	         be redistrubted to BGP."
        ::= { csBgpNetworkEntry 2 }

    csBgpNetworkRowStatus OBJECT-TYPE
        SYNTAX  RowStatus
        MAX-ACCESS  read-create
        STATUS  current
        DESCRIPTION
                "The RowStatus object for this table.  This is
                used to add & remove rows from this table."
        ::= { csBgpNetworkEntry 3 }

--
-- The BGP Neighbor Group Table
--

    csBgpNbrGroupTable OBJECT-TYPE
        SYNTAX  SEQUENCE OF CsBgpNbrGroupEntry
        MAX-ACCESS  not-accessible
        STATUS  current
        DESCRIPTION
                "This table contains information about the BGP Group's
		 on a single virtual router."
        ::= { csBgpNbrGroup 1 }

    csBgpNbrGroupEntry OBJECT-TYPE
        SYNTAX CsBgpNbrGroupEntry
        MAX-ACCESS not-accessible
        STATUS  current
        DESCRIPTION
                "Each entry contains information about a single group
                on a single virtual router."
        INDEX   { csOrionGlobalVPNIndex, csOrionVPNVRouterIndex,
		  csBgpNbrGroupName }
        ::= { csBgpNbrGroupTable 1 }

    CsBgpNbrGroupEntry ::=
        SEQUENCE {
        csBgpNbrGroupName
                DisplayString,
        csBgpNbrGroupAdminStatus
                INTEGER,
        csBgpNbrGroupRemoteAS
                INTEGER,
        csBgpNbrGroupMd5Password
                OCTET STRING,
        csBgpNbrGroupRowStatus
                RowStatus,
        csBgpNbrGroupHoldTimeConfigured
                Integer32,
        csBgpNbrGroupLocalAddr
                IpAddress,
        csBgpNbrGroupNextHopSelf
                INTEGER,
        csBgpNbrGroupMhopGw
                IpAddress
        }

    csBgpNbrGroupName OBJECT-TYPE
        SYNTAX DisplayString ( SIZE(1..31))
        MAX-ACCESS  not-accessible
        STATUS  current
        DESCRIPTION
                "The Name of the BGP Group"
        ::= { csBgpNbrGroupEntry 1 }

    csBgpNbrGroupAdminStatus OBJECT-TYPE
        SYNTAX  INTEGER {
                stop  (1),
                start (2)
        }
        MAX-ACCESS  read-create
        STATUS  current
        DESCRIPTION
                "The desired state of the BGP connection.
                A transition from 'stop' to 'start' will
                cause the BGP Start Event to be generated.
                A transition from 'start' to 'stop' will
                cause the BGP Stop Event to be generated.
                This parameter can be used to restart BGP
                peer connections in the bgp group."
        DEFVAL { start }
        ::= { csBgpNbrGroupEntry 2 }

    csBgpNbrGroupRemoteAS OBJECT-TYPE
        SYNTAX  INTEGER (1..65535)
        MAX-ACCESS  read-create
        STATUS  current
        DESCRIPTION
                "The remote autonomous system number of the group."
        ::= { csBgpNbrGroupEntry 3 }

    csBgpNbrGroupMd5Password OBJECT-TYPE
        SYNTAX  OCTET STRING (SIZE(0..255))
        MAX-ACCESS  read-create
        STATUS  current
        DESCRIPTION
                "The Md5 password used to authenticate messages
                exchanged with the neighbors defined in the group.
		This attribute can be over-ridden for each 
		Nbr in the group by setting the csBgpNbrMd5Password
		Attribute"
        DEFVAL { "" }
        ::= { csBgpNbrGroupEntry 4 }

    csBgpNbrGroupRowStatus OBJECT-TYPE
        SYNTAX  RowStatus
        MAX-ACCESS  read-create
        STATUS  current
        DESCRIPTION
                "The RowStatus object for this table.  This is
                used to add & remove rows from this table."
        ::= { csBgpNbrGroupEntry 5 }


    csBgpNbrGroupHoldTimeConfigured OBJECT-TYPE
        SYNTAX  Integer32 (-1 | 20..65535)
        MAX-ACCESS  read-create
        STATUS  current
        DESCRIPTION
                "The configured holdtime to be used by the neighbors
		 in this group. default value is -1 which indicates
		 this is not configured and the neighbors in the
		 group will be use a value of 180 seconds.
		 This attribute can be over-ridden for each Nbr
		 in the group by setting the csBgpNbrHoldTimeConfigured
		 attribute.  " 
	DEFVAL { -1 }
        ::= { csBgpNbrGroupEntry 6 }

    csBgpNbrGroupLocalAddr OBJECT-TYPE
        SYNTAX  IpAddress
        MAX-ACCESS  read-create
        STATUS  current
        DESCRIPTION
                "The IpAddress to be used at the local end of the
                 connection with the bgp peers in this group. If the LocalAddr
                 is set to 0.0.0.0, it indicates that the LocalAddr
                 is not configured."
	DEFVAL { 0 }
        ::= { csBgpNbrGroupEntry 7 }

    csBgpNbrGroupNextHopSelf OBJECT-TYPE
        SYNTAX  INTEGER { notconfigured (-1),
                          enable(1),
                          disable (2) }
        MAX-ACCESS  read-create
        STATUS  current
        DESCRIPTION
                "To enable/disable this system to be the next
                 hopself for an ebgp session with the bgp peers
		 in this group. 
                 default is -1 which indicates not configured
		 and disabled.
		 This attribute can be over-ridden for each Nbr in the
		 group by setting the csBgpNbrNextHopSelf attribute."
	DEFVAL { notconfigured }
        ::= { csBgpNbrGroupEntry 8 }

    csBgpNbrGroupMhopGw OBJECT-TYPE
        SYNTAX  IpAddress
        MAX-ACCESS  read-create
        STATUS  current
        DESCRIPTION
                " To specify the gateway address if the ebgp
                  neighbors belonging to this group are not directly 
		  connected to this system. 
		  If the MhopGw is set to 0.0.0.0, it
                  indicates that the MhopGw is not configured.
		  This attribute can be over-ridden for each Nbr in 
		  the group by setting the csBgpNbrMhopGw attribute."
	DEFVAL { 0 }
        ::= { csBgpNbrGroupEntry 9 }



--
-- The BGP Neighbor Group Import policy table
--

    csBgpNbrGroupImpPolTable OBJECT-TYPE
        SYNTAX  SEQUENCE OF CsBgpNbrGroupImpPolEntry
        MAX-ACCESS  not-accessible
        STATUS  current
        DESCRIPTION
                "This table is used to configure the import policies applied
                to each BGP Group on each virtual router."
        ::= { csBgpNbrGroup 2 }

    csBgpNbrGroupImpPolEntry OBJECT-TYPE
        SYNTAX CsBgpNbrGroupImpPolEntry
        MAX-ACCESS not-accessible
        STATUS  current
        DESCRIPTION
                "Each entry contains information about a single policy
                applied to a single virtual router's BGP Group."
        INDEX   { csOrionGlobalVPNIndex, csOrionVPNVRouterIndex,
                csBgpNbrGroupName, csBgpNbrGroupImpPolId }
        ::= { csBgpNbrGroupImpPolTable 1 }

    CsBgpNbrGroupImpPolEntry ::=
        SEQUENCE {
        csBgpNbrGroupImpPolId
                Integer32,
        csBgpNbrGroupImpPolRowStatus
                RowStatus
        }

    csBgpNbrGroupImpPolId OBJECT-TYPE
        SYNTAX  Integer32 (1..65535)
        MAX-ACCESS  not-accessible
        STATUS  current
        DESCRIPTION
                "The identifier of the policy to apply to this group.
                This identifies an entry in either the csBgpImpImpPolTable
                or the csBgpExpImpPolTable. 
		The import polices defined at the group level can be 
		over-ridden for each Nbr in the group by accessing
		the csBgpNbrImpPolTable."
        ::= { csBgpNbrGroupImpPolEntry 1 }

    csBgpNbrGroupImpPolRowStatus OBJECT-TYPE
        SYNTAX  RowStatus
        MAX-ACCESS  read-create
        STATUS  current
        DESCRIPTION
                "The RowStatus object for this table.  This is
                used to add & remove rows from this table."
        ::= { csBgpNbrGroupImpPolEntry 2 }

--
-- The BGP Neighbor Export policy table
--

    csBgpNbrGroupExpPolTable OBJECT-TYPE
        SYNTAX  SEQUENCE OF CsBgpNbrGroupExpPolEntry
        MAX-ACCESS  not-accessible
        STATUS  current
        DESCRIPTION
                "This table is used to configure the export policies applied
                to each BGP Group on each virtual router."
        ::= { csBgpNbrGroup 3 }

    csBgpNbrGroupExpPolEntry OBJECT-TYPE
        SYNTAX CsBgpNbrGroupExpPolEntry
        MAX-ACCESS not-accessible
        STATUS  current
        DESCRIPTION
                "Each entry contains information about a single policy
                applied to a single virtual router's BGP Group."
        INDEX   { csOrionGlobalVPNIndex, csOrionVPNVRouterIndex,
                csBgpNbrGroupName, csBgpNbrGroupExpPolId }
        ::= { csBgpNbrGroupExpPolTable 1 }

    CsBgpNbrGroupExpPolEntry ::=
        SEQUENCE {
        csBgpNbrGroupExpPolId
                Integer32,
        csBgpNbrGroupExpPolRowStatus
                RowStatus
        }

    csBgpNbrGroupExpPolId OBJECT-TYPE
        SYNTAX  Integer32 (1..65535)
        MAX-ACCESS  not-accessible
        STATUS  current
        DESCRIPTION
                "The identifier of the policy to apply to this group.
                This identifies an entry in either the csBgpExpExpPolTable
                or the csBgpExpExpPolTable.
		If the export policies are defined at the group level,
		all the neighbors in the group will inherit these 
		export policies, even if export policies are defined
		at the Nbr level."
        ::= { csBgpNbrGroupExpPolEntry 1 }

    csBgpNbrGroupExpPolRowStatus OBJECT-TYPE
        SYNTAX  RowStatus
        MAX-ACCESS  read-create
        STATUS  current
        DESCRIPTION
                "The RowStatus object for this table.  This is
                used to add & remove rows from this table."
        ::= { csBgpNbrGroupExpPolEntry 2 }

------------------------------------------------------------------------------
--
--	       Following is isis mib according to ietf-isis-wg-mib-02
--
------------------------------------------------------------------------------

        OSINSAddress ::= TEXTUAL-CONVENTION
           STATUS       current
           DESCRIPTION
              "OSI Network Service Address, e.g. NSAP, Network Entity Title"
           SYNTAX     OCTET STRING (SIZE(0..20))

        SNPAAddress ::= TEXTUAL-CONVENTION
           STATUS       current
           DESCRIPTION
              "A MAC Address or DTE Address or other SNPA Address."
           SYNTAX     OCTET STRING (SIZE(0..20))

        NSAPPrefix ::= TEXTUAL-CONVENTION
           STATUS       current
           DESCRIPTION
              "NSAP Prefix. The first octet of the string is used to
               encode as an unsigned integer the length in bits of the
               subsequent prefix. This length must be a multiple of 4
               bits and may range from 0..160. The second and
               subsequent octets are used to hold the prefix value.
               If the last 4 bits of the last octet are not part of
               the prefix then their value is undefined."
           SYNTAX       OCTET STRING (SIZE(1..21))

        SNPAPrefix ::= TEXTUAL-CONVENTION
           STATUS       current
           DESCRIPTION
              "SNPA Prefix. The first octet of the string is used to
               encode as an unsigned integer the length in bits of the
               subsequent prefix. The second and
               subsequent octets are used to hold the prefix value.
               Bits in the last octet which are not part of
               the prefix have undefined value."
           SYNTAX         OCTET STRING (SIZE(1..21))

        SystemID ::= TEXTUAL-CONVENTION
           STATUS       current
           DESCRIPTION
              "A system ID."
         SYNTAX            OCTET STRING (SIZE(0..8))

        LSPBuffSize ::= TEXTUAL-CONVENTION
           STATUS       current
           DESCRIPTION
                 "Integer sub range for LSP size."
           SYNTAX         Integer32 (512..1492)

        LevelState ::= TEXTUAL-CONVENTION
           STATUS       current
           DESCRIPTION
                 "states of the ISIS protocol."
           SYNTAX        INTEGER
                            {
                             off (1),
                             on (2),
                             waiting (3)
                            }

        SupportedProtocol ::= TEXTUAL-CONVENTION
           STATUS       current
           DESCRIPTION
                 "Types of network protocol supported by Integrated ISIS.
                  The values for ISO8473 and IP are those registered for
                  these protocols in ISO TR9577."
           SYNTAX        INTEGER
                            {
                             iso8473(129),
                             ip(204),
                             ipV6(205)
                            }

        DefaultMetric ::= TEXTUAL-CONVENTION
           STATUS       current
           DESCRIPTION
              "Integer sub-range for default metric for single hop."
           SYNTAX        Integer32 (1..63)

        OtherMetric ::= TEXTUAL-CONVENTION
           STATUS       current
           DESCRIPTION
              "Integer sub-range for metrics other than the default
               metric for single hop."
           SYNTAX         Integer32 (0..63)

        MetricType ::= TEXTUAL-CONVENTION
           STATUS       current
           DESCRIPTION
              "Class of metric at Level 2."
           SYNTAX           INTEGER
                               {
                                internal(1),
                                external(2)
                               }

        CircuitID ::= TEXTUAL-CONVENTION
           STATUS       current
           DESCRIPTION
                 "ID for a circuit."
           SYNTAX OCTET STRING (SIZE(2..9))

        ISPriority ::= TEXTUAL-CONVENTION
           STATUS       current
           DESCRIPTION
              "Integer sub-range for ISIS priority."
         SYNTAX             Integer32 (1..127)

         TOS ::= INTEGER
                 {
                     default(1),
                     delay(2),
                     expense(3),
                     error(4)
                  }
         -- Types Of Service (equivalent to Qualities Of Service)
         -- which define types of metric.

            PathCost ::= INTEGER (0..1023)
             -- Integer sub-range for any metric for complete path.

--
--     		csIsisSysTable
--

     -- Behaviour Definitions

     -- ResettingTimer behaviour definition
     -- "This object specifies the interval between certain events in
     -- the operation of the protocol state machine. If the value of
     -- this object is set to a new value while the protocol state
     -- machine is in operation, the implementation shall take the
     -- necessary steps to ensure that for any time interval which
     -- was in progress when the value of the corresponding object
     -- was changed, the next expiration of that interval takes place
     -- the specified time after the original start of that interval,
     -- or immediately, whichever is later. The precision with which
     -- this time shall be implemented shall be the same as that
     -- associated with the basic operation of the timer object."

     -- OperationalState behaviour definition
     -- "This object controls the enabling and disabling of the
     -- corresponding table row. Setting this object to the value
     -- off has the effect of disabling the corresponding row.
     -- Setting this object to the value on has the effect of
     -- enabling the corresponding row. Setting the value of this
     -- object to the same value as its current value has no effect.
     -- If the table entry also contains an object controlling the
     -- row status then the object following the operationalState
     -- behaviour shall not be set to on when the object following
     -- the Row Status behaviour has value off. An attempt to do
     -- so is rejected."

         csIsisSysTable OBJECT-TYPE
             SYNTAX SEQUENCE OF CsIsisSysEntry
             MAX-ACCESS not-accessible
             STATUS current
             DESCRIPTION
                 "The set of instances of the Integrated IS-IS protocol
                 existing on the system."
         ::= { csIsisSystem 1 }

         csIsisSysEntry OBJECT-TYPE
             SYNTAX CsIsisSysEntry
             MAX-ACCESS not-accessible
             STATUS current
             DESCRIPTION
                 "Each row defines information specific to a single
                 instance of the protocol existing on the system."
             REFERENCE 
				"ISIS.poi cLNSISISBasic-P (1)"
             INDEX { csOrionGlobalVPNIndex, csOrionVPNVRouterIndex, csIsisSysInstance }
         ::= { csIsisSysTable 1 }

         CsIsisSysEntry ::=
             SEQUENCE {
                 csIsisSysInstance
                     Integer32,
                 csIsisSysVersion
                     DisplayString,
                 csIsisSysType
                     INTEGER,
                 csIsisSysID
                     SystemID,
                 csIsisSysMaxPathSplits
                     Integer32,
                 csIsisSysMaxLSPGenInt
                     Integer32,
                 csIsisSysOrigL1LSPBuffSize
                     LSPBuffSize,
                 csIsisSysMaxAreaAddresses
                     Integer32,
                 csIsisSysMinL1LSPGenInt        -- Change - jdp
                     Integer32,
                 csIsisSysMinL2LSPGenInt        -- Added - jdp
                     Integer32,
                 csIsisSysPollESHelloRate
                     Integer32,
                 csIsisSysWaitTime
                     Integer32,
                 csIsisSysOperState
                     OperState,
                 csIsisSysL1State
                     LevelState,
                 csIsisSysCorrLSPs
                     Counter32,
                 csIsisSysLSPL1DbaseOloads
                     Counter32,
                 csIsisSysManAddrDropFromAreas
                     Counter32,
                 csIsisSysAttmptToExMaxSeqNums
                     Counter32,
                 csIsisSysSeqNumSkips
                     Counter32,
                 csIsisSysOwnLSPPurges
                     Counter32,
                 csIsisSysIDFieldLenMismatches
                     Counter32,
                 csIsisSysMaxAreaAddrMismatches
                     Counter32,
                 csIsisSysOrigL2LSPBuffSize
                     LSPBuffSize,
                 csIsisSysL2State
                     LevelState,
                 csIsisSysLSPL2DbaseOloads
                     Counter32,
                 csIsisSysAuthAreaType
                     INTEGER,
                 csIsisSysAuthAreaTransPwd
                     OCTET STRING,
                 csIsisSysAuthDomainType
                     INTEGER,
                 csIsisSysAuthDomainTransPwd
                     OCTET STRING,
                 csIsisSysAuthFails
                     Counter32,
                 csIsisSysLSPIgnoreErrors
                     TruthValue,
                 csIsisSysLogAdjacencyChanges
                     TruthValue,
                 csIsisSysPartChanges
                     Counter32,
                 csIsisSysMaxAreaCheck
                     TruthValue,
                 csIsisSysNextCircIndex
                     TestAndIncr,
                 csIsisSysExistState
                     RowStatus,
				 csIsisSysAdminStatus
					INTEGER,
				csIsisSysSPFL1Int
					Integer32,
				csIsisSysSPFL2Int
					Integer32,
				csIsisSysSPFStartInt
					Integer32,
				csIsisSysDefInfoOrig
					TruthValue,
				csIsisSysL2TO1Leak
					TruthValue,
				csIsisSysLogAreaFlag
					Unsigned32,
				csIsisSysLogLevelFlag
					Unsigned32
             }

         csIsisSysInstance OBJECT-TYPE
             SYNTAX Integer32
             MAX-ACCESS not-accessible
             STATUS current
             DESCRIPTION
                 "The unique identifier of the Integrated IS-IS instance
                 to which this row corresponds. This object follows the
                 index behaviour."
         ::= { csIsisSysEntry 1 }

         csIsisSysVersion OBJECT-TYPE
             SYNTAX DisplayString
             MAX-ACCESS read-only
             STATUS current
             DESCRIPTION
                 "The version number of the IS-IS protocol to which this
                 instance conforms. This value must be set by the
                 implementation when the row is valid."
             REFERENCE
				"ISIS.aoi version (1)"
         ::= { csIsisSysEntry 2 }

         csIsisSysType OBJECT-TYPE
             SYNTAX INTEGER {
                 level1IS (1),
                 level2IS (2),
                 level1l2IS (3)
                 }
             MAX-ACCESS read-create
             STATUS current
             DESCRIPTION
                 "The type of this instance of the Integrated IS-IS
                 protocol. This object follows the
                 replaceOnlyWhileDisabled behaviour."
             REFERENCE
				"ISIS.aoi iSType (2)"
			 DEFVAL	{level1l2IS}
         ::= { csIsisSysEntry 3 }

         csIsisSysID OBJECT-TYPE
             SYNTAX SystemID
             MAX-ACCESS read-create
             STATUS current
             DESCRIPTION
                 "The ID for this instance of the Integrated IS-IS
                 protocol. This value is appended to each of the
                 instance's area addresses to form the Network Entity
                 Titles valid for this instance. The derivation of a value
                 for this object is implementation-specific. Some
                 implementations may assign values and not permit write
             MAX-ACCESS, others may require the value to be set manually."
             REFERENCE
				 "ISIS.aoi systemId (119)"
         ::= { csIsisSysEntry 4 }

         csIsisSysMaxPathSplits OBJECT-TYPE
             SYNTAX Integer32 (1..32)
             MAX-ACCESS read-create
             STATUS current
             DESCRIPTION
                 "Maximum number of paths with equal routing metric value
                 which it is permitted to split between. This object
                 follows the replaceOnlyWhileDisabled behaviour."
             REFERENCE
				 "ISIS.aoi maximumPathSplits (3)"
             DEFVAL { 3 }
         ::= { csIsisSysEntry 5 }

         csIsisSysMaxLSPGenInt OBJECT-TYPE
             SYNTAX Integer32 (1..65535)
             MAX-ACCESS read-create
             STATUS current
             DESCRIPTION
                 "Maximum interval, in seconds, between generated LSPs
                 by this instance. This object follows the resettingTimer
                 behaviour."
             REFERENCE
				 "ISIS.aoi maximumLSPGenerationInterval (6)"
             DEFVAL { 100 }
         ::= { csIsisSysEntry 6 }

         csIsisSysOrigL1LSPBuffSize OBJECT-TYPE
             SYNTAX LSPBuffSize
             MAX-ACCESS read-create
             STATUS current
             DESCRIPTION
                 "The maximum size of Level 1 LSPs and SNPs originated by
                 this instance. This object follows the
                 replaceOnlyWhileDisabled behaviour."
             REFERENCE 
				"ISIS.aoi originatingL1LSPBufferSize (9)"
             DEFVAL { 1492 }
         ::= { csIsisSysEntry 7 }

         csIsisSysMaxAreaAddresses OBJECT-TYPE
             SYNTAX Integer32 (0..254)
             MAX-ACCESS read-create
             STATUS current
             DESCRIPTION
                 "The maximum number of area addresses to be permitted for
                 the area in which this instance exists. Note that all
                 Intermediate Systems in the same area must have the same
                 value configured for this attribute if correct operation
                 is to be assumed. This object follows the
                 replaceOnlyWhileDisabled behaviour."
             REFERENCE
				 "ISIS.aoi maximumAreaAddresses (4)"
             DEFVAL { 3 }
         ::= { csIsisSysEntry 8 }

         csIsisSysMinL1LSPGenInt OBJECT-TYPE
             SYNTAX Integer32 (1..65535)
             MAX-ACCESS read-create
             STATUS current
             DESCRIPTION
                 "Minimum interval, in seconds, between successive generation
                 of L1 LSPs with the same LSPID by this instance.
                 This object follows the resettingTimer behaviour."
             REFERENCE
				 "ISIS.aoi minimumLSPGenerationInterval (11)"
             DEFVAL { 100 }
         ::= { csIsisSysEntry 9 }

         csIsisSysMinL2LSPGenInt OBJECT-TYPE
             SYNTAX Integer32 (1..65535)
             MAX-ACCESS read-create
             STATUS current
             DESCRIPTION
                 "Minimum interval, in seconds, between successive generation
                 of L2 LSPs with the same LSPID by this instance.
                 This object follows the resettingTimer behaviour."
             REFERENCE
				 "ISIS.aoi minimumLSPGenerationInterval (11)"
             DEFVAL { 100 }
         ::= { csIsisSysEntry 10 }

         csIsisSysPollESHelloRate OBJECT-TYPE
             SYNTAX Integer32 (1..65535)
             MAX-ACCESS read-create
             STATUS current
             DESCRIPTION
                 "The value, in seconds, to be used for the suggested ES
                 configuration timer in ISH PDUs when soliciting the ES
                 configuration."
             REFERENCE
				 "ISIS.aoi pollESHelloRate (13)"
             DEFVAL { 100 }
         ::= { csIsisSysEntry 11 }

         csIsisSysWaitTime OBJECT-TYPE
             SYNTAX Integer32 (1..65535)
             MAX-ACCESS read-create
             STATUS current
             DESCRIPTION
                 "Number of seconds to delay in waiting state before
                 entering on state. This object follows the resettingTimer
                 behaviour."
             REFERENCE
				 "ISIS.aoi waitingTime (15)"
             DEFVAL { 100 }
         ::= { csIsisSysEntry 12 }

         csIsisSysOperState OBJECT-TYPE
             SYNTAX OperState
             MAX-ACCESS read-create
             STATUS current
             DESCRIPTION
                 "The operational state of this instance of the Integrated
                 IS-IS protocol. Setting this object to the value on when
                 its current value is off enables operation of this
                 instance of the Integrated IS-IS protocol."
             DEFVAL { off }
         ::= { csIsisSysEntry 13 }

         csIsisSysL1State OBJECT-TYPE
             SYNTAX LevelState
             MAX-ACCESS read-only
             STATUS current
             DESCRIPTION
                 "The state of the Level 1 database."
             REFERENCE
				 "ISIS.aoi l1State (17)"
         ::= { csIsisSysEntry 14 }

         csIsisSysCorrLSPs OBJECT-TYPE
             SYNTAX Counter32
             MAX-ACCESS read-only
             STATUS current
             DESCRIPTION
                 "Number of corrupted LSPs detected."
             REFERENCE
				 "ISIS.aoi corruptedLSPsDetected (19)"
         ::= { csIsisSysEntry 15 }

         csIsisSysLSPL1DbaseOloads OBJECT-TYPE
             SYNTAX Counter32
             MAX-ACCESS read-only
             STATUS current
             DESCRIPTION
                 "Number of times the LSP L1 database has become
                 overloaded."
             REFERENCE
				 "ISIS.aoi lSPL1DatabaseOverloads (20)"
         ::= { csIsisSysEntry 16 }

         csIsisSysManAddrDropFromAreas OBJECT-TYPE
             SYNTAX Counter32
             MAX-ACCESS read-only
             STATUS current
             DESCRIPTION
                 "Number of times a manual address has been dropped from
                 the area."
             REFERENCE
				 "ISIS.aoi manualAddressesDroppedFromArea (21)"
         ::= { csIsisSysEntry 17 }

         csIsisSysAttmptToExMaxSeqNums OBJECT-TYPE
             SYNTAX Counter32
             MAX-ACCESS read-only
             STATUS current
             DESCRIPTION
                 "Number of times the IS has attempted to exceed the
                 maximum sequence number."
             REFERENCE
				 "ISIS.aoi
                 attemptsToExceedmaximumSequenceNumber (22)"
         ::= { csIsisSysEntry 18 }

         csIsisSysSeqNumSkips OBJECT-TYPE
             SYNTAX Counter32
             MAX-ACCESS read-only
             STATUS current
             DESCRIPTION
                 "Number of times a sequence number skip has occurred."
             REFERENCE
				 "ISIS.aoi sequenceNumberSkips (23)"
         ::= { csIsisSysEntry 19 }

         csIsisSysOwnLSPPurges OBJECT-TYPE
             SYNTAX Counter32
             MAX-ACCESS read-only
             STATUS current
             DESCRIPTION
                 "Number of times a zero-aged copy of the system's own LSP
                 is received from some other node."
             REFERENCE
				 "ISIS.aoi ownLSPPurges (24)"
         ::= { csIsisSysEntry 20 }

         csIsisSysIDFieldLenMismatches OBJECT-TYPE
             SYNTAX Counter32
             MAX-ACCESS read-only
             STATUS current
             DESCRIPTION
                 "Number of times a PDU is received with a different value
                 for ID field length to that of the receiving system."
             REFERENCE
				 "ISIS.aoi iDFieldLengthMismatches (25)"
         ::= { csIsisSysEntry 21 }

         csIsisSysMaxAreaAddrMismatches OBJECT-TYPE
             SYNTAX Counter32
             MAX-ACCESS read-only
             STATUS current
             DESCRIPTION
                 "Number of times a PDU is received with a different value
                 for MaximumAreaAddresses from that of the receiving
                 system."
             REFERENCE
				 "ISIS.aoi MaximumAreaAddressesMismatches (118)"
         ::= { csIsisSysEntry 22 }

     -- The following objects map those from the cLNSISISLevel2-P
     -- Package

         csIsisSysOrigL2LSPBuffSize OBJECT-TYPE
             SYNTAX LSPBuffSize
             MAX-ACCESS read-create
             STATUS current
             DESCRIPTION
                 "The maximum size of Level 2 LSPs and SNPs originated by
                 this system. This object follows the
                 replaceOnlyWhileDisabled behaviour."
             REFERENCE 
				"ISIS.aoi originatingL2LSPBufferSize (26)"
             DEFVAL { 1492 }
         ::= { csIsisSysEntry 23 }

         csIsisSysL2State OBJECT-TYPE
             SYNTAX LevelState
             MAX-ACCESS read-only
             STATUS current
             DESCRIPTION
                 "The state of the Level 2 database."
             REFERENCE
				 "ISIS.aoi l2State (28)"
			 DEFVAL	{ off }
         ::= { csIsisSysEntry 24 }

         csIsisSysLSPL2DbaseOloads OBJECT-TYPE
             SYNTAX Counter32
             MAX-ACCESS read-only
             STATUS current
             DESCRIPTION
                 "Number of times the Level 2 LSP database has become
                 overloaded."
             REFERENCE
				 "ISIS.aoi lSPL2DatabaseOverloads (32)"
         ::= { csIsisSysEntry 25 }

         csIsisSysAuthAreaType OBJECT-TYPE
             SYNTAX INTEGER {
                     none(1),
                     plaintext(2),
					 md5(3)
                 }
             MAX-ACCESS read-create
             STATUS current
             DESCRIPTION
                 "What authentication scheme, if any, is used to protect
                  Level 1 Link State packets?"
             DEFVAL { none }
         ::= { csIsisSysEntry 26 }

         csIsisSysAuthAreaTransPwd OBJECT-TYPE
             SYNTAX OCTET STRING (SIZE (0..255))
             MAX-ACCESS read-create
             STATUS current
             DESCRIPTION
                 "The value to be used as the Authentication Key in
                 Level 1 Link State Packets whenever the value of
                 csIsisSysAuthAreaType has a value of plaintext.
                 A modification of csIsisSysAuthAreaType does not
                 modify the csIsisSysAuthAreaTransPwd value.

                 Reading this object always results in an  OCTET
                 STRING of length zero; authentication may not
                 be bypassed by reading the MIB object."
             DEFVAL { "" }
         ::= { csIsisSysEntry 27 }

         csIsisSysAuthDomainType OBJECT-TYPE
             SYNTAX INTEGER {
                     none(1),
                     plaintext(2),
					 md5(3)
                 }
             MAX-ACCESS read-create
             STATUS current
             DESCRIPTION
                 "What authentication scheme, if any, is used to protect
                  Level 2 Link State packets?"
             DEFVAL { none }
         ::= { csIsisSysEntry 28 }

         csIsisSysAuthDomainTransPwd OBJECT-TYPE
             SYNTAX OCTET STRING (SIZE (0..255))
             MAX-ACCESS read-create
             STATUS current
             DESCRIPTION
                 "The value to be used as the Authentication Key in
                 Level 2 Link State Packets whenever the value of
                 csIsisSysAuthDomainType has a value of plaintext.
                 A modification of csIsisSysAuthDomainType does not
                 modify the csIsisSysAuthDomainTransPwd value.

                 Reading this object always results in an  OCTET
                 STRING of length zero; authentication may not
                 be bypassed by reading the MIB object."
             DEFVAL { "" }
         ::= { csIsisSysEntry 29 }

         csIsisSysAuthFails OBJECT-TYPE
             SYNTAX Counter32
             MAX-ACCESS read-only
             STATUS current
             DESCRIPTION
                 "The number of authentication failures recognized by this
                 instance of the protocol."
         ::= { csIsisSysEntry 30 }

         csIsisSysLSPIgnoreErrors OBJECT-TYPE
             SYNTAX TruthValue
             MAX-ACCESS read-create
             STATUS current
             DESCRIPTION
                 "If true, allow the router to ignore IS-IS link state packets
                 (LSPs) that are received with internal checksum errors rather
                 than purging the LSPs."
             DEFVAL { true }

         ::= { csIsisSysEntry 31 }

         csIsisSysLogAdjacencyChanges OBJECT-TYPE
             SYNTAX TruthValue
             MAX-ACCESS read-create
             STATUS current
             DESCRIPTION
                 "If true, causes IS-IS to generate a log message when an
                 IS-IS adjacency changes state (up or down)."
             DEFVAL { false }
         ::= { csIsisSysEntry 32 }

         csIsisSysPartChanges OBJECT-TYPE
             SYNTAX Counter32
             MAX-ACCESS read-only
             STATUS current
             DESCRIPTION
                 "partition changes"
         ::= { csIsisSysEntry 33 }

         csIsisSysMaxAreaCheck OBJECT-TYPE
             SYNTAX TruthValue
             MAX-ACCESS read-create
             STATUS current
             DESCRIPTION
                 "When on, enables checking of maximum area
                 addresses per IS version of ISO10589."
             DEFVAL { true }
         ::= { csIsisSysEntry 34 }

         csIsisSysNextCircIndex OBJECT-TYPE
             SYNTAX TestAndIncr
             MAX-ACCESS read-create
             STATUS current
             DESCRIPTION
                 "This object is used to assign values to
                 csIsisCircIndex as described in 'Textual
                 Conventions for SNMPv2'.  The network manager
                 reads this object, and then writes the value
                 back in a SET that creates a new instance of
                 csIsisCircEntry.  If the SET fails with the
                 code 'inconsistentValue', then the process must
                 be repeated; If the SET succeeds, then the ob-
                 ject is incremented, and the new instance is
                 created according to the manager's directions."
         ::= { csIsisSysEntry 35 }

         csIsisSysExistState OBJECT-TYPE
             SYNTAX RowStatus
             MAX-ACCESS read-create
             STATUS current
             DESCRIPTION
                 "The state of the ISIS router.  Turning this off
                 forces the router to forget all current state"
             DEFVAL { active }
         ::= { csIsisSysEntry 36 }

	csIsisSysAdminStatus OBJECT-TYPE
             SYNTAX INTEGER {
			enable (1),
			disable (2)
	     }
             MAX-ACCESS read-create
             STATUS current
             DESCRIPTION
                 "This object is used to enable/disable IS-IS routing on
		  this Virtual Router."
	     DEFVAL { enable }
         ::= { csIsisSysEntry 37 }

	csIsisSysSPFL1Int OBJECT-TYPE
	     SYNTAX Integer32 (1.. 120)
	     MAX-ACCESS read-create
	     STATUS current
             DESCRIPTION
		" This object is used for SPF Level 1 Interval, it is in seconds."
		DEFVAL { 5 }
	 ::= { csIsisSysEntry 38 }

	csIsisSysSPFL2Int OBJECT-TYPE
	     SYNTAX Integer32 (1.. 120)
	     MAX-ACCESS read-create
	     STATUS current
             DESCRIPTION
		" This object is used for SPF Level 2 Interval, it is in seconds."
		DEFVAL { 5 }
	 ::= { csIsisSysEntry 39 }

	csIsisSysSPFStartInt OBJECT-TYPE
	     SYNTAX Integer32 (1.. 120)
	     MAX-ACCESS read-create
	     STATUS current
             DESCRIPTION
		" The number in seconds system will wait to start 
		  SPF Interval calculation."
	     DEFVAL { 5 }
	 ::= { csIsisSysEntry 40 }

	 csIsisSysDefInfoOrig OBJECT-TYPE
             SYNTAX TruthValue
             MAX-ACCESS read-create
             STATUS current
             DESCRIPTION
                 "When on, distributes the default route
                 into the IS-IS routing domain."
             DEFVAL { false }
         ::= { csIsisSysEntry 41 }

	csIsisSysL2TO1Leak OBJECT-TYPE
             SYNTAX TruthValue
             MAX-ACCESS read-create
             STATUS current
             DESCRIPTION
                 "When on, enables Level-2 to Level-1
                 route leaking."
             DEFVAL { false }
         ::= { csIsisSysEntry 42 }
	csIsisSysLogAreaFlag OBJECT-TYPE
        SYNTAX          Unsigned32
        MAX-ACCESS      read-create
        STATUS          current
        DESCRIPTION
                "Each bit within this object enables loggin for a specific
                area within ISIS.  Below is a list of the different areas
                available for logging within BGP and their corresponding
                bits identifiers.

                        area                            bit
                ------------------------------------------------------
                        system                0
						adj					  1
						lsp					  2
						snp					  3
						spf					  4
						packet recv			  5
						packet send			  6
								

                end of description."
        DEFVAL { 0 }
        ::= { csIsisSysEntry 43 }

     csIsisSysLogLevelFlag OBJECT-TYPE
        SYNTAX          Unsigned32
        MAX-ACCESS      read-create
        STATUS          current
        DESCRIPTION
                "Each bit within this object enables logging at a specific
                level for ISIS.  Below is a list of the different log levels
                available and their corresponding bits identifiers.

                        area                            bit
                ------------------------------------------------------
                        critical              0
                        error                 1
                        warning               2
                        information           3
                        detail				  4	
						debug                 5
                end of description. "
        DEFVAL { 0 }
        ::= { csIsisSysEntry 44 }

     -- The Level 1 Manual Area Address Table
     -- contains the set of area addresses manually configured
     -- for each instance of the Integrated IS-IS protocol.
     -- At least one row in which the value of
     -- csIsisManAreaAddrExistState
     -- is on must be present for each instance of the protocol
     -- when csIsisSysOperState is also on for that instance. The
     -- maximum number of rows in this table for each instance of
     -- the protocol for which the object csIsisManAreaAddrExistState
     -- has the value on is the value of maximumAreaAddresses (as
     -- defined in ISO 10589) for that instance. An Attempt
     -- to create a new row such that the number of rows with
     -- csIsisManAreaAddrExistState set to on for that protocol
     -- instance exceeds maximumAreaAddresses is rejected."

         csIsisManAreaAddrTable OBJECT-TYPE
             SYNTAX SEQUENCE OF CsIsisManAreaAddrEntry
             MAX-ACCESS not-accessible
             STATUS current
             DESCRIPTION
                 "The set of manual area addresses configured on this
                 Intermediate System."
             REFERENCE
				 "ISIS.aoi manualAreaAddresses (10)"
         ::= { csIsisSystem 2 }

         csIsisManAreaAddrEntry OBJECT-TYPE
             SYNTAX CsIsisManAreaAddrEntry
             MAX-ACCESS not-accessible
             STATUS current
             DESCRIPTION
                 "Each entry contains one area address manually configured
                 on this system"
             INDEX { csOrionGlobalVPNIndex, csOrionVPNVRouterIndex, csIsisManAreaAddrSysInstance,
                     csIsisManAreaAddr }
         ::= { csIsisManAreaAddrTable 1 }

         CsIsisManAreaAddrEntry ::=
             SEQUENCE {
                 csIsisManAreaAddrSysInstance
                     Integer32,
                 csIsisManAreaAddr
                     OSINSAddress,
                 csIsisManAreaAddrExistState
                     RowStatus
                 }

         csIsisManAreaAddrSysInstance OBJECT-TYPE
             SYNTAX Integer32
             MAX-ACCESS not-accessible
             STATUS current
             DESCRIPTION
                 "The unique identifier of the Integrated IS-IS instance
                 to which this row corresponds. This object follows the
                 index behaviour."
         ::= { csIsisManAreaAddrEntry 1 }

         csIsisManAreaAddr OBJECT-TYPE
             SYNTAX OSINSAddress
             MAX-ACCESS not-accessible
             STATUS current
             DESCRIPTION
                 "A manually configured area address for this system. This
                 object follows the index behaviour.

                 Note: an index for the entry {1, {49.0001} active} in
                 this table would be the ordered pair
                 (1, (0x03 0x49 0x00 0x01)), as the length of an Octet
                 string is part of the OID."
         ::= { csIsisManAreaAddrEntry 2 }

         csIsisManAreaAddrExistState OBJECT-TYPE
             SYNTAX RowStatus
             MAX-ACCESS read-create
             STATUS current
             DESCRIPTION
                 "The state of the csIsisManAreaAddrEntry. This object
                 follows the Row Status behaviour. If an attempt is
                 made to set this object to the value off when the
                 corresponding csIsisManAreaAddrEntry is the only valid
                 entry for this instance and when the corresponding ISIS
                 instance has csIsisSysOperState set to On then the attempt
                 is rejected."
             DEFVAL { active }
         ::= { csIsisManAreaAddrEntry 3 }

     -- The Level 1 Area Address Table

     -- The Level 1 Area Address Table contains the
     -- union of the sets of area addresses reported in all Level 1
     -- LSPs received by this Intermediate System.

         csIsisAreaAddrTable OBJECT-TYPE
             SYNTAX SEQUENCE OF CsIsisAreaAddrEntry
             MAX-ACCESS not-accessible
             STATUS current
             DESCRIPTION
                 "The union of the sets of area addresses reported in all
                 Level 1 LSPs received by this instance of the protocol."
             REFERENCE
				 "ISIS.aoi areaAddresses (18)"
         ::= { csIsisSystem 3 }

         csIsisAreaAddrEntry OBJECT-TYPE
             SYNTAX CsIsisAreaAddrEntry
             MAX-ACCESS not-accessible
             STATUS current
             DESCRIPTION
                 "Each entry contains one area address reported in a
                 Level 1 LSP received by this instance of the protocol."
             INDEX { csOrionGlobalVPNIndex, csOrionVPNVRouterIndex, csIsisAreaAddrSysInstance,
                     csIsisAreaAddr }
         ::= { csIsisAreaAddrTable 1 }

         CsIsisAreaAddrEntry ::=
             SEQUENCE {
                 csIsisAreaAddrSysInstance
                     Integer32,
                 csIsisAreaAddr
                     OSINSAddress
                 }

         csIsisAreaAddrSysInstance OBJECT-TYPE
             SYNTAX Integer32
             MAX-ACCESS not-accessible
             STATUS current
             DESCRIPTION
                 "The unique identifier of the Integrated IS-IS instance
                 to which this row corresponds."
         ::= { csIsisAreaAddrEntry 1 }

         csIsisAreaAddr OBJECT-TYPE
             SYNTAX OSINSAddress
             MAX-ACCESS read-only
             STATUS current
             DESCRIPTION
                 "An area address reported in a Level 1 LSP received by
                 this instance of the protocol."
         ::= { csIsisAreaAddrEntry 2 }

     -- The System Integrated Group

     -- The System Integrated Group is present if the system
     -- supports Integrated ISIS at Level 1.

     -- The System Protocol Supported Table

     -- The System Protocol Supported Table contains the manually
     -- configured set of protocols supported by each
     -- instance of the Integrated ISIS protocol.
     --

         csIsisSysProtSuppTable OBJECT-TYPE
             SYNTAX SEQUENCE OF CsIsisSysProtSuppEntry
             MAX-ACCESS not-accessible
             STATUS current
             DESCRIPTION
                 "This table contains the manually configured set of
                 protocols supported by each instance of the Integrated
                 ISIS protocol."
         ::= { csIsisSystem 4 }

         csIsisSysProtSuppEntry OBJECT-TYPE
             SYNTAX CsIsisSysProtSuppEntry
             MAX-ACCESS not-accessible
             STATUS current
             DESCRIPTION
                 "Each entry contains one protocol supported by an
                 instance of the Integrated ISIS protocol."
             INDEX {  csOrionGlobalVPNIndex, csOrionVPNVRouterIndex, csIsisSysProtSuppSysInstance,
                      csIsisSysProtSuppProtocol }

         ::= { csIsisSysProtSuppTable 1 }

         CsIsisSysProtSuppEntry ::=
             SEQUENCE {
                 csIsisSysProtSuppSysInstance
                     Integer32,
                 csIsisSysProtSuppProtocol
                     SupportedProtocol,
                 csIsisSysProtSuppExistState
                     RowStatus
                 }

         csIsisSysProtSuppSysInstance OBJECT-TYPE
             SYNTAX Integer32
             MAX-ACCESS not-accessible
             STATUS current
             DESCRIPTION
                 "The unique identifier of the Integrated IS-IS instance
                 to which this row corresponds. This object follows the
                 index behaviour."
         ::= { csIsisSysProtSuppEntry 1 }

         csIsisSysProtSuppProtocol OBJECT-TYPE
             SYNTAX SupportedProtocol
             MAX-ACCESS not-accessible
             STATUS current
             DESCRIPTION
                 "One supported protocol. This object follows the index
                 behaviour."
         ::= { csIsisSysProtSuppEntry 2 }

         csIsisSysProtSuppExistState OBJECT-TYPE
             SYNTAX RowStatus
             MAX-ACCESS read-create
             STATUS current
             DESCRIPTION
                 "The state of the csIsisSysProtSuppEntry. This object
                 follows the RowStatus behavior."
             DEFVAL { active }
         ::= { csIsisSysProtSuppEntry 3 }

     -- The Level 2 IP Group

     -- The Level 2 IP Group is present if the system
     -- supports IP Integrated IS-IS at Level 2

     -- The Level 2 Summary Address Table

     -- The Level 2 Summary Address Table contains the set of summary
     -- addresses manually configured for each Level 2 instance of
     -- IP Integrated ISIS on the system.

         csIsisL2SummAddrTable OBJECT-TYPE
             SYNTAX SEQUENCE OF CsIsisL2SummAddrEntry
             MAX-ACCESS not-accessible
             STATUS current
             DESCRIPTION
                 "The set of IP summary addresses to use in forming the
                 contents of Level 2 LSPs originated by this level 2
                 Intermediate System."
         ::= { csIsisSystem 5 }

         csIsisL2SummAddrEntry OBJECT-TYPE
             SYNTAX CsIsisL2SummAddrEntry
             MAX-ACCESS not-accessible
             STATUS current
             DESCRIPTION
                 "Each entry contains one IP summary address."
             INDEX { csOrionGlobalVPNIndex, csOrionVPNVRouterIndex, 
		     csIsisL2SummAddrSysInstance,
                     csIsisL2SummAddress,
                     csIsisL2SummAddrMask }
         ::= { csIsisL2SummAddrTable 1 }

         CsIsisL2SummAddrEntry ::=
             SEQUENCE {
                 csIsisL2SummAddrSysInstance
                     Integer32,
                 csIsisL2SummAddress
                     IpAddress,
                 csIsisL2SummAddrMask
                     IpAddress,
                 csIsisL2SummAddrExistState
                     RowStatus,
                 csIsisL2SummAddrOperState
                     OperState,
                 csIsisL2SummAddrDefaultMetric
                     DefaultMetric,
                 csIsisL2SummAddrDelayMetric
                     OtherMetric,
                 csIsisL2SummAddrExpenseMetric
                     OtherMetric,
                 csIsisL2SummAddrErrorMetric
                     OtherMetric
             }

         csIsisL2SummAddrSysInstance OBJECT-TYPE
             SYNTAX Integer32
             MAX-ACCESS not-accessible
             STATUS current
             DESCRIPTION
                 "The unique identifier of the Integrated IS-IS instance
                 to which this row corresponds. This object follows the
                 index behaviours."
         ::= { csIsisL2SummAddrEntry 1 }

         csIsisL2SummAddress OBJECT-TYPE
             SYNTAX IpAddress
             MAX-ACCESS not-accessible
             STATUS current
             DESCRIPTION
                 "The IP Address value for this summary address. This
                 object follows the index behaviour."
         ::= { csIsisL2SummAddrEntry 2 }

         csIsisL2SummAddrMask OBJECT-TYPE
             SYNTAX IpAddress
             MAX-ACCESS not-accessible
             STATUS current
             DESCRIPTION
                 "The mask value for this summary address. This object
                 follows the index behaviour."
         ::= { csIsisL2SummAddrEntry 3 }

         csIsisL2SummAddrExistState OBJECT-TYPE
             SYNTAX RowStatus
             MAX-ACCESS read-create
             STATUS current
             DESCRIPTION
                 "The existence state of this summary address. This object
                 follows the row status behaviour."
             DEFVAL { active }
         ::= { csIsisL2SummAddrEntry 4 }

         csIsisL2SummAddrOperState OBJECT-TYPE
             SYNTAX OperState
             MAX-ACCESS read-create
             STATUS current
             DESCRIPTION
                 "The operational state of this entry. This object follows
                 the operationalState behaviour. When the operational
                 state changes if this would cause the contents of Level 2
                 LSPs originated by the system to change then those new
                 LSPs must be generated and sent as soon as is permitted
                 by the ISIS protocol."
             DEFVAL { off }
         ::= { csIsisL2SummAddrEntry 5 }

         csIsisL2SummAddrDefaultMetric OBJECT-TYPE
             SYNTAX DefaultMetric
             MAX-ACCESS read-create
             STATUS current
             DESCRIPTION
                 "The default metric value to announce this summary
                 address with in Level 2 LSPs generated by this system."
             DEFVAL { 20 }
         ::= { csIsisL2SummAddrEntry 6 }

            csIsisL2SummAddrDelayMetric OBJECT-TYPE
                SYNTAX OtherMetric
                MAX-ACCESS read-create
                STATUS current
                DESCRIPTION
                    "The delay metric value to announce this summary address
                    with in Level 2 LSPs generated by this system. The value
                    of zero is reserved to indicate that this metric is not
                    supported."
                DEFVAL { 0 }
            ::= { csIsisL2SummAddrEntry 7 }

            csIsisL2SummAddrExpenseMetric OBJECT-TYPE
                SYNTAX OtherMetric
                MAX-ACCESS read-create
                STATUS current
                DESCRIPTION
                    "The expense metric value to announce this summary
                    address with in Level 2 LSPs generated by this system.
                    The value of zero is reserved to indicate that this
                    metric is not supported."
                DEFVAL { 0 }
            ::= { csIsisL2SummAddrEntry 8 }

            csIsisL2SummAddrErrorMetric OBJECT-TYPE
                SYNTAX OtherMetric
                MAX-ACCESS read-create
                STATUS current
                DESCRIPTION
                    "The error metric value to announce this summary address
                    with in Level 2 LSPs generated by this system. The value
                    of zero is reserved to indicate that this metric is not
                    supported."
                DEFVAL { 0 }
            ::= { csIsisL2SummAddrEntry 9 }


--
--  The ISIS Export Policy Table
--	this table identifies the Export policies that are applied by ISIS
--

    csIsisExpPolTable OBJECT-TYPE
        SYNTAX   SEQUENCE OF CsIsisExpPolEntry
        MAX-ACCESS   not-accessible
        STATUS   current
        DESCRIPTION
           "A set of Export Policies (see csExpPolTable) that
           are applied by ISIS."
      ::= { csIsisSystem 6 }

    csIsisExpPolEntry OBJECT-TYPE
        SYNTAX   CsIsisExpPolEntry
        MAX-ACCESS   not-accessible
        STATUS   current
        DESCRIPTION
           "Each entry represents a single export policy
           applied by the ISIS layer on a Virtual Router."
      INDEX { csOrionGlobalVPNIndex, csOrionVPNVRouterIndex, csIsisExpPolId }
      ::= { csIsisExpPolTable 1 }


    CsIsisExpPolEntry ::=
	SEQUENCE {
	csIsisExpPolId
		Integer32,
	csIsisExpPolStatus
		RowStatus
	}

    csIsisExpPolId OBJECT-TYPE
	SYNTAX   Integer32
	MAX-ACCESS   not-accessible
	STATUS   current
	DESCRIPTION
		"The Export Policy (see the corresponding entry in 
		csExpPolTable) that is applied to this Virtual Router."
    ::= { csIsisExpPolEntry 1 }

    csIsisExpPolStatus OBJECT-TYPE
	SYNTAX  RowStatus
	MAX-ACCESS  read-create
	STATUS  current
	DESCRIPTION
		"The RowStatus object for this table.  This is used to
		add and delete entries from this table."
    ::= { csIsisExpPolEntry 2 }

     -- The Circuit Group

     -- The Circuit Group is current

     -- The Circuit Table
     -- Each broadcast or point-to-point interface on the system
     -- corresponds to one entry in the Circuit table. There may be
     -- many X.25 DA circuit entries in the Circuit table for an
     -- X.25 interface.

         csIsisCircTable OBJECT-TYPE
             SYNTAX SEQUENCE OF CsIsisCircEntry
             MAX-ACCESS not-accessible
             STATUS current
             DESCRIPTION
                 "The table of circuits used by each instance of
                 Integrated IS-IS on this system."
         ::= { csIsisCirc 1 }

         csIsisCircEntry OBJECT-TYPE
             SYNTAX CsIsisCircEntry
             MAX-ACCESS not-accessible
             STATUS current
             DESCRIPTION
                 "An csIsisCircEntry exists for each circuit used by
                 Integrated IS-IS on this system."
             INDEX { csOrionGlobalVPNIndex, csOrionVPNVRouterIndex,
		     csIsisCircSysInstance, csIsisCircIndex }
         ::= { csIsisCircTable 1 }

         CsIsisCircEntry ::=
             SEQUENCE {
                 csIsisCircSysInstance
                     Integer32,
                 csIsisCircIndex
                     Integer32,
                 csIsisCircIfIndex
                     Integer32,
                 csIsisCircIfSubIndex
                     Integer32,
                 csIsisCircLocalID
                     Integer32,
                 csIsisCircOperState
                     OperState,
                 csIsisCircExistState
                     RowStatus,
                 csIsisCircType
                     INTEGER,
                 csIsisCircL1DefaultMetric
                     DefaultMetric,
                 csIsisCircL1DelayMetric
                     OtherMetric,
                 csIsisCircL1ExpenseMetric
                     OtherMetric,
                 csIsisCircL1ErrorMetric
                     OtherMetric,
                 csIsisCircExtDomain
                     TruthValue,
                 csIsisCircAdjChanges
                     Counter32,
                 csIsisCircInitFails
                     Counter32,
                 csIsisCircRejAdjs
                     Counter32,
                 csIsisCircOutCtrlPDUs
                     Counter32,
                 csIsisCircInCtrlPDUs
                     Counter32,
                 csIsisCircIDFieldLenMismatches
                     Counter32,
                 csIsisCircL2DefaultMetric
                     DefaultMetric,
                 csIsisCircL2DelayMetric
                     OtherMetric,
                 csIsisCircL2ExpenseMetric
                     OtherMetric,
                 csIsisCircL2ErrorMetric
                     OtherMetric,
                 csIsisCircManL2Only
                     TruthValue,
                 csIsisCircL1ISPriority
                     ISPriority,
                 csIsisCircL1CircID
                     CircuitID,
                 csIsisCircL1DesIS
                     SystemID,
                 csIsisCircLANL1DesISChanges
                     Counter32,
                 csIsisCircL2ISPriority
                     ISPriority,
                 csIsisCircL2CircID
                     CircuitID,
                 csIsisCircL2DesIS
                     SystemID,
                 csIsisCircLANL2DesISChanges
                     Counter32,
                 csIsisCircMCAddr
                     INTEGER,
                 csIsisCircPtToPtCircID
                     CircuitID,
                 csIsisCircL1HelloTimer
                     Integer32,
                 csIsisCircL2HelloTimer
                     Integer32,
                 csIsisCircL1HelloMultiplier
                     Integer32,
                 csIsisCircL2HelloMultiplier
                     Integer32,
                 csIsisCircDRL1HelloTimer
                     Integer32,
                 csIsisCircDRL2HelloTimer
                     Integer32,
                 csIsisCircMinBroadLSPTransInt
                     Integer32,
                 csIsisCircL1MinLSPTransInt
                     Integer32,
                 csIsisCircL2MinLSPTransInt
                     Integer32,
                 csIsisCircL1CSNPInterval
                     Integer32,
                 csIsisCircL2CSNPInterval
                     Integer32,
                 csIsisCircL1PartSNPInterval
                     Integer32,
                 csIsisCircL2PartSNPInterval
                     Integer32,
                 csIsisCircLSPThrottle
                     Integer32,
                 csIsisCircPassiveCircuit
                     TruthValue,
                 csIsisCircMeshGroupEnabled
                     INTEGER,
                 csIsisCircMeshGroup
                     Integer32,
                 csIsisCircL1AuthType
                     INTEGER,
                 csIsisCircL1Password
                     OCTET STRING,
                 csIsisCircL2AuthType
                     INTEGER,
                 csIsisCircL2Password
                     OCTET STRING,
                 csIsisCircSmallHellos
                     OperState,
                 csIsisManAdjNeighNSAP
                     OSINSAddress,
                 csIsisManAdjNeighSNPA
                     SNPAAddress,
                 csIsisCircIPEncaps
                     TruthValue,
                 csIsisCircUpTime
                     Integer32,
		 csIsisCircIpAddress
		     IpAddress,
		 csIsisCircLevel
		     INTEGER
             }

         csIsisCircSysInstance OBJECT-TYPE
             SYNTAX Integer32
             MAX-ACCESS not-accessible
             STATUS current
             DESCRIPTION
                 "The unique identifier of the Integrated IS-IS instance
                 to which this row corresponds. This object follows the
                 index behaviour."
         ::= { csIsisCircEntry 1 }

         csIsisCircIndex OBJECT-TYPE
             SYNTAX Integer32
             MAX-ACCESS not-accessible
             STATUS current
             DESCRIPTION
                 "The identifier of this circuit, unique within the
                 instance of the protocol. This object follows the index
                 behaviour.  This is for SNMP Indexing purposes only
                 and has no relation to any protocol value."
         ::= { csIsisCircEntry 2 }

         csIsisCircIfIndex OBJECT-TYPE
             SYNTAX Integer32
             MAX-ACCESS read-only
             STATUS current
             DESCRIPTION
                 "The value of ifIndex for the interface to which this
                 circuit corresponds.   This object cannot be modified
                 after creation"
         ::= { csIsisCircEntry 3 }

         csIsisCircIfSubIndex OBJECT-TYPE
             SYNTAX Integer32
             MAX-ACCESS read-only
             STATUS current
             DESCRIPTION
                 "A specifier for the part of the interface ifIndex to which
                 this circuit corresponds, such as a DLCI or VPI/VCI.
                 This object cannot be modified after creation"
         ::=    { csIsisCircEntry 4 }

         csIsisCircLocalID OBJECT-TYPE
             SYNTAX Integer32
             MAX-ACCESS read-only
             STATUS current
             DESCRIPTION
                 "An identification that can be used in protocol packets
                 to identify a circuit.  Implementations may devise ways
                 to assure that this value is suitable for the circuit
                 it is used on.  LAN packets only have space for 8 bits.

                 Values of csIsisCircLocalID do not need to be unique.  They
                 are only required to differ on LANs where the Intermediate
                 System is the Designated Intermediate System."
         ::=    { csIsisCircEntry 5 }

         csIsisCircOperState OBJECT-TYPE
             SYNTAX OperState
             MAX-ACCESS read-create
             STATUS current
             DESCRIPTION
                 "The operational state of the circuit. This object
                 follows the operationalState behaviour."
             DEFVAL { off }
         ::= { csIsisCircEntry 6 }

         csIsisCircExistState OBJECT-TYPE
             SYNTAX RowStatus
             MAX-ACCESS read-create
             STATUS current
             DESCRIPTION
                 "The existence state of this circuit. This object follows
                 the Row Status behaviour."
             DEFVAL { active }
         ::= { csIsisCircEntry 7 }

         csIsisCircType OBJECT-TYPE
             SYNTAX INTEGER {
                 broadcast(1),
                 ptToPt(2),
                 staticIn(3),
                 staticOut(4),
                 dA(5)
                 }
             MAX-ACCESS read-create
             STATUS current
             DESCRIPTION
                 "The type of the circuit. This object follows the
                 replaceOnlyWhileDisabled behaviour. The type specified
                 must be compatible with the type of the interface defined
                 by the value of csIsisCircIfIndex."
             REFERENCE
				 "ISIS.aoi type (33)"
         ::= { csIsisCircEntry 8 }

         csIsisCircL1DefaultMetric OBJECT-TYPE
             SYNTAX DefaultMetric
             MAX-ACCESS read-create
             STATUS current
             DESCRIPTION
                 "The default metric value of this circuit for Level 1
                 traffic."
             REFERENCE
				 "ISIS.aoi l1DefaultMetric (35)"
             DEFVAL { 10 }
         ::= { csIsisCircEntry 9 }

         csIsisCircL1DelayMetric OBJECT-TYPE
             SYNTAX OtherMetric
             MAX-ACCESS read-create
             STATUS current
             DESCRIPTION
                 "The delay metric value of this circuit for Level 1
                 traffic. The value of zero is reserved to indicate that
                 this metric is not supported."
             REFERENCE 
				"ISIS.aoi l1DelayMetric (36)"
             DEFVAL { 0 }
         ::= { csIsisCircEntry 10 }

         csIsisCircL1ExpenseMetric OBJECT-TYPE
             SYNTAX OtherMetric
             MAX-ACCESS read-create
             STATUS current
             DESCRIPTION
                 "The expense metric value of this circuit for Level 1
                 traffic. The value of zero is reserved to indicate that
                 this metric is not supported."
             REFERENCE
				 "ISIS.aoi l1ExpenseMetric (37)"
             DEFVAL { 0 }
         ::= { csIsisCircEntry 11 }

         csIsisCircL1ErrorMetric OBJECT-TYPE
             SYNTAX OtherMetric
             MAX-ACCESS read-create
             STATUS current
             DESCRIPTION
                 "The error metric value of this circuit for Level 1
                 traffic. The value of zero is reserved to indicate that
                 this metric is not supported."
             REFERENCE
				 "ISIS.aoi l1ErrorMetric (38)"
             DEFVAL { 0 }
         ::= { csIsisCircEntry 12 }

         csIsisCircExtDomain OBJECT-TYPE
             SYNTAX TruthValue
             MAX-ACCESS read-create
             STATUS current
             DESCRIPTION
                 "If true, suppress normal transmission of and
                 interpretation of Intra-domain ISIS PDUs on this
                 circuit."
             REFERENCE
				 "ISIS.aoi externalDomain (46)"
             DEFVAL { false }
         ::= { csIsisCircEntry 13 }

         csIsisCircAdjChanges OBJECT-TYPE
             SYNTAX Counter32
             MAX-ACCESS read-only
             STATUS current
             DESCRIPTION
                 "The number of times an adjacency state change has
                 occurred on this circuit."
             REFERENCE 
				"ISIS.aoi changesInAdjacencyState (40)"
         ::= { csIsisCircEntry 14 }

         csIsisCircInitFails OBJECT-TYPE
             SYNTAX Counter32
             MAX-ACCESS read-only
             STATUS current
             DESCRIPTION
                 "The number of times initialization of this circuit has
                 failed."
             REFERENCE
				 "ISIS.aoi initializationFailures (41)"
         ::= { csIsisCircEntry 15 }

         csIsisCircRejAdjs OBJECT-TYPE
             SYNTAX Counter32
             MAX-ACCESS read-only
             STATUS current
             DESCRIPTION
                 "The number of times an adjacency has been rejected on
                 this circuit."
             REFERENCE
				 "ISIS.aoi rejectedAdjacencies (42)"
         ::= { csIsisCircEntry 16 }

         csIsisCircOutCtrlPDUs OBJECT-TYPE
             SYNTAX Counter32
             MAX-ACCESS read-only
             STATUS current
             DESCRIPTION
                 "The number of IS-IS control PDUs sent on this circuit."
             REFERENCE 
				"ISIS.aoi iSISControlPDUsSent (43)"
         ::= { csIsisCircEntry 17 }

         csIsisCircInCtrlPDUs OBJECT-TYPE
             SYNTAX Counter32
             MAX-ACCESS read-only
             STATUS current
             DESCRIPTION
                 "The number of IS-IS control PDUs received on this
                 circuit."
             REFERENCE 
				"ISIS.aoi controlPDUsReceived (44)"
         ::= { csIsisCircEntry 18 }

         csIsisCircIDFieldLenMismatches OBJECT-TYPE
             SYNTAX Counter32
             MAX-ACCESS read-only
             STATUS current
             DESCRIPTION
                 "The number of times an IS-IS control PDU with an ID
                 field length different to that for this system has been
                 received."
             REFERENCE 
				"ISIS.aoi iDFieldLengthMismatches (25)"
         ::= { csIsisCircEntry 19 }

     -- The following objects map those from the linkageISISLevel2-P
     -- package

         csIsisCircL2DefaultMetric OBJECT-TYPE
             SYNTAX DefaultMetric
             MAX-ACCESS read-create
             STATUS current
             DESCRIPTION
                 "The default metric value of this circuit for level 2
                 traffic."
             REFERENCE
				 "ISIS.aoi l2DefaultMetric (68)"
             DEFVAL { 10 }
         ::= { csIsisCircEntry 20 }

         csIsisCircL2DelayMetric OBJECT-TYPE
             SYNTAX OtherMetric
             MAX-ACCESS read-create
             STATUS current
             DESCRIPTION
                 "The delay metric value of this circuit for level 2
                 traffic. The value of zero is reserved to indicate that
                 this metric is not supported."
             REFERENCE 
				"ISIS.aoi l2DelayMetric (69)"
             DEFVAL { 0 }
         ::= { csIsisCircEntry 21 }

         csIsisCircL2ExpenseMetric OBJECT-TYPE
             SYNTAX OtherMetric
             MAX-ACCESS read-create
             STATUS current
             DESCRIPTION
                 "The expense metric value of this circuit for level 2
                 traffic. The value of zero is reserved to indicate that
                 this metric is not supported."
             REFERENCE 
				"ISIS.aoi l2ExpenseMetric (70)"
             DEFVAL { 0 }
         ::= { csIsisCircEntry 22 }

         csIsisCircL2ErrorMetric OBJECT-TYPE
             SYNTAX OtherMetric
             MAX-ACCESS read-create
             STATUS current
             DESCRIPTION
                 "The error metric value of this circuit for level 2
                 traffic. The value of zero is reserved to indicate that
                 this metric is not supported."
             REFERENCE
				 "ISIS.aoi l2ErrorMetric (71)"
             DEFVAL { 0 }
         ::= { csIsisCircEntry 23 }

         csIsisCircManL2Only OBJECT-TYPE
             SYNTAX TruthValue
             MAX-ACCESS read-create
             STATUS current
             DESCRIPTION
                 "When true, indicates that this circuit is to be used
                 only for level 2. This object follows the
                 replaceOnlyWhileDisabled behaviour."
             REFERENCE 
				"ISIS.aoi manualL2OnlyMode (72)"
             DEFVAL { false }
         ::= { csIsisCircEntry 24 }

     -- The following objects map those from the
     -- linkageISISBroadcast-P package

         csIsisCircL1ISPriority OBJECT-TYPE
             SYNTAX ISPriority
             MAX-ACCESS read-create
             STATUS current
             DESCRIPTION
                 "The priority for becoming LAN Level 1 Deignated
                 Intermediate System on a broadcast circuit."
             REFERENCE 
				"ISIS.aoi l1IntermediateSystemPriority (47)"
             DEFVAL { 64 }
         ::= { csIsisCircEntry 25 }

         csIsisCircL1CircID OBJECT-TYPE
             SYNTAX CircuitID
             MAX-ACCESS read-only
             STATUS current
             DESCRIPTION
                 "The LAN ID allocated by the LAN Level 1 Designated
                 Intermediate System. Where this system is not aware of
                 the value (because it is not participating in the Level 1
                 Designated Intermediate System election), this object has
                 the value which would be proposed for this circuit (i.e.
                 the concatenation of the local system ID and the one
                 octet local Circuit ID for this circuit."
             REFERENCE 
				"ISIS.aoi l1CircuitID (48)"
         ::= { csIsisCircEntry 26 }

         csIsisCircL1DesIS OBJECT-TYPE
             SYNTAX SystemID
             MAX-ACCESS read-only
             STATUS current
             DESCRIPTION
                 "The ID of the LAN Level 1 Designated Intermediate System
                 on this circuit. If, for any reason this system is not
                 partaking in the relevant Designated Intermediate System
                 election process, then the value returned is the zero
                 length OCTET STRING."
             REFERENCE 
				"ISIS.aoi l1DesignatedIntermediateSystem (49)"
         ::= { csIsisCircEntry 27 }

         csIsisCircLANL1DesISChanges OBJECT-TYPE
             SYNTAX Counter32
             MAX-ACCESS read-only
             STATUS current
             DESCRIPTION
                 "The number of times the LAN Level 1 Designated
                 Intermediate System has changed."
             REFERENCE 
				"ISIS.aoi
                 lanL1DesignatedIntermediateSystemChanges (50)"
         ::= { csIsisCircEntry 28 }

     -- The following objects map those from the
     -- linkageISISLevel2Broadcast-P package

         csIsisCircL2ISPriority OBJECT-TYPE
             SYNTAX ISPriority
             MAX-ACCESS read-create
             STATUS current
             DESCRIPTION
                 "The priority for becoming LAN level 2 Designated
                 Intermediate System."
             REFERENCE 
				"ISIS.aoi l2IntermediateSystemPriority (73)"
             DEFVAL { 64 }
         ::= { csIsisCircEntry 29 }

         csIsisCircL2CircID OBJECT-TYPE
             SYNTAX CircuitID
             MAX-ACCESS read-only
             STATUS current
             DESCRIPTION
                 "The LAN ID allocated by the LAN Level 2 Designated
                 Intermediate System. Where this system is not aware of
                 this value (because it is not participating in the Level
                 2 Designated Intermediate System election), this object
                 has the value which would be proposed for this circuit
                 (i.e. the concatenation of the local system ID and the
                 one octet local Circuit ID for this circuit."
             REFERENCE 
				"ISIS.aoi l2CircuitID (74)"
         ::= { csIsisCircEntry 30 }

         csIsisCircL2DesIS OBJECT-TYPE
             SYNTAX SystemID
             MAX-ACCESS read-only
             STATUS current
             DESCRIPTION
                 "The ID of the LAN Level 2 Designated Intermediate System
                 on this circuit. If, for any reason, this system is not
                 partaking in the relevant Designated Intermediate System
                 election process, then the value returned is the zero
                 length OCTET STRING."
             REFERENCE 
				"ISIS.aoi l2DesignatedIntermediateSystem (75)"
         ::= { csIsisCircEntry 31 }

         csIsisCircLANL2DesISChanges OBJECT-TYPE
             SYNTAX Counter32
             MAX-ACCESS read-only
             STATUS current
             DESCRIPTION
                 "The number of times the LAN Level 2 Designated
                 Intermediate System has changed."
             REFERENCE 
				"ISIS.aoi
                 lanL2DesignatedIntermediateSystemChanges (76)"
         ::= { csIsisCircEntry 32 }

         csIsisCircMCAddr OBJECT-TYPE
             SYNTAX INTEGER{
                 group (1),
                 functional (2)
                 }
             MAX-ACCESS read-create
             STATUS current
             DESCRIPTION
                 "Specifies which type of multicast address will
                 be used for sending HELLO PDUs on this
                 circuit."
             DEFVAL { group }
         ::= { csIsisCircEntry 33 }

         csIsisCircPtToPtCircID OBJECT-TYPE
             SYNTAX CircuitID
             MAX-ACCESS read-only
             STATUS current
             DESCRIPTION
                 "The ID of the circuit allocated during initialization.
                 If no value has been negotiated (either because the
                 adjacency is to an End System, or because initialization
                 has not yet successfully completed), this object has the
                 value which would be proposed for this circuit (i.e. the
                 concatenation of the local system ID and the one octet
                 local Circuit ID for this circuit."
             REFERENCE 
				"ISIS.aoi ptPtCircuitID (51)"
         ::= { csIsisCircEntry 34 }

         csIsisCircL1HelloTimer OBJECT-TYPE
             SYNTAX Integer32 (10..600000)
             MAX-ACCESS read-create
             STATUS current
             DESCRIPTION
                 "Maximum period, in milliseconds, between Level 1
                 IIH PDUs on multiaccess networks.  It is also used
                 as the period between Hellos on point to point circuits.
                 This object follows the resettingTimer behaviour."
             REFERENCE 
				"ISIS.aoi iSISHelloTimer (45)"
             DEFVAL { 10 }
         ::= { csIsisCircEntry 35 }

         csIsisCircL2HelloTimer OBJECT-TYPE
             SYNTAX Integer32 (10..600000)
             MAX-ACCESS read-create
             STATUS current
             DESCRIPTION
                 "Maximum period, in milliseconds, between Level 1
                 IIH PDUs on multiaccess networks.  This object
                 follows the resettingTimer behaviour."
             REFERENCE 
				"ISIS.aoi iSISHelloTimer (45)"
             DEFVAL { 10 }
         ::= { csIsisCircEntry 36 }

         csIsisCircL1HelloMultiplier OBJECT-TYPE
             SYNTAX Integer32 (2..100)
             MAX-ACCESS read-create
             STATUS current
             DESCRIPTION
                 "This value is multiplied by the corresponding HelloTimer
                 and the result in seconds (rounded up) is used as the
                 holding time in transmitted hellos, to be used by receivers
                 of hello packets from this IS"
             REFERENCE 
				"ISIS.aoi iSISHelloTimer (45)"
             DEFVAL { 3 }
         ::= { csIsisCircEntry 37 }

         csIsisCircL2HelloMultiplier OBJECT-TYPE
             SYNTAX Integer32 (2..100)
             MAX-ACCESS read-create
             STATUS current
             DESCRIPTION
                 "This value is multiplied by the corresponding HelloTimer
                 and the result in seconds (rounded up) is used as the
                 holding time in transmitted hellos, to be used by receivers
                 of hello packets from this IS"
             REFERENCE 
				"ISIS.aoi iSISHelloTimer (45)"
             DEFVAL { 3 }
         ::= { csIsisCircEntry 38 }

         csIsisCircDRL1HelloTimer OBJECT-TYPE
             SYNTAX Integer32 (10..120000)
             MAX-ACCESS read-create
             STATUS current
             DESCRIPTION
                 "Period, in milliseconds, between Level 1 PDUs on
                 multiaccess networks when this IS is the Designated
                 Intermediate System.  This object follows the
                 resettingTimer behaviour."
             REFERENCE 
				"ISIS.aoi iSISHelloTimer (45)"
             DEFVAL { 10 }
         ::= { csIsisCircEntry 39 }

         csIsisCircDRL2HelloTimer OBJECT-TYPE
             SYNTAX Integer32 (10..120000)
             MAX-ACCESS read-create
             STATUS current
             DESCRIPTION
                 "Period, in milliseconds, between Level 2 PDUs on
                 multiaccess networks when this IS is the Designated
                 Intermediate System.  This object follows the
                 resettingTimer behaviour."
             REFERENCE 
				"ISIS.aoi iSISHelloTimer (45)"
             DEFVAL { 10 }
         ::= { csIsisCircEntry 40 }

         csIsisCircMinBroadLSPTransInt OBJECT-TYPE
             SYNTAX Integer32 (1..1000)
             MAX-ACCESS read-create
             STATUS current
             DESCRIPTION
                 "Minimum interval, in milliseconds, between transmission
                 of LSPs on a broadcast circuit. This object follows the
                 resettingTimer behaviour. This timer shall be capable of
                 a resolution not coarser than 10 milliseconds."
             REFERENCE 
				"ISIS.aoi minimumBroadcastLSPTransmissionInterval (7)"
             DEFVAL { 33 }
         ::= { csIsisCircEntry 41 }

         csIsisCircL1MinLSPTransInt OBJECT-TYPE
             SYNTAX Integer32 (1..300)
             MAX-ACCESS read-create
             STATUS current
             DESCRIPTION
                 "Minimum interval, in seconds, between re-transmission of
                 an Level 1 LSP. This object follows the resettingTimer
                 behaviour."
             REFERENCE 
				"ISIS.aoi minimumLSPTransmissionInterval (5)"
             DEFVAL { 5 }
         ::= { csIsisCircEntry 42 }

         csIsisCircL2MinLSPTransInt OBJECT-TYPE
             SYNTAX Integer32 (1..300)
             MAX-ACCESS read-create
             STATUS current
             DESCRIPTION
                 "Minimum interval, in seconds, between re-transmission of
                 an Level 2 LSP. This object follows the resettingTimer
                 behaviour."
             REFERENCE 
				"ISIS.aoi minimumLSPTransmissionInterval (5)"
             DEFVAL { 5 }
         ::= { csIsisCircEntry 43 }

         csIsisCircL1CSNPInterval OBJECT-TYPE
             SYNTAX Integer32 (1..600)
             MAX-ACCESS read-create
             STATUS current
             DESCRIPTION
                 "Interval of time, in seconds, between transmission
                 of Level 1 CSNPs on multiaccess networks if this
                 router is the designated router."
             REFERENCE 
				"NONE"
             DEFVAL { 10 }
         ::= { csIsisCircEntry 44 }

         csIsisCircL2CSNPInterval OBJECT-TYPE
             SYNTAX Integer32 (1..600)
             MAX-ACCESS read-create
             STATUS current
             DESCRIPTION
                 "Interval of time, in seconds, between transmission
                 of Level 2 CSNPs on multiaccess networks if this
                 router is the designated router."
             REFERENCE 
				"NONE"
             DEFVAL { 10 }
         ::= { csIsisCircEntry 45 }

         csIsisCircL1PartSNPInterval OBJECT-TYPE
             SYNTAX Integer32 (1..120)
             MAX-ACCESS read-create
             STATUS current
             DESCRIPTION
                 "Minimum interval between sending Level 1 Partial Sequence
                 Number PDUs. This object follows the resettingTimer behaviour."
             REFERENCE 
				"ISIS.aoi partialSNPInterval (14)"
             DEFVAL { 2 }
         ::= { csIsisCircEntry 46 }

         csIsisCircL2PartSNPInterval OBJECT-TYPE
             SYNTAX Integer32 (1..120)
             MAX-ACCESS read-create
             STATUS current
             DESCRIPTION
                 "Minimum interval between sending Level 2 Partial Sequence
                 Number PDUs. This object follows the resettingTimer behaviour."
             REFERENCE 
				"ISIS.aoi partialSNPInterval (14)"
             DEFVAL { 2 }
         ::= { csIsisCircEntry 47 }

         csIsisCircLSPThrottle OBJECT-TYPE
             SYNTAX Integer32 (1..65535)
             MAX-ACCESS read-create
             STATUS current
             DESCRIPTION
                 "Minimal interval of time, in milliseconds, between
                 transmissions of LSPs on a point to point interface."
             REFERENCE
				 "NONE"
             DEFVAL { 33 }
         ::= { csIsisCircEntry 48 }

         csIsisCircPassiveCircuit OBJECT-TYPE
             SYNTAX TruthValue
             MAX-ACCESS read-create
             STATUS current
             DESCRIPTION
                 "Should we include this interface in LSPs, even if
                 it is not running the ISIS Protocol?"
             REFERENCE 
				"NONE"
             DEFVAL { false }
         ::= { csIsisCircEntry 49 }

         csIsisCircMeshGroupEnabled OBJECT-TYPE
             SYNTAX INTEGER {
                     inactive(1),
                     blocked(2),
                     set(3)
             }
             MAX-ACCESS read-create
             STATUS current
             DESCRIPTION
                 "Is this port a member of a mesh group, or blocked?
                 Circuits in the same mesh group act as a virtual
                 multiaccess network.  LSPs seen on one circuit in
                 a mesh group will not be flooded to another circuit
                 in the same mesh group."
             REFERENCE 
				"NONE"
             DEFVAL { inactive }
         ::= { csIsisCircEntry 50 }

         csIsisCircMeshGroup OBJECT-TYPE
             SYNTAX Integer32 (1..2000000000)
             MAX-ACCESS read-create
             STATUS current
             DESCRIPTION
                 "Circuits in the same mesh group act as a virtual
                 multiaccess network.  LSPs seen on one circuit in
                 a mesh group will not be flooded to another circuit
                 in the same mesh group.  If csIsisCircMeshGroupEnabled
                 is false, this value is ignored."
             REFERENCE 
				"NONE"
             DEFVAL { 1 }
         ::= { csIsisCircEntry 51 }

         csIsisCircL1AuthType OBJECT-TYPE
             SYNTAX INTEGER {
                     none(1),
                     plaintext(2)
                 }
             MAX-ACCESS read-create
             STATUS current
             DESCRIPTION
                 "What authentication scheme, if any, is used to protect
                 Level 1 and Point-to-Point hello packets?"
             REFERENCE 
				"NONE"
             DEFVAL { none }
         ::= { csIsisCircEntry 52 }

         csIsisCircL1Password OBJECT-TYPE
             SYNTAX OCTET STRING (SIZE (0..255))
             MAX-ACCESS read-create 
             STATUS current
             DESCRIPTION
                 "The value to be used as the Authentication Key in Level 1
                 and Point-to-Point hello packets whenever the corresponding
                 instance of csIsisCircL1AuthType has a value of plaintext.
                 A modification of the corresponding instance of
                 csIsisCircL1AuthType does not modify the csIsisCircL1Password
                 value.

                 Reading this object always results in an  OCTET
                 STRING of length zero; authentication may not
                 be bypassed by reading the MIB object."
             REFERENCE 
				"NONE"
             DEFVAL { ''H }
         ::= { csIsisCircEntry 53 }

         csIsisCircL2AuthType OBJECT-TYPE
             SYNTAX INTEGER {
                     none(1),
                     plaintext(2)
                 }
             MAX-ACCESS read-create
             STATUS current
             DESCRIPTION
                 "What authentication scheme, if any, is used to protect
                  Level 2 hello packets?"
             REFERENCE 
				"NONE"
             DEFVAL { none }
         ::= { csIsisCircEntry 54 }

         csIsisCircL2Password OBJECT-TYPE
             SYNTAX OCTET STRING (SIZE (0..255))
             MAX-ACCESS read-create
             STATUS current
             DESCRIPTION
                 "The value to be used as the Authentication Key in Level 1
                 Hello packets whenever the corresponding instance of
                 csIsisCircL1AuthType has a value of plaintext.  A
                 modification of the corresponding instance of
                 csIsisCircL1AuthType does not modify the
                 csIsisCircL1Password value.
                 Reading this object always results in an  OCTET
                 STRING of length zero; authentication may not
                 be bypassed by reading the MIB object."
             REFERENCE 
				"NONE"
             DEFVAL { ''H }
         ::= { csIsisCircEntry 55 }

         csIsisCircSmallHellos OBJECT-TYPE
             SYNTAX OperState
             MAX-ACCESS read-create
             STATUS current
             DESCRIPTION
                 "Can we send unpadded hellos on LAN circuits?  Off means
                 LAN Hellos must be padded."
              DEFVAL { off }
         ::= { csIsisCircEntry 56 }

         csIsisManAdjNeighNSAP OBJECT-TYPE
             SYNTAX OSINSAddress
             MAX-ACCESS read-create
             STATUS current
             DESCRIPTION
                 "The address of the neighbour if this is a manual adjacency.
                 This object follows the replaceOnlyWhileDisabled behaviour."
         ::= { csIsisCircEntry 57 }

         csIsisManAdjNeighSNPA OBJECT-TYPE
             SYNTAX SNPAAddress
             MAX-ACCESS read-create
             STATUS current
             DESCRIPTION
                 "The SNPA of the neighbour if this is a manual adjacency.
                 This object follows the replaceOnlyWhileDisabled behaviour."
         ::= { csIsisCircEntry 58 }

         csIsisCircIPEncaps OBJECT-TYPE
             SYNTAX TruthValue
             MAX-ACCESS read-create
             STATUS current
             DESCRIPTION
                 "Should we encapsulate IS-IS in IP packets?"
             DEFVAL { false }
         ::= { csIsisCircEntry 59 }

         csIsisCircUpTime OBJECT-TYPE
             SYNTAX Integer32
             MAX-ACCESS read-only
             STATUS current
             DESCRIPTION
                 "The amount of time in seconds since this circuit entered
                  state 'up'.

                 Note: This can be implemented as start time less
                 the current time."
         ::= { csIsisCircEntry 60 }

         csIsisCircIpAddress OBJECT-TYPE
             SYNTAX IpAddress
             MAX-ACCESS read-create
             STATUS current
             DESCRIPTION
                 "The IP Address of the VI that IS-IS is enabled on."
         ::= { csIsisCircEntry 61 }

         csIsisCircLevel OBJECT-TYPE
	     SYNTAX INTEGER {
                 level-1(1),
                 level-2(2),
                 level-1-2(3)
                 }
             MAX-ACCESS read-create
             STATUS current
             DESCRIPTION
                 "This is the IS-IS circuit level.
		  Level-1 only => isisCircLevel = 1,
		  Level-2 only => isisCircLevel = 2,
		  Level-1 or 2 => isisCircLevel = 3. "
         ::= { csIsisCircEntry 62 }


     -- The Circuit IS Group
     --
     -- The Circuit IS Group is present if the system supports the
     -- IS functions of the ISO 9542 protocol.
     -- The Circuit IS Table
     --
     -- This table is not implemented - jdp

     -- The IS Adjacency Group
     --
     -- The IS Adjacency Group is current and contains information
     -- about adjacencies to routers maintained by the Integrated
     -- IS-IS protocol
     --
     -- The IS Adjacency Table
     --
     -- Each adjacency to an IS corresponds to one entry in this
     -- table.

         csIsisISAdjTable OBJECT-TYPE
             SYNTAX SEQUENCE OF CsIsisISAdjEntry
             MAX-ACCESS not-accessible
             STATUS current
             DESCRIPTION
                 "The table of adjacencies to Intermediate Systems."
         ::= { csIsisISAdj 1 }

         csIsisISAdjEntry OBJECT-TYPE
             SYNTAX CsIsisISAdjEntry
             MAX-ACCESS not-accessible
             STATUS current
             DESCRIPTION
                 "Each entry corresponds to one adjacency to an
                 Intermediate System on this system."
             INDEX { csOrionGlobalVPNIndex, 
		     csOrionVPNVRouterIndex,
		     csIsisISAdjSysInstance,
                     csIsisISAdjCircIndex,
                     csIsisISAdjIndex }
         ::= { csIsisISAdjTable 1 }

         CsIsisISAdjEntry ::=
             SEQUENCE {
                 csIsisISAdjSysInstance
                     Integer32,
                 csIsisISAdjCircIndex
                     Integer32,
                 csIsisISAdjIndex
                     Integer32,
                 csIsisISAdjState
                     INTEGER,
                 csIsisISAdjNeighSNPAAddress
                     SNPAAddress,
                 csIsisISAdjNeighSysType
                     INTEGER,
                 csIsisISAdjNeighSysID
                     OCTET STRING,
                 csIsisISAdjUsage
                     INTEGER,
                 csIsisISAdjHoldTimer
                     Integer32,
                 csIsisISAdjNeighPriority
                     ISPriority,
                 csIsisISAdjUpTime
                     Integer32
           }

         csIsisISAdjSysInstance OBJECT-TYPE
             SYNTAX Integer32
             MAX-ACCESS not-accessible
             STATUS current
             DESCRIPTION
                 "The unique identifier of the Integrated IS-IS instance
                 to which this row corresponds."
         ::= { csIsisISAdjEntry 1 }

         csIsisISAdjCircIndex OBJECT-TYPE
             SYNTAX Integer32
             MAX-ACCESS not-accessible
             STATUS current
             DESCRIPTION
                 "The Circuit Index of the Circuit which is the parent of
                 the IS adjacency."
         ::= { csIsisISAdjEntry 2 }

         csIsisISAdjIndex OBJECT-TYPE
             SYNTAX Integer32
             MAX-ACCESS not-accessible
             STATUS current
             DESCRIPTION
                 "A unique value identifying the IS adjacency from all
                 other such adjacencies on this circuit. This value is
                 assigned by the system when the adjacency is created
                 automatically."
         ::= { csIsisISAdjEntry 3 }

         csIsisISAdjState OBJECT-TYPE
             SYNTAX INTEGER {
                 initializing (1),
                 up (2),
                 failed (3),
                 down (4)
                 }
             MAX-ACCESS read-only
             STATUS current
             DESCRIPTION
                 "The state of the adjacency"
             REFERENCE 
				"ISIS.aoi adjacencyState (78)"
         ::= { csIsisISAdjEntry 4 }

         csIsisISAdjNeighSNPAAddress OBJECT-TYPE
             SYNTAX SNPAAddress
             MAX-ACCESS read-only
             STATUS current
             DESCRIPTION
                 "The SNPA address of the neighboring system."
             REFERENCE 
				"ISIS.aoi neighbourSNPAAddress (79)"
         ::= { csIsisISAdjEntry 5 }

         csIsisISAdjNeighSysType OBJECT-TYPE
             SYNTAX INTEGER {
                 unknown(1),
                 intermediateSystem(3),
                 l1IntermediateSystem(4),
                 l2IntermediateSystem(5)
                 }
             MAX-ACCESS read-only
             STATUS current
             DESCRIPTION
                 "The type of the neighboring system."
             REFERENCE 
				"ISIS.aoi neighbourSystemType (80)"
         ::= { csIsisISAdjEntry 6 }

         csIsisISAdjNeighSysID OBJECT-TYPE
             SYNTAX OCTET STRING (SIZE(0..12))
             MAX-ACCESS read-only
             STATUS current
             DESCRIPTION
                 "The system ID and circuit ID of the neighboring
                 Intermediate System set from the source ID field
                 of the neighbor's IIH PDUs."
             REFERENCE 
				"ISIS.aoi neighbourSystemIds (83)"
         ::= { csIsisISAdjEntry 7 }

         csIsisISAdjUsage OBJECT-TYPE
             SYNTAX INTEGER {
                 undefined(1),
                 level1(2),
                 level2(3),
                 level1and2(4)
                 }
             MAX-ACCESS read-only
             STATUS current
             DESCRIPTION
                 "An adjacency of type level1 is used for level 1
                 traffic only. An adjacency of type level2 is used
                 for level 2 traffic only. An adjacency of type level1and2
                 is used for both level 1 and level 2 traffic. There
                 may be two adjacencies (of types level1 and level2)
                 between the same pair of Intermediate Systems."
             REFERENCE 
				"ISIS.aoi adjacencyUsage (82)"
         ::= { csIsisISAdjEntry 8 }

         csIsisISAdjHoldTimer OBJECT-TYPE
             SYNTAX Integer32 (1..65535)
             MAX-ACCESS read-only
             STATUS current
             DESCRIPTION
                 "The holding time for this adjacency updated from
                 received IIH PDUs."
             REFERENCE 
				"ISIS.aoi holdingTimer (85)"
         ::= { csIsisISAdjEntry 9 }

         csIsisISAdjNeighPriority OBJECT-TYPE
             SYNTAX ISPriority
             MAX-ACCESS read-only
             STATUS current
             DESCRIPTION
                 "Priority of the neighboring Intermediate System for
                 becoming the LAN Level 1 Designated Intermediate System
                 if the value of csIsisISAdjNeighSysType is
                 L1IntermediateSystem or LAN Level 2 Designated
                 Intermediate System if the value of
                 csIsisISAdjNeighSysType is L2IntermediateSystem."
             REFERENCE 
				"ISIS.aoi lANPriority (86)"
         ::= { csIsisISAdjEntry 10 }

         csIsisISAdjUpTime OBJECT-TYPE
             SYNTAX Integer32
             MAX-ACCESS read-only
             STATUS current
             DESCRIPTION
                 "The amount of time in seconds since this adjacency entered
                 state 'up'.

                 Note: This can be implemented as start time less
                 the current time."
         ::= { csIsisISAdjEntry 11 }

     -- The IS Adjacency Area Address Table

     -- The IS Adjacency Area Address Table contains the set of
     -- Area Addresses of neighboring
     -- Intermediate Systems as reported in IIH PDUs.

         csIsisISAdjAreaAddrTable OBJECT-TYPE
             SYNTAX SEQUENCE OF CsIsisISAdjAreaAddrEntry
             MAX-ACCESS not-accessible
             STATUS current
             DESCRIPTION
                 "This table contains the set of Area Addresses of
                 neighboring Intermediate Systems as reported in received
                 IIH PDUs."
             REFERENCE 
				"ISIS.aoi areaAddressesOfNeighbour (84)"
         ::= { csIsisISAdj 2 }

         csIsisISAdjAreaAddrEntry OBJECT-TYPE
             SYNTAX CsIsisISAdjAreaAddrEntry
             MAX-ACCESS not-accessible
             STATUS current
             DESCRIPTION
                 "Each entry contains one Area Address reported by a
                 neighboring Intermediate System in its IIH PDUs."
             INDEX { csOrionGlobalVPNIndex, 
		     csOrionVPNVRouterIndex,
		     csIsisISAdjAreaAddrSysInstance,
                     csIsisISAdjAreaAddrCircIndex,
                     csIsisISAdjAreaAddrAdjIndex,
                     csIsisISAdjAreaAddress }
         ::= { csIsisISAdjAreaAddrTable 1 }

         CsIsisISAdjAreaAddrEntry ::=
             SEQUENCE {
                 csIsisISAdjAreaAddrSysInstance
                     Integer32,
                 csIsisISAdjAreaAddrCircIndex
                     Integer32,
                 csIsisISAdjAreaAddrAdjIndex
                     Integer32,
                 csIsisISAdjAreaAddress
                     OSINSAddress
                 }

         csIsisISAdjAreaAddrSysInstance OBJECT-TYPE
             SYNTAX Integer32
             MAX-ACCESS not-accessible
             STATUS current
             DESCRIPTION
                 "The unique identifier of the Integrated IS-IS instance
                 to which this row corresponds."
         ::= { csIsisISAdjAreaAddrEntry 1 }

         csIsisISAdjAreaAddrCircIndex OBJECT-TYPE
             SYNTAX Integer32
             MAX-ACCESS not-accessible
             STATUS current
             DESCRIPTION
                 "The identifier of the Circuit which is the parent of the
                 IS adjacency to which this Area Address entry
                 corresponds."
         ::= { csIsisISAdjAreaAddrEntry 2 }

         csIsisISAdjAreaAddrAdjIndex OBJECT-TYPE
             SYNTAX Integer32
             MAX-ACCESS not-accessible
             STATUS current
             DESCRIPTION
                 "The identifier of the IS adjacency to which this entry
                 belongs."
         ::= { csIsisISAdjAreaAddrEntry 3 }

         csIsisISAdjAreaAddress OBJECT-TYPE
             SYNTAX OSINSAddress
             MAX-ACCESS read-only
             STATUS current
             DESCRIPTION
                 "One Area Address as reported in IIH PDUs received from
                 the neighbor."
         ::= { csIsisISAdjAreaAddrEntry 4 }

     -- The IS Adjacency IP Group

     -- The IS Adjacency IP Group is present if the system supports
     -- IP Integrated IS-IS

     -- The IS Adjacency IP Address Table

     -- The IS Adjacency IP Address Table contains the
     -- set of IP Addresses of neighboring Intermediate Systems
     -- as reported in received IIH PDUs.

         csIsisISAdjIPAddrTable OBJECT-TYPE
             SYNTAX SEQUENCE OF CsIsisISAdjIPAddrEntry
             MAX-ACCESS not-accessible
             STATUS current
             DESCRIPTION
                 "This table contains the set of IP Addresses of
                 neighboring Intermediate Systems as reported in received
                 IIH PDUs."
         ::= { csIsisISAdj 3 }

         csIsisISAdjIPAddrEntry OBJECT-TYPE
             SYNTAX CsIsisISAdjIPAddrEntry
             MAX-ACCESS not-accessible
             STATUS current
             DESCRIPTION
                 "Each entry contains one IP Address reported by a
                 neighboring Intermediate System in its IIH PDUs."
             INDEX { csOrionGlobalVPNIndex, 
		     csOrionVPNVRouterIndex,
		     csIsisISAdjIPAddrSysInstance,
                     csIsisISAdjIPAddrCircIndex,
                     csIsisISAdjIPAddrAdjIndex
                     }
         ::= { csIsisISAdjIPAddrTable 1 }

         CsIsisISAdjIPAddrEntry ::=
             SEQUENCE {
                 csIsisISAdjIPAddrSysInstance
                     Integer32,
                 csIsisISAdjIPAddrCircIndex
                     Integer32,
                 csIsisISAdjIPAddrAdjIndex
                     Integer32,
                 csIsisISAdjIPAddress
                     IpAddress
             }

         csIsisISAdjIPAddrSysInstance OBJECT-TYPE
             SYNTAX Integer32
             MAX-ACCESS not-accessible
             STATUS current
             DESCRIPTION
                 "The unique identifier of the Integrated IS-IS instance
                 to which this row corresponds."
         ::= { csIsisISAdjIPAddrEntry 1 }

         csIsisISAdjIPAddrCircIndex OBJECT-TYPE
             SYNTAX Integer32
             MAX-ACCESS not-accessible
             STATUS current
             DESCRIPTION
                 "The identifier of the Circuit which is the parent of the
                 IS adjacency to which this IP Address entry corresponds."
         ::= { csIsisISAdjIPAddrEntry 2 }

         csIsisISAdjIPAddrAdjIndex OBJECT-TYPE
             SYNTAX Integer32
             MAX-ACCESS not-accessible
             STATUS current
             DESCRIPTION
                 "The identifier of the IS adjacency to which this entry
                 belongs."
         ::= { csIsisISAdjIPAddrEntry 3 }

         csIsisISAdjIPAddress OBJECT-TYPE
             SYNTAX IpAddress
             MAX-ACCESS read-only
             STATUS current
             DESCRIPTION
                 "One IP Address as reported in IIH PDUs received from the
                 neighbor."
         ::= { csIsisISAdjIPAddrEntry 4 }

     -- The IS Adjacency Integrated Group
     --
     -- The IS Adjacency Integrated Group is present if the system
     -- supports Integrated ISIS.
     --
     --
     -- The IS Adjacency Protocol Supported Table
     --
     -- The IS Adjacency Protocol Supported Table contains the set of
     -- protocols supported by neighboring
     -- Intermediate Systems as reported in received IIH PDUs.
     --
         csIsisISAdjProtSuppTable OBJECT-TYPE
             SYNTAX SEQUENCE OF CsIsisISAdjProtSuppEntry
             MAX-ACCESS not-accessible
             STATUS current
             DESCRIPTION
                 "This table contains the set of protocols supported by
                 neighboring Intermediate Systems as reported in received
                 IIH PDUs."
         ::= { csIsisISAdj 4 }

         csIsisISAdjProtSuppEntry OBJECT-TYPE
             SYNTAX CsIsisISAdjProtSuppEntry
             MAX-ACCESS not-accessible
             STATUS current
             DESCRIPTION
                 "Each entry contains one protocol supported by a
                 neighboring Intermediate System as reported in its IIH
                 PDUs."
             INDEX { csOrionGlobalVPNIndex, 
		     csOrionVPNVRouterIndex,
		     csIsisISAdjProtSuppSysInstance,
                     csIsisISAdjProtSuppCircIndex,
                     csIsisISAdjProtSuppAdjIndex,
                     csIsisISAdjProtSuppProtocol }
         ::= { csIsisISAdjProtSuppTable 1 }

         CsIsisISAdjProtSuppEntry ::=
             SEQUENCE {
                 csIsisISAdjProtSuppSysInstance
                     Integer32,
                 csIsisISAdjProtSuppCircIndex
                     Integer32,
                 csIsisISAdjProtSuppAdjIndex
                     Integer32,
                 csIsisISAdjProtSuppProtocol
                     SupportedProtocol
             }

         csIsisISAdjProtSuppSysInstance OBJECT-TYPE
             SYNTAX Integer32
             MAX-ACCESS not-accessible
             STATUS current
             DESCRIPTION
                 "The unique identifier of the Integrated IS-IS instance
                 to which this row corresponds."
         ::= { csIsisISAdjProtSuppEntry 1 }

         csIsisISAdjProtSuppCircIndex OBJECT-TYPE
             SYNTAX Integer32
             MAX-ACCESS not-accessible
             STATUS current
             DESCRIPTION
                 "The identifier of the Circuit which is the parent of the
                 IS adjacency to which this supported protocol entry
                 corresponds."
         ::= { csIsisISAdjProtSuppEntry 2 }

         csIsisISAdjProtSuppAdjIndex OBJECT-TYPE
             SYNTAX Integer32
             MAX-ACCESS not-accessible
             STATUS current
             DESCRIPTION
                 "The identifier the IS adjacency to which this entry
                 corresponds."
         ::= { csIsisISAdjProtSuppEntry 3 }

         csIsisISAdjProtSuppProtocol OBJECT-TYPE
             SYNTAX SupportedProtocol
             MAX-ACCESS read-only
             STATUS current
             DESCRIPTION
                 "One supported protocol as reported in IIH PDUs received
                 from the neighbor."
         ::= { csIsisISAdjProtSuppEntry 4 }

     -- The IP Reachable Address Group
     -- The IP Reachable Address Group is optional.

     -- Each entry records information about one IP reachable
     -- address manually configured on this system or learned from
     -- another protocol.

         csIsisIPRATable OBJECT-TYPE
             SYNTAX SEQUENCE OF CsIsisIPRAEntry
             MAX-ACCESS not-accessible
             STATUS current
             DESCRIPTION
                 "The table of IP Reachable Addresses to networks,
                 subnetworks or hosts either manually configured or
                 learned from another protocol."
         ::= { csIsisIPReachAddr 1 }

         csIsisIPRAEntry OBJECT-TYPE
             SYNTAX CsIsisIPRAEntry
             MAX-ACCESS not-accessible
             STATUS current
             DESCRIPTION
                 "Each entry defines an IP Reachable Address to a network,
                 subnetwork or host."
             INDEX {  csOrionGlobalVPNIndex, 
		      csOrionVPNVRouterIndex,
	 	      csIsisIPRASysInstance,
                      csIsisIPRACircIndex,
                      csIsisIPRAType,
                      csIsisIPRAIndex }
         ::= { csIsisIPRATable 1 }

         CsIsisIPRAEntry ::=
             SEQUENCE {
                 csIsisIPRASysInstance
                     Integer32,
                 csIsisIPRACircIndex
                     Integer32,
                 csIsisIPRAIndex
                     Integer32,
                 csIsisIPRAType
                     INTEGER,
                 csIsisIPRADest
                     IpAddress,
                 csIsisIPRAMask
                     IpAddress,
                 csIsisIPRAExistState
                     RowStatus,
                 csIsisIPRAOperState
                     OperState,
                 csIsisIPRADefMetric
                     DefaultMetric,
                 csIsisIPRADelMetric
                     OtherMetric,
                 csIsisIPRAExpMetric
                     OtherMetric,
                 csIsisIPRAErrMetric
                     OtherMetric,
                 csIsisIPRADefMetricType
                     MetricType,
                 csIsisIPRADelMetricType
                     MetricType,
                 csIsisIPRAExpMetricType
                     MetricType,
                 csIsisIPRAErrMetricType
                     MetricType,
                 csIsisIPRASNPAAddress
                     SNPAAddress
             }

         csIsisIPRASysInstance OBJECT-TYPE
             SYNTAX Integer32
             MAX-ACCESS not-accessible
             STATUS current
             DESCRIPTION
                 "The identifier of the Integrated IS-IS instance to which
                 this row corresponds. This object follows the index and
                 manualOrAutomatic behaviours."
         ::= { csIsisIPRAEntry 1 }

         csIsisIPRACircIndex OBJECT-TYPE
             SYNTAX Integer32
             MAX-ACCESS not-accessible
             STATUS current
             DESCRIPTION
                 "The identifier of the Circuit over which this IP
                 destination is reachable. This object follows the index
                 and manualOrAutomatic behaviours."
         ::= { csIsisIPRAEntry 2 }

         csIsisIPRAIndex OBJECT-TYPE
             SYNTAX Integer32
             MAX-ACCESS not-accessible
             STATUS current
             DESCRIPTION
                 "The identifier for this csIsisIPRAEntry. This value must
                 be unique amongst all IP Reachable Addresses on the same
                 parent Circuit. This object follows the index and
                 manualOrAutomatic behaviours."
         ::= { csIsisIPRAEntry 3 }

         csIsisIPRAType OBJECT-TYPE
             SYNTAX   INTEGER
                 {
                     manual (1),
                     automatic (2)
                 }
             MAX-ACCESS not-accessible
             STATUS current
             DESCRIPTION
                 "The type of this IP Reachable Address. Those of type
                 manual are created by the network manager. Those of type
                 automatic are created through propagation of routing
                 information from another routing protocol."
         ::= { csIsisIPRAEntry 4 }

         csIsisIPRADest OBJECT-TYPE
             SYNTAX IpAddress
             MAX-ACCESS read-create
             STATUS current
             DESCRIPTION
                 "The destination of this IP Reachable Address. This is
                 either a network address, subnetwork address or host
                 address. This object follows the manualOrAutomatic
                 behaviour."
         ::= { csIsisIPRAEntry 5 }

         csIsisIPRAMask OBJECT-TYPE
             SYNTAX IpAddress
             MAX-ACCESS read-create
             STATUS current
             DESCRIPTION
                 "The network mask for the IP Address in the csIsisIPRADest
                 object. This object follows the manualOrAutomatic
                 behaviour."
         ::= { csIsisIPRAEntry 6 }

         csIsisIPRAExistState OBJECT-TYPE
             SYNTAX RowStatus
             MAX-ACCESS read-create
             STATUS current
             DESCRIPTION
                 "The state of this IP Reachable Address. This object
                 follows the ExistenceState and manualOrAutomatic
                 behaviours."
             DEFVAL { active }
         ::= { csIsisIPRAEntry 7 }

         csIsisIPRAOperState OBJECT-TYPE
             SYNTAX OperState
             MAX-ACCESS read-create
             STATUS current
             DESCRIPTION
                 "The operational state of the IP Reachable Address. This
                 object follows the operationalState and manualOrAutomatic
                 behaviours."
             DEFVAL { off }
         ::= { csIsisIPRAEntry 8 }

         csIsisIPRADefMetric OBJECT-TYPE
             SYNTAX DefaultMetric
             MAX-ACCESS read-create
             STATUS current
             DESCRIPTION
                 "The default metric value for reaching the specified
                 destination over this circuit. This object follows the
                 manualOrAutomatic behaviour."
             DEFVAL { 20 }
         ::= { csIsisIPRAEntry 9 }

         csIsisIPRADelMetric OBJECT-TYPE
             SYNTAX OtherMetric
             MAX-ACCESS read-create
             STATUS current
             DESCRIPTION
                 "The delay metric value for reaching the specified
                 destination over this circuit. The value zero is reserved
                 to mean the metric is not supported. This object follows
                 the manualOrAutomatic behaviour."
             DEFVAL { 0 }
         ::= { csIsisIPRAEntry 10 }

         csIsisIPRAExpMetric OBJECT-TYPE
             SYNTAX OtherMetric
             MAX-ACCESS read-create
             STATUS current
             DESCRIPTION
                 "The expense metric value for reaching the specified
                 destination over this circuit. The value zero is reserved
                 to mean the metric is not supported. This object follows
                 the manualOrAutomatic behaviour."
             DEFVAL { 0 }
         ::= { csIsisIPRAEntry 11 }

         csIsisIPRAErrMetric OBJECT-TYPE
             SYNTAX OtherMetric
             MAX-ACCESS read-create
             STATUS current
             DESCRIPTION
                 "The error metric value for reaching the specified
                 destination over this circuit. The value zero is reserved
                 to mean the metric is not supported. This object follows
                 the manualOrAutomatic behaviour."
             DEFVAL { 0 }
         ::= { csIsisIPRAEntry 12 }

         csIsisIPRADefMetricType OBJECT-TYPE
             SYNTAX MetricType
             MAX-ACCESS read-create
             STATUS current
             DESCRIPTION
                 "Indicates whether the default metric is internal or
                 external. This object follows the manualOrAutomatic
                 behaviour."
             DEFVAL { internal }
         ::= { csIsisIPRAEntry 13 }

         csIsisIPRADelMetricType OBJECT-TYPE
             SYNTAX MetricType
             MAX-ACCESS read-create
             STATUS current
             DESCRIPTION
                 "Indicates whether the delay metric is internal or
                 external. This object follows the manualOrAutomatic
                 behaviour."
             DEFVAL { internal }
         ::= { csIsisIPRAEntry 14 }

         csIsisIPRAExpMetricType OBJECT-TYPE
             SYNTAX MetricType
             MAX-ACCESS read-create
             STATUS current
             DESCRIPTION
                 "Indicates whether the expense metric is internal or
                 external. This object follows the manualOrAutomatic
                 behaviour."
             DEFVAL { internal }
         ::= { csIsisIPRAEntry 15 }

         csIsisIPRAErrMetricType OBJECT-TYPE
             SYNTAX MetricType
             MAX-ACCESS read-create
             STATUS current
             DESCRIPTION
                 "Indicates whether the error metric is internal or
                 external. This object follows the manualOrAutomatic
                 behaviour."
             DEFVAL { internal }
         ::= { csIsisIPRAEntry 16 }

         csIsisIPRASNPAAddress OBJECT-TYPE
             SYNTAX SNPAAddress
             MAX-ACCESS read-create
             STATUS current
             DESCRIPTION
                 "The SNPA Address to which a PDU may be forwarded in
                 order to reach a destination which matches this IP
                 Reachable Address. This object follows the
                 manualOrAutomatic behaviour."
             DEFVAL { ''H }
         ::= { csIsisIPRAEntry 17 }



----------------------------------------------------------------------
--
-- TE-RSVP Session Table (derived from RFC2206's rsvpSessionTable)
--
----------------------------------------------------------------------

csRsvpSessionTable  OBJECT-TYPE
   SYNTAX        SEQUENCE OF CsRsvpSessionEntry
   MAX-ACCESS    not-accessible
   STATUS        current
   DESCRIPTION
       "This  table  has one row for each session being managed by LSR.
        It provides the statistics pertaining to the session."
   ::= { csTeRsvpObjects 1 }

csRsvpSessionEntry OBJECT-TYPE
   SYNTAX        CsRsvpSessionEntry
   MAX-ACCESS    not-accessible
   STATUS        current
   DESCRIPTION
       "An entry in this table is created by LSR for every
        established session.
        This entry is indexed by Session destination IP address
        Tunnel Identifier and Extended Tunnel Identifier."
   INDEX         { csOrionGlobalVPNIndex, csOrionVPNVRouterIndex,
		   csRsvpSessionTunnelEndpoint, csRsvpSessionTunnelID,
                    csRsvpSessionExtendedTunnelID }
      ::= { csRsvpSessionTable 1 }



CsRsvpSessionEntry ::= SEQUENCE {
      csRsvpSessionTunnelEndpoint      IpAddress,
      csRsvpSessionTunnelID            INTEGER,
      csRsvpSessionExtendedTunnelID    Unsigned32,
      csRsvpSessionUpPsbs              Gauge32,
      csRsvpSessionDownPsbs            Gauge32,
      csRsvpSessionUpRsbs              Gauge32,
      csRsvpSessionDownRsbs            Gauge32
   }

csRsvpSessionTunnelEndpoint OBJECT-TYPE
   SYNTAX        IpAddress
   MAX-ACCESS    not-accessible
   STATUS        current
   DESCRIPTION
       "One of the indices  for  the row of the table.
        Specifies the IP address (IPv4 only supported) of
        the destination of the Session."
   ::= { csRsvpSessionEntry 1 }

csRsvpSessionTunnelID OBJECT-TYPE
   SYNTAX        INTEGER (0..65535) 
   MAX-ACCESS    not-accessible
   STATUS        current
   DESCRIPTION
       "One of the indices  for  the row of the table.
        Specifies the Tunnel identifier of the Session."
   ::= { csRsvpSessionEntry 2 }

csRsvpSessionExtendedTunnelID OBJECT-TYPE
   SYNTAX        Unsigned32
   MAX-ACCESS    not-accessible
   STATUS        current
   DESCRIPTION
       "One of the indices  for  the row of the table.
        Specifies the Extended Tunnel identifier of the Session."
   ::= { csRsvpSessionEntry 3 }

csRsvpSessionUpPsbs OBJECT-TYPE
   SYNTAX        Gauge32
   MAX-ACCESS    read-only
   STATUS        current
   DESCRIPTION
       "This object specifies the number of upside senders (Up PSBs)
        for this session known to this processor of this LSR."
   ::= { csRsvpSessionEntry 4 }

csRsvpSessionDownPsbs OBJECT-TYPE
   SYNTAX        Gauge32
   MAX-ACCESS    read-only
   STATUS        current
   DESCRIPTION
       "This object specifies the number of downside senders (Down PSBs)
        for this session known to this processor of this LSR."
   ::= { csRsvpSessionEntry 5 }

csRsvpSessionUpRsbs OBJECT-TYPE
   SYNTAX        Gauge32
   MAX-ACCESS    read-only
   STATUS        current
   DESCRIPTION
       "This object specifies the number of upside receivers (Up RSBs)
        for this session known to this processor of this LSR."
   ::= { csRsvpSessionEntry 6 }

csRsvpSessionDownRsbs OBJECT-TYPE
   SYNTAX        Gauge32
   MAX-ACCESS    read-only
   STATUS        current
   DESCRIPTION
       "This object specifies the number of downside receivers (Down RSBs)
        for this session known to this processor of this LSR."
   ::= { csRsvpSessionEntry 7 }


-- End of csRsvpSessionTable


----------------------------------------------------------------------
-- csRsvpIfTable specifies information pertaining to each interface
-- running TE-RSVP for this LSR.
----------------------------------------------------------------------
 
csRsvpIfTable  OBJECT-TYPE
   SYNTAX         SEQUENCE OF CsRsvpIfEntry
   MAX-ACCESS     not-accessible
   STATUS         current
   DESCRIPTION
        "This  table  has one row each for every interface of this LSR
         running TE-RSVP.
         Corresponding row in csRsvpNbrTable must be configured before
         a row in this table can be activated."
   ::= { csTeRsvpObjects 2 }
 
csRsvpIfEntry OBJECT-TYPE
   SYNTAX        CsRsvpIfEntry
   MAX-ACCESS    not-accessible
   STATUS        current
   DESCRIPTION
       "An entry in this table is created for every interface
        running TE-RSVP."
   INDEX         {  csOrionGlobalVPNIndex, csOrionVPNVRouterIndex,
					csOrionVIfIndex
                 }
      ::= { csRsvpIfTable 1 }
 
 
CsRsvpIfEntry ::= SEQUENCE {
	  csRsvpIfMaxBandwidth                       Integer32,
      csRsvpIfMaxFlowBandwidth					 Integer32,
      csRsvpIfUdpNbrs                            Gauge32,
      csRsvpIfIpNbrs                             Gauge32,
      csRsvpIfNbrs                               Gauge32,
      csRsvpIfEnabled                            TruthValue,
      csRsvpIfUdpRequired                        TruthValue,
      csRsvpIfRefreshBlockadeMultiple            INTEGER,
      csRsvpIfRefreshMultiple                    INTEGER,
      csRsvpIfTTL                                INTEGER,
      csRsvpIfRefreshInterval                    TimeInterval,
      csRsvpIfRouteDelay                         TimeInterval,
      csRsvpIfStatus                             RowStatus,
      csRsvpIfPktsIn                             Counter32,
      csRsvpIfPathIn                             Counter32,
      csRsvpIfResvIn                             Counter32,
      csRsvpIfPathTearIn                         Counter32,
      csRsvpIfPathErrIn                          Counter32,
      csRsvpIfResvTearIn                         Counter32,
      csRsvpIfResvErrIn                          Counter32,
      csRsvpIfResvConfIn                         Counter32,
      csRsvpIfPathOut                            Counter32,
      csRsvpIfResvOut                            Counter32,
      csRsvpIfPathTearOut                        Counter32,
      csRsvpIfPathErrOut                         Counter32,
      csRsvpIfResvTearOut                        Counter32,
      csRsvpIfResvErrOut                         Counter32,
      csRsvpIfResvConfOut                        Counter32,
      csRsvpIfBadPathIn                          Counter32,
      csRsvpIfBadResvIn                          Counter32,
      csRsvpIfBadPathTearIn                      Counter32,
      csRsvpIfBadResvTearIn                      Counter32,
      csRsvpIfBadPathErrIn                       Counter32,
      csRsvpIfBadResvErrIn                       Counter32,
      csRsvpIfBadResvConfIn                      Counter32,
      csRsvpIfBadOtherIn                         Counter32,
      csRsvpIfUpPsbsCreated                      Counter32,
      csRsvpIfDownPsbsCreated                    Counter32,
      csRsvpIfUpRsbsCreated                      Counter32,
      csRsvpIfDownRsbsCreated                    Counter32,
      csRsvpIfIngressLspsCreated                 Counter32,
      csRsvpIfEgressLspsCreated                  Counter32,
      csRsvpIfIpAddress                          IpAddress
   }


csRsvpIfMaxBandwidth    OBJECT-TYPE
   SYNTAX        Integer32
   MAX-ACCESS    read-create
   STATUS        current
   DESCRIPTION
       "RSVP Reservable Bandwidth (KBPS)"
   ::= { csRsvpIfEntry 1 }

csRsvpIfMaxFlowBandwidth    OBJECT-TYPE
   SYNTAX        Integer32
   MAX-ACCESS    read-create
   STATUS        current
   DESCRIPTION
       "Largest Reservable Flow (KBPS)"
   ::= { csRsvpIfEntry 2 }

csRsvpIfUdpNbrs    OBJECT-TYPE
   SYNTAX        Gauge32
   MAX-ACCESS    read-only
   STATUS        current
   DESCRIPTION
       "The number of neighbors perceived to be  using only the
        RSVP UDP Encapsulation."
   ::= { csRsvpIfEntry 3 }

csRsvpIfIpNbrs    OBJECT-TYPE
   SYNTAX        Gauge32
   MAX-ACCESS    read-only
   STATUS        current
   DESCRIPTION
       "The number of neighbors perceived to be  using only the
        RSVP IP Encapsulation."
   ::= { csRsvpIfEntry 4 }

csRsvpIfNbrs    OBJECT-TYPE
   SYNTAX        Gauge32
   MAX-ACCESS    read-only
   STATUS        current
   DESCRIPTION
       "The number of neighbors  currently  perceived; this 
        will  exceed rsvpIfIpNbrs + rsvpIfUdpNbrs by the
        number of neighbors using both  encapsulations."
   ::= { csRsvpIfEntry 5 }

csRsvpIfEnabled    OBJECT-TYPE
   SYNTAX        TruthValue
   MAX-ACCESS    read-create
   STATUS        current
   DESCRIPTION
       "If TRUE, RSVP is enabled  on  this  Interface.
        If  FALSE,  RSVP  is not enabled on this interface."
   ::= { csRsvpIfEntry 6 }

csRsvpIfUdpRequired    OBJECT-TYPE
   SYNTAX        TruthValue
   MAX-ACCESS    read-create
   STATUS        current
   DESCRIPTION
       "If TRUE, manual configuration forces  the  use
        of  UDP  encapsulation  on  the  interface.  If
        FALSE, UDP encapsulation is only used if rsvpIfUdpNbrs
        is not zero."
   ::= { csRsvpIfEntry 7 }

csRsvpIfRefreshBlockadeMultiple    OBJECT-TYPE
   SYNTAX        INTEGER (1..65535)
   MAX-ACCESS    read-create
   STATUS        current
   DESCRIPTION
       "The value of the RSVP value 'Kb', Which is the
        minimum   number   of  refresh  intervals  that
        blockade state will last once entered."
   DEFVAL        { 4 }
   ::= { csRsvpIfEntry 8 }

csRsvpIfRefreshMultiple    OBJECT-TYPE
   SYNTAX        INTEGER (1..65535)
   MAX-ACCESS    read-create
   STATUS        current
   DESCRIPTION
       "The value of the RSVP value 'K', which is  the
        number  of  refresh intervals which must elapse
        (minimum) before a PATH or RESV  message  which
        is not being refreshed will be aged out."
   DEFVAL        { 3 }
   ::= { csRsvpIfEntry 9 }

csRsvpIfTTL    OBJECT-TYPE
   SYNTAX        INTEGER (0..255)
   MAX-ACCESS    read-create
   STATUS        current
   DESCRIPTION
       "The value of SEND_TTL used on  this  interface
        for  messages  this node originates.  If set to
        zero, the node determines  the  TTL  via  other
        means."
   DEFVAL        { 0 } -- which is to say, no override
   ::= { csRsvpIfEntry 10 }

csRsvpIfRefreshInterval    OBJECT-TYPE
   SYNTAX        TimeInterval
   UNITS         "milliseconds"
   MAX-ACCESS    read-create
   STATUS        current
   DESCRIPTION
       "The value of the RSVP value 'R', which is  the
        minimum period between refresh transmissions of
        a given PATH or RESV message on an interface."
   DEFVAL        { 3000 }  -- 30 Seconds
   ::= { csRsvpIfEntry 11 }

csRsvpIfRouteDelay    OBJECT-TYPE
   SYNTAX        TimeInterval
   UNITS         "hundredths of a second"
   MAX-ACCESS    read-create
   STATUS        current
   DESCRIPTION
       "The approximate period from the time  a  route
        is  changed to the time a resulting message appears
        on the interface."
   DEFVAL        { 200 }  -- 2 Seconds
   ::= { csRsvpIfEntry 12 }

csRsvpIfStatus    OBJECT-TYPE
   SYNTAX        RowStatus
   MAX-ACCESS    read-create
   STATUS        current
   DESCRIPTION
       "'active' on interfaces that are configured for RSVP.
        Corresponding row in csRsvpNbrTable must be configured and
        activated before the row in this table can be activated."
   ::= { csRsvpIfEntry 13 }

csRsvpIfPktsIn    OBJECT-TYPE
   SYNTAX        Counter32
   MAX-ACCESS    read-only
   STATUS        current
   DESCRIPTION
       "Number of RSVP Packets received in this interface."
   ::= { csRsvpIfEntry 14 }

csRsvpIfPathIn    OBJECT-TYPE
   SYNTAX        Counter32
   MAX-ACCESS    read-only
   STATUS        current
   DESCRIPTION
       "Number of PATH messages received on this interface."
   ::= { csRsvpIfEntry 15 }

csRsvpIfResvIn    OBJECT-TYPE
   SYNTAX        Counter32
   MAX-ACCESS    read-only
   STATUS        current
   DESCRIPTION
       "Number of RESV messages received on this interface."
   ::= { csRsvpIfEntry 16 }

csRsvpIfPathTearIn    OBJECT-TYPE
   SYNTAX        Counter32
   MAX-ACCESS    read-only
   STATUS        current
   DESCRIPTION
       "Number of Path Tear  messages received on this interface."
   ::= { csRsvpIfEntry 17 }

csRsvpIfPathErrIn    OBJECT-TYPE
   SYNTAX        Counter32
   MAX-ACCESS    read-only
   STATUS        current
   DESCRIPTION
       "Number of Path Error messages received on this interface."
   ::= { csRsvpIfEntry 18 }

csRsvpIfResvTearIn    OBJECT-TYPE
   SYNTAX        Counter32
   MAX-ACCESS    read-only
   STATUS        current
   DESCRIPTION
       "Number of Resv Tear  messages received on this interface."
   ::= { csRsvpIfEntry 19 }

csRsvpIfResvErrIn    OBJECT-TYPE
   SYNTAX        Counter32
   MAX-ACCESS    read-only
   STATUS        current
   DESCRIPTION
       "Number of RESV Error messages received on this interface."
   ::= { csRsvpIfEntry 20 }

csRsvpIfResvConfIn    OBJECT-TYPE
   SYNTAX        Counter32
   MAX-ACCESS    read-only
   STATUS        current
   DESCRIPTION
       "Number of RESV COnfirmation messages received on this interface."
   ::= { csRsvpIfEntry 21 }

csRsvpIfPathOut    OBJECT-TYPE
   SYNTAX        Counter32
   MAX-ACCESS    read-only
   STATUS        current
   DESCRIPTION
       "Number of Path messages sent out over this interface."
   ::= { csRsvpIfEntry 22 }

csRsvpIfResvOut    OBJECT-TYPE
   SYNTAX        Counter32
   MAX-ACCESS    read-only
   STATUS        current
   DESCRIPTION
       "Number of Resv messages sent out over this interface."
   ::= { csRsvpIfEntry 23 }

csRsvpIfPathTearOut    OBJECT-TYPE
   SYNTAX        Counter32
   MAX-ACCESS    read-only
   STATUS        current
   DESCRIPTION
       "Number of Path Tear messages sent out over this interface."
   ::= { csRsvpIfEntry 24 }

csRsvpIfPathErrOut    OBJECT-TYPE
   SYNTAX        Counter32
   MAX-ACCESS    read-only
   STATUS        current
   DESCRIPTION
       "Number of Path Error messages sent out over this interface."
   ::= { csRsvpIfEntry 25 }

csRsvpIfResvTearOut    OBJECT-TYPE
   SYNTAX        Counter32
   MAX-ACCESS    read-only
   STATUS        current
   DESCRIPTION
       "Number of Resv Tear messages sent out over this interface."
   ::= { csRsvpIfEntry 26 }
 
csRsvpIfResvErrOut    OBJECT-TYPE
   SYNTAX        Counter32
   MAX-ACCESS    read-only
   STATUS        current
   DESCRIPTION
       "Number of Resv Error messages sent out over this interface."
   ::= { csRsvpIfEntry 27 }

csRsvpIfResvConfOut    OBJECT-TYPE
   SYNTAX        Counter32
   MAX-ACCESS    read-only
   STATUS        current
   DESCRIPTION
       "Number of Resv Confirm messages sent out over this interface."
   ::= { csRsvpIfEntry 28 }

csRsvpIfBadPathIn    OBJECT-TYPE
   SYNTAX        Counter32
   MAX-ACCESS    read-only
   STATUS        current
   DESCRIPTION
       "Number of bad Path messages received over this interface."
   ::= { csRsvpIfEntry 29 }

csRsvpIfBadResvIn    OBJECT-TYPE
   SYNTAX        Counter32
   MAX-ACCESS    read-only
   STATUS        current
   DESCRIPTION
       "Number of bad Resv messages received over this interface."
   ::= { csRsvpIfEntry 30 }

csRsvpIfBadPathTearIn    OBJECT-TYPE
   SYNTAX        Counter32
   MAX-ACCESS    read-only
   STATUS        current
   DESCRIPTION
       "Number of bad Path Tear  messages received over this interface."
   ::= { csRsvpIfEntry 31 }

csRsvpIfBadPathErrIn    OBJECT-TYPE
   SYNTAX        Counter32
   MAX-ACCESS    read-only
   STATUS        current
   DESCRIPTION
       "Number of bad Path Error messages received over this interface."
   ::= { csRsvpIfEntry 32 }

csRsvpIfBadResvTearIn    OBJECT-TYPE
   SYNTAX        Counter32
   MAX-ACCESS    read-only
   STATUS        current
   DESCRIPTION
       "Number of bad Resv Tear  messages received over this interface."
   ::= { csRsvpIfEntry 33 }
 
csRsvpIfBadResvErrIn    OBJECT-TYPE
   SYNTAX        Counter32
   MAX-ACCESS    read-only
   STATUS        current
   DESCRIPTION
       "Number of bad Resv Error messages received over this interface."
   ::= { csRsvpIfEntry 34 }

csRsvpIfBadResvConfIn    OBJECT-TYPE
   SYNTAX        Counter32
   MAX-ACCESS    read-only
   STATUS        current
   DESCRIPTION
       "Number of bad Resv Confirm messages received over this interface."
   ::= { csRsvpIfEntry 35 }

csRsvpIfBadOtherIn    OBJECT-TYPE
   SYNTAX        Counter32
   MAX-ACCESS    read-only
   STATUS        current
   DESCRIPTION
       "Number of messages received over this interface which were
        not valid RSVP messages."
   ::= { csRsvpIfEntry 36 }

csRsvpIfUpPsbsCreated    OBJECT-TYPE
   SYNTAX        Counter32
   MAX-ACCESS    read-only
   STATUS        current
   DESCRIPTION
       "Number of Upside PSBs created so far on this interface."
   ::= { csRsvpIfEntry 37 }

csRsvpIfDownPsbsCreated    OBJECT-TYPE
   SYNTAX        Counter32
   MAX-ACCESS    read-only
   STATUS        current
   DESCRIPTION
       "Number of Downside PSBs created so far on this interface."
   ::= { csRsvpIfEntry 38 }

csRsvpIfUpRsbsCreated    OBJECT-TYPE
   SYNTAX        Counter32
   MAX-ACCESS    read-only
   STATUS        current
   DESCRIPTION
       "Number of Upside RSBs created so far on this interface."
   ::= { csRsvpIfEntry 39 }

csRsvpIfDownRsbsCreated    OBJECT-TYPE
   SYNTAX        Counter32
   MAX-ACCESS    read-only
   STATUS        current
   DESCRIPTION
       "Number of Downside RSBs created so far on this interface."
   ::= { csRsvpIfEntry 40 }

csRsvpIfIngressLspsCreated    OBJECT-TYPE
   SYNTAX        Counter32
   MAX-ACCESS    read-only
   STATUS        current
   DESCRIPTION
       "Number of LSPs created on this node which were originated
        from this interface of this node."
   ::= { csRsvpIfEntry 41 }
 
csRsvpIfEgressLspsCreated    OBJECT-TYPE
   SYNTAX        Counter32
   MAX-ACCESS    read-only
   STATUS        current
   DESCRIPTION
       "Number of LSPs created on this node which were terminated
        on this interface of this node."
   ::= { csRsvpIfEntry 42 }


csRsvpIfIpAddress    OBJECT-TYPE
   SYNTAX        IpAddress
   MAX-ACCESS    read-create
   STATUS        current
   DESCRIPTION
       "The IP Address of this RSVP interface."
   ::= { csRsvpIfEntry 43 }

-- End csRsvpIfTable


----------------------------------------------------------------------
--
-- TE-RSVP csRsvpVrConfTable
--
----------------------------------------------------------------------
csRsvpVrConfTable  OBJECT-TYPE
   SYNTAX        SEQUENCE OF CsRsvpVrConfEntry
   MAX-ACCESS    not-accessible
   STATUS        current
   DESCRIPTION
       "This table is used to provide RSVP related functionality at the router level"
   ::= { csTeRsvpObjects 3 }

csRsvpVrConfEntry OBJECT-TYPE
   SYNTAX        CsRsvpVrConfEntry
   MAX-ACCESS    not-accessible
   STATUS        current
   DESCRIPTION
       "This entry is indexed by the VPN and VR ID"
   INDEX         { csOrionGlobalVPNIndex, csOrionVPNVRouterIndex }
      ::= { csRsvpVrConfTable 1 }

CsRsvpVrConfEntry ::= SEQUENCE {
      csRsvpVrAdminStatus          INTEGER,
	  csRsvpVrEventLogLevel        Integer32,
	  csRsvpVrEventLogArea         Integer32,
	  csRsvpVrConfOpCode		   Integer32,
	  csRsvpVrConfRowStatus		   RowStatus
   }

	csRsvpVrAdminStatus    OBJECT-TYPE
	   SYNTAX        INTEGER {
						 enabled  (1),
						 disabled (2)
					}
	   MAX-ACCESS    read-create
	   STATUS        current
	   DESCRIPTION
		   "Indicates the administrator's intent as to  whether
			RSVP   should  be  enabled  or  disabled on this
			router."
	   DEFVAL { disabled }
	   ::= { csRsvpVrConfEntry 1 }

	csRsvpVrEventLogLevel    OBJECT-TYPE
	   SYNTAX        Integer32 
	   MAX-ACCESS    read-create
	   STATUS        current
	   DESCRIPTION
		   "This object is used to set the level of details for
            event logs for RSVP "
	   ::= { csRsvpVrConfEntry 2 }

	csRsvpVrEventLogArea    OBJECT-TYPE
	   SYNTAX        Integer32 
	   MAX-ACCESS    read-create
	   STATUS        current
	   DESCRIPTION
		   "This object is used to set the area of event logs
            for RSVP"
	   ::= { csRsvpVrConfEntry 3 }

	csRsvpVrConfOpCode    OBJECT-TYPE
	   SYNTAX        Integer32 
	   MAX-ACCESS    read-create
	   STATUS        current
	   DESCRIPTION
		   "Used by Rsvp Trace Commands"
	   ::= { csRsvpVrConfEntry 4 }

	csRsvpVrConfRowStatus OBJECT-TYPE
	SYNTAX		RowStatus 
	MAX-ACCESS	read-create
	STATUS		current
	DESCRIPTION
	       "A row status type for the Rsvp Table"
	::= {  csRsvpVrConfEntry 5 }

-- End of csRsvpVrConfTable

----------------------------------------------------------------------
--
-- TE-MPLS LSP Table (derived from draft-kompella-mpls-te-mib-00.txt)
--
----------------------------------------------------------------------
   csMplsLspTable OBJECT-TYPE
       SYNTAX     SEQUENCE OF CsMplsLspEntry
       MAX-ACCESS not-accessible
       STATUS     current
       DESCRIPTION "List of Configured Label Switched Paths."
       ::= { csTeMplsObjects 1 }

   csMplsLspEntry OBJECT-TYPE
       SYNTAX     CsMplsLspEntry
       MAX-ACCESS not-accessible
       STATUS     current
       DESCRIPTION
           "Entry containing information about a particular
            Label Switched Path."
       INDEX { csOrionGlobalVPNIndex, csOrionVPNVRouterIndex,
	       csMplsLspID, csMplsLspName, csMplsLspPreference }
       ::= { csMplsLspTable 1 }

   CsMplsLspEntry ::=
       SEQUENCE {
		   csMplsLspID					Integer32,
           csMplsLspName				DisplayString,
           csMplsLspState				INTEGER,
-- IPSX doesnot support Counter64
-- So the following SYNTAX is changed to Counter32
--         csMplsLspOctets				Counter64,
--         csMplsLspPackets				Counter64,
           csMplsLspOctets				Counter32,
           csMplsLspPackets				Counter32,
           csMplsLspAge					TimeStamp,
           csMplsLspTimeUp				TimeStamp,
           csMplsLspPrimaryTimeUp		TimeStamp,
           csMplsLspTransitions			Counter32,
           csMplsLspLastTransition		TimeStamp,
           csMplsLspPathChanges			Counter32,
           csMplsLspLastPathChange		TimeStamp,
           csMplsLspConfiguredPaths		Integer32,
           csMplsLspStandbyPaths		Integer32,
           csMplsLspOperationalPaths	Integer32,
           csMplsLspFrom				IpAddress,
           csMplsLspTo					IpAddress,
           csMplsPathName				DisplayString,
           csMplsPathType				INTEGER,
           csMplsPathBandwidth			Integer32,
           csMplsPathCOS				INTEGER (0..7 | 255),
           csMplsPathInclude			Integer32,
           csMplsPathExclude			Integer32,
           csMplsPathSetupPriority		INTEGER (0..7),
           csMplsPathHoldPriority		INTEGER (0..7),
           csMplsPathRecordRoute		INTEGER,
           csMplsPathDynamic			INTEGER,
		   csMplsPathIdentifier			Integer32,
		   csMplsPathBgpAutoRouteAnnounce  INTEGER,
		   csMplsPathMetricMode		    INTEGER,
		   csMplsPathMetricValue        Integer32,
		   csMplsPathAffinity			Integer32,
		   csMplsPathAffinityMask		Integer32,
		   csMplsLspPreference			Integer32,
		   csMplsLspRowStatus			RowStatus,
		   csMplsPathIsisAutoRouteAnnounce  INTEGER,
		   csMplsPathOspfAutoRouteAnnounce  INTEGER,
		   csMplsVrPathRecordRoute    OCTET STRING (SIZE (0..1024))
       }

   csMplsLspID OBJECT-TYPE
	SYNTAX Integer32 (1..65535)
	MAX-ACCESS  not-accessible
	STATUS  current
	DESCRIPTION
		"This object identifies a Label Switched Path."
	::= { csMplsLspEntry 1 }

   csMplsLspName OBJECT-TYPE
       SYNTAX     DisplayString (SIZE (0..32))
       MAX-ACCESS not-accessible
       STATUS     current
       DESCRIPTION "Name of the Label Switched Path."
       ::= { csMplsLspEntry 2 }

   csMplsLspState OBJECT-TYPE
       SYNTAX     INTEGER {
                  unknown(1),
                  up(2),
                  down(3)
       }
       MAX-ACCESS read-create
       STATUS     current
       DESCRIPTION "The operational state of the LSP."
	DEFVAL  { down }
       ::= { csMplsLspEntry 3 }

-- IPSX doesnot support Counter64
-- So the following SYNTAX is changed to Counter32

   csMplsLspOctets OBJECT-TYPE
--     SYNTAX     Counter64
       SYNTAX     Counter32
       MAX-ACCESS read-only
       STATUS     current
       DESCRIPTION
           "The number of octets that have been forwarded
            over current LSP active path. The number reported
            is not realtime, may subject to several minutes
            delay.  The delay is controllable by mpls statistics
            gathering interval, which by default is once every
            5 minutes.  If mpls statistics gathering is not
            enabled, this number will not increment."
       ::= { csMplsLspEntry 4 }

-- IPSX doesnot support Counter64
-- So the following SYNTAX is changed to Counter32

   csMplsLspPackets OBJECT-TYPE
--     SYNTAX     Counter64
       SYNTAX     Counter32
       MAX-ACCESS read-only
       STATUS     current
       DESCRIPTION
           "The number of packets that have been forwarded
            over current LSP active path. The number reported
            is not realtime, may subject to several minutes
            delay.  The delay is controllable by mpls statistics
            gathering interval, which by default is once every
            5 minutes.  If mpls statistics gathering is not
            enabled, this number will not increment."
       ::= { csMplsLspEntry 5 }

   csMplsLspAge OBJECT-TYPE
       SYNTAX     TimeStamp
       MAX-ACCESS read-create
       STATUS     current
       DESCRIPTION
           "The age (i.e., time from creation till now) of
            this LSP in 10-millisecond periods."
       ::= { csMplsLspEntry 6 }

   csMplsLspTimeUp OBJECT-TYPE
       SYNTAX     TimeStamp
       MAX-ACCESS read-create
       STATUS     current
       DESCRIPTION
           "The total time in 10-millisecond units that this
            LSP has been operational.  For example, the
            percentage up time can be determined by computing
            (mplsLspTimeUp/mplsLspAge * 100 %)."
       ::= { csMplsLspEntry 7 }

   csMplsLspPrimaryTimeUp OBJECT-TYPE
       SYNTAX     TimeStamp
       MAX-ACCESS read-create
       STATUS     current
       DESCRIPTION
           "The total time in 10-millisecond units that this
            LSP's primary path has been operational.  For
            example, the percentage contribution of the primary
            path to the operational time is given by
            (mplsLspPrimaryTimeUp/mplsLspTimeUp * 100) %."
       ::= { csMplsLspEntry 8 }

   csMplsLspTransitions OBJECT-TYPE
       SYNTAX     Counter32
       MAX-ACCESS read-only
       STATUS     current
       DESCRIPTION
           "The number of state transitions (up -> down and
            down -> up) this LSP has undergone."
       ::= { csMplsLspEntry 9 }

   csMplsLspLastTransition OBJECT-TYPE
       SYNTAX     TimeStamp
       MAX-ACCESS read-create
       STATUS     current
       DESCRIPTION
           "The time in 10-millisecond units since the last
            transition occurred on this LSP."
       ::= { csMplsLspEntry 10 }

   csMplsLspPathChanges OBJECT-TYPE
       SYNTAX     Counter32
       MAX-ACCESS read-only
       STATUS     current
       DESCRIPTION
           "The number of path changes this LSP has had. For
           every path change (path down, path up, path change),
           a corresponding syslog/trap (if enabled) is generated
           for it."
       ::= { csMplsLspEntry 11 }

   csMplsLspLastPathChange OBJECT-TYPE
       SYNTAX     TimeStamp
       MAX-ACCESS read-create
       STATUS     current
       DESCRIPTION
           "The time in 10-millisecond units since the last
            change occurred on this LSP."
       ::= { csMplsLspEntry 12 }

   csMplsLspConfiguredPaths OBJECT-TYPE
       SYNTAX     Integer32
       MAX-ACCESS read-create
       STATUS     current
       DESCRIPTION
           "The number of paths configured for this LSP."
       ::= { csMplsLspEntry 13 }

   csMplsLspStandbyPaths OBJECT-TYPE
       SYNTAX     Integer32
       MAX-ACCESS read-create
       STATUS     current
       DESCRIPTION
           "The number of standby paths configured for
            this LSP."
       ::= { csMplsLspEntry 14 }

   csMplsLspOperationalPaths OBJECT-TYPE
       SYNTAX     Integer32
       MAX-ACCESS read-create 
       STATUS     current
       DESCRIPTION
           "The number of operational paths for this LSP.
            This includes the path currently active, as
            well as operational standby paths."
       ::= { csMplsLspEntry 15 }

   csMplsLspFrom OBJECT-TYPE
       SYNTAX     IpAddress
       MAX-ACCESS read-create
       STATUS     current
       DESCRIPTION
           "Source IP address of this LSP."
       ::= { csMplsLspEntry 16 }

   csMplsLspTo OBJECT-TYPE
       SYNTAX     IpAddress
       MAX-ACCESS read-create
       STATUS     current
       DESCRIPTION
           "Destination IP address of this LSP."
       ::= { csMplsLspEntry 17 }

   csMplsPathName OBJECT-TYPE
       SYNTAX     DisplayString (SIZE(0..16))
       MAX-ACCESS read-create
       STATUS     current
       DESCRIPTION
           "The name of the active path for this LSP, if
            any.  If there is none, the name should be
            empty."
	   DEFVAL  { "" }
       ::= { csMplsLspEntry 18 }

   csMplsPathType OBJECT-TYPE
       SYNTAX     INTEGER {
           other(1),
           primary(2),
           standby(3),
           secondary(4)
       }
       MAX-ACCESS read-create
       STATUS     current
       DESCRIPTION
           "The type of path that is active, i.e., a
            primary path, a standby path, or a generic
            secondary path. This field is meaningless
            if csMplsPathName or csMplsPathIdentifier 
			is not supplied"
       ::= { csMplsLspEntry 19 }


   csMplsPathBandwidth OBJECT-TYPE
       SYNTAX     Integer32
       MAX-ACCESS read-create
       STATUS     current
       DESCRIPTION
           "The configured bandwidth for this LSP, in units
            of thousands of bits per second (Kbps)."
	   DEFVAL  { 0 }
       ::= { csMplsLspEntry 20 }

   csMplsPathCOS OBJECT-TYPE
       SYNTAX     INTEGER (0..7 | 255)
       MAX-ACCESS read-create
       STATUS     current
       DESCRIPTION
           "The configured Class Of Service on this path.  If
            the value is between 0 and 7 inclusive, this value
            will be inserted in the 3 bit COS field in the
            label.  If the value is 255, the value in the COS
            field of the label will depend on other factors.
            This field is meaningless if csMplsPathName or 
			csMplsPathIdentifier is not supplied"
       ::= { csMplsLspEntry 21 }

   csMplsPathInclude OBJECT-TYPE
       SYNTAX     Integer32
       MAX-ACCESS read-create
       STATUS     current
       DESCRIPTION
           "This is a configured set of colors (administrative
            groups) specified as a bit vector (i.e., bit n is 1
            if color n is in the set, where n = 0 is the LSB).
            For each link that this path goes through, the
            link MUST have colors associated with it, and
            the intersection of the link's colors and the
            'include' set MUST be non-null. This field is meaningless
            if csMplsPathName or csMplsPathIdentifier 
			is not supplied"
       ::= { csMplsLspEntry 22 }

   csMplsPathExclude OBJECT-TYPE
       SYNTAX     Integer32
       MAX-ACCESS read-create
       STATUS     current
       DESCRIPTION
           "This is a configured set of colors (administrative
            groups) specified as a bit vector (i.e., bit n is 1
            if color n is in the set, where n = 0 is the LSB).
            For each link that this path goes through, the
            link MUST have colors associated with it, and
            the intersection of the link's colors and the
            'exclude' set MUST be null.This field is meaningless
            if csMplsPathName or csMplsPathIdentifier is not supplied"
       ::= { csMplsLspEntry 23 }

   csMplsPathSetupPriority OBJECT-TYPE
       SYNTAX     INTEGER (0..7)
       MAX-ACCESS read-create
       STATUS     current
       DESCRIPTION
           "The setup priority configured for this path."
	   DEFVAL  { 7 }
       ::= { csMplsLspEntry 24 }

   csMplsPathHoldPriority OBJECT-TYPE
       SYNTAX     INTEGER (0..7)
       MAX-ACCESS read-create
       STATUS     current
       DESCRIPTION
           "The hold priority configured for this path."
	   DEFVAL  { 0 }
       ::= { csMplsLspEntry 25 }

   csMplsPathRecordRoute OBJECT-TYPE
       SYNTAX     INTEGER {
			 off(0),
	 		 on (1)
       }
       MAX-ACCESS read-create
       STATUS     current
       DESCRIPTION
           "This is used to set record route"
	   DEFVAL  { off }
       ::= { csMplsLspEntry 26 }

   csMplsPathDynamic OBJECT-TYPE
       SYNTAX     INTEGER {
			 off(0),
	 		 on (1)
       }
       MAX-ACCESS read-create
       STATUS     current
       DESCRIPTION
           "This is used to configure a dynamic path"
	   DEFVAL  { off }
       ::= { csMplsLspEntry 27 }

	csMplsPathIdentifier OBJECT-TYPE
	SYNTAX	Integer32 (0..65535)
       MAX-ACCESS read-create
       STATUS     current
       DESCRIPTION
           " Path-option explicit-path identifier"
	   DEFVAL  { 0 }
       ::= { csMplsLspEntry 28 }

	csMplsPathBgpAutoRouteAnnounce OBJECT-TYPE
        SYNTAX INTEGER {
			 off(0),
	 		 on (1)
		 }
        MAX-ACCESS read-create
        STATUS current
        DESCRIPTION
            " Used to specify that the IGP should use the tunnel (if the tunnel is up)
			  in its enhanced shortest path first (SPF) calculation."
		DEFVAL  { off }
          ::= { csMplsLspEntry 29 }

	csMplsPathMetricMode OBJECT-TYPE
        SYNTAX INTEGER {
			other(0),
			absolute (1),
			relative (2)
		 }
        MAX-ACCESS read-create
        STATUS current
        DESCRIPTION
            "Used to specify the MPLS traffic engineering tunnel
		     metric type that the IGP enhanced SPF calculation uses.
		     MetricMode can be absolute or relative"
		DEFVAL  { relative }
        ::= { csMplsLspEntry 30 }

	csMplsPathMetricValue OBJECT-TYPE
        SYNTAX Integer32
        MAX-ACCESS read-create
        STATUS current
        DESCRIPTION
            "Absolute metric mode the user can enter a positive value
			 and for relative metric mode the user can enter a positive
			 negative or zero value"
		DEFVAL  { -1 }
          ::= { csMplsLspEntry 31 }


	csMplsPathAffinity OBJECT-TYPE
        SYNTAX Integer32
        MAX-ACCESS read-create
        STATUS current
        DESCRIPTION
            "Used to configure an affinity for an MPLS 
			 traffic engineering tunnel"
		DEFVAL  { 0 }
          ::= { csMplsLspEntry 32 }

	csMplsPathAffinityMask OBJECT-TYPE
        SYNTAX Integer32
        MAX-ACCESS read-create
        STATUS current
        DESCRIPTION
            "Used to configure affinity mask value for an MPLS 
			 traffic engineering tunnel"
		 DEFVAL  { 65535 }
       ::= { csMplsLspEntry 33 }

	csMplsLspPreference OBJECT-TYPE
		SYNTAX Integer32 (1..65535)
		MAX-ACCESS  not-accessible
		STATUS  current
		DESCRIPTION
			"Used to set the Lsp Preference Value"
	   DEFVAL        { 65535 }
		::= { csMplsLspEntry 34 }


	csMplsLspRowStatus OBJECT-TYPE
		SYNTAX RowStatus
		MAX-ACCESS  read-create
		STATUS  current
		DESCRIPTION
			"A row status type for the Lsp Table"
		::= { csMplsLspEntry 35 }

	csMplsPathIsisAutoRouteAnnounce OBJECT-TYPE
        SYNTAX INTEGER {
			 off(0),
	 		 on (1)
		 }
        MAX-ACCESS read-create
        STATUS current
        DESCRIPTION
            " Used to specify that the IGP should use the tunnel (if the tunnel is up)
			  in its enhanced shortest path first (SPF) calculation.Used by Isis."
		DEFVAL  { off }
          ::= { csMplsLspEntry 36 }

	csMplsPathOspfAutoRouteAnnounce OBJECT-TYPE
        SYNTAX INTEGER {
			 off(0),
	 		 on (1)
		 }
        MAX-ACCESS read-create
        STATUS current
        DESCRIPTION
            " Used to specify that the IGP should use the tunnel (if the tunnel is up)
			  in its enhanced shortest path first (SPF) calculation. Used by Ospf."
		DEFVAL  { off }
          ::= { csMplsLspEntry 37 }

	csMplsVrPathRecordRoute OBJECT-TYPE
       SYNTAX     OCTET STRING (SIZE (0..1024))
       MAX-ACCESS read-only
       STATUS     current
       DESCRIPTION
           "This entry records the path recorded by Rsvp for 
		    the tunnel. This field is a displayable string in 
			the format of XXX.XXX.XXX.XXX <semi-colon> repeated 
			for each explicit address."
       ::= { csMplsLspEntry 38 }

--------------------------------------------------------------------------
-- csMplsInterfaceConfTable table specifies information pertaining 
-- to each interface running MPLS
--------------------------------------------------------------------------
 
csMplsInterfaceConfTable  OBJECT-TYPE
   SYNTAX         SEQUENCE OF CsMplsInterfaceConfEntry
   MAX-ACCESS     not-accessible
   STATUS         current
   DESCRIPTION
        "This table has one entry for every interface running Mpls"
   ::= { csTeMplsObjects 2 }
 
csMplsInterfaceConfEntry OBJECT-TYPE
   SYNTAX        CsMplsInterfaceConfEntry
   MAX-ACCESS    not-accessible
   STATUS        current
   DESCRIPTION
       "An entry in this table is created for interface specific
        Label space configuration information."
   INDEX         {  csOrionGlobalVPNIndex, csOrionVPNVRouterIndex,
					csOrionVIfIndex
                 }
      ::= { csMplsInterfaceConfTable 1 }
 
 
CsMplsInterfaceConfEntry ::= SEQUENCE {
      csMplsInterfaceUseInterfaceLabels               TruthValue,
      csMplsInterfaceLabelRange                       INTEGER,
      csMplsInterfaceLabelMinIn                       MplsLabel,
      csMplsInterfaceLabelMaxIn                       MplsLabel,
      csMplsInterfaceLabelMinOut                      MplsLabel,
      csMplsInterfaceLabelMaxOut                      MplsLabel,
      csMplsInterfaceAdminStatus                      INTEGER,
      csMplsInterfaceOperStatus                       INTEGER,
	  csMplsInterfaceAdminWeight					  Integer32,
	  csMplsInterfaceAttribFlags					  Integer32,
	  csMplsInterfaceRowStatus						  RowStatus
   }

csMplsInterfaceUseInterfaceLabels    OBJECT-TYPE
   SYNTAX        TruthValue
   MAX-ACCESS    read-create
   STATUS        current
   DESCRIPTION
       "If TRUE indicates that this interface is configured to
        use interface specific label space. If FALSE then this
        interface is configured to use Platform specific label
        space."
   DEFVAL        { false }  -- Platform specific label space used.
   ::= { csMplsInterfaceConfEntry 1 }

csMplsInterfaceLabelRange    OBJECT-TYPE
   SYNTAX        INTEGER {
                     generic           (0),
                     atm-range         (1),
                     fr-range-dlci10   (2),
                     fr-range-dlci17   (3),
                     fr-range-dlci23   (4)
                 }
   MAX-ACCESS    read-create
   STATUS        current
   DESCRIPTION
       "This object specifies the type of Labels that are being
        use for interface specific label space configuration
        information. Value of this object is significant only if
        csMplsInterfaceUseInterfaceLabels is set to TRUE.
        (If csMplsInterfaceUseInterfaceLabels is FALSE then this
        interface is configured to use Platform specific label
        space.)"
   ::= { csMplsInterfaceConfEntry 2 }

csMplsInterfaceLabelMinIn    OBJECT-TYPE
   SYNTAX        MplsLabel
   MAX-ACCESS    read-create
   STATUS        current
   DESCRIPTION
       "This object specifies the lower limit of the label range
        to be used in incoming packets
        over this interface. This object specifies configuration
        information for interface specific label space and is
        significant only if value of csMplsInterfaceUseInterfaceLabels
        is set to TRUE."
   ::= { csMplsInterfaceConfEntry 3 }

csMplsInterfaceLabelMaxIn    OBJECT-TYPE
   SYNTAX        MplsLabel
   MAX-ACCESS    read-create
   STATUS        current
   DESCRIPTION
       "This object specifies the upper limit of the label range
        to be used in incoming packets
        over this interface. This object specifies configuration
        information for interface specific label space and is
        significant only if value of csMplsInterfaceUseInterfaceLabels
        is set to TRUE."
   ::= { csMplsInterfaceConfEntry 4 }

csMplsInterfaceLabelMinOut    OBJECT-TYPE
   SYNTAX        MplsLabel
   MAX-ACCESS    read-create
   STATUS        current
   DESCRIPTION
       "This object specifies the lower limit of the label range
        to be used in outgoing packets
        over this interface. This object specifies configuration
        information for interface specific label space and is
        significant only if value of csMplsInterfaceUseInterfaceLabels
        is set to TRUE."
   ::= { csMplsInterfaceConfEntry 5 }

csMplsInterfaceLabelMaxOut    OBJECT-TYPE
   SYNTAX        MplsLabel
   MAX-ACCESS    read-create
   STATUS        current
   DESCRIPTION
       "This object specifies the upper limit of the label range
        to be used in outgoing packets
        over this interface. This object specifies configuration
        information for interface specific label space and is
        significant only if value of csMplsInterfaceUseInterfaceLabels
        is set to TRUE."
   ::= { csMplsInterfaceConfEntry 6 }

csMplsInterfaceAdminStatus    OBJECT-TYPE
   SYNTAX        INTEGER {
                     enabled  (1),
                     disabled (2)
                 }
   MAX-ACCESS    read-create
   STATUS        current
   DESCRIPTION
       "Indicates the administrator's intent as to   whether
        MPLS   should  be  enabled  or  disabled   on   this
        interface."
   ::= { csMplsInterfaceConfEntry 7 }

csMplsInterfaceOperStatus    OBJECT-TYPE
   SYNTAX        INTEGER {
                     enabled  (1),
                     disabled (2)
                 }
   MAX-ACCESS    read-only
   STATUS        current
   DESCRIPTION
       "This object specifies the operational state of MPLS 
        on this interface."
   ::= { csMplsInterfaceConfEntry 8 }

csMplsInterfaceAdminWeight OBJECT-TYPE
             SYNTAX Integer32
             MAX-ACCESS read-create
             STATUS current
             DESCRIPTION
                 " Used to override the Interior Gateway Protocol (IGP) 
				    administrative weight (cost) of the link"
	   DEFVAL  { 0 }
          ::= { csMplsInterfaceConfEntry 9 }

csMplsInterfaceAttribFlags OBJECT-TYPE
             SYNTAX Integer32
             MAX-ACCESS read-create
             STATUS current
             DESCRIPTION
                 " Used to set the user-specified attribute flags for the interface"
	   DEFVAL  { 0 }
          ::= { csMplsInterfaceConfEntry 10 }

csMplsInterfaceRowStatus OBJECT-TYPE
             SYNTAX		RowStatus
             MAX-ACCESS read-create
             STATUS		current
             DESCRIPTION
                 "A row status type for the MplsInterface table"
          ::= { csMplsInterfaceConfEntry 11 }
  							  

-- End csMplsInterfaceConfTable

----------------------------------------------------------------------
--
-- TE-MPLS csMplsVrConfTable
--
----------------------------------------------------------------------
csMplsVrConfTable  OBJECT-TYPE
   SYNTAX        SEQUENCE OF CsMplsVrConfEntry
   MAX-ACCESS    not-accessible
   STATUS        current
   DESCRIPTION
       "This table is used to Configure Mpls on a Virtual Router."
   ::= { csTeMplsObjects 3 }

csMplsVrConfEntry OBJECT-TYPE
   SYNTAX        CsMplsVrConfEntry
   MAX-ACCESS    not-accessible
   STATUS        current
   DESCRIPTION
       "This entry is indexed by the VPN and VR ID"
   INDEX         { csOrionGlobalVPNIndex, 
			csOrionVPNVRouterIndex	}
      ::= { csMplsVrConfTable 1 }


CsMplsVrConfEntry ::= SEQUENCE {
      csMplsVrAdminStatus          INTEGER,
	  csMplsVrEventLogLevel        Integer32,
	  csMplsVrEventLogArea         Integer32,
	  csMplsVrConfOpCode		   Integer32,
	  csMplsVrConfRowStatus		   RowStatus
   }

	csMplsVrAdminStatus    OBJECT-TYPE
	   SYNTAX        INTEGER {
						 enabled  (1),
						 disabled (2)
					}
	   MAX-ACCESS    read-create
	   STATUS        current
	   DESCRIPTION
		   "Indicates the administrator's intent as to   whether
			MPLS   should  be  enabled  or  disabled   on   this
			router."
	   DEFVAL { disabled }
	   ::= { csMplsVrConfEntry 1 }


	csMplsVrEventLogLevel    OBJECT-TYPE
	   SYNTAX        Integer32 
	   MAX-ACCESS    read-create
	   STATUS        current
	   DESCRIPTION
		   "This object is used to set the level of details for
            event logs for MPLS"
	   ::= { csMplsVrConfEntry 2 }

	csMplsVrEventLogArea    OBJECT-TYPE
	   SYNTAX        Integer32 
	   MAX-ACCESS    read-create
	   STATUS        current
	   DESCRIPTION
		   "This object is used to set the area of event logs
            for MPLS"
	   ::= { csMplsVrConfEntry 3 }

	csMplsVrConfOpCode    OBJECT-TYPE
	   SYNTAX        Integer32 
	   MAX-ACCESS    read-create
	   STATUS        current
	   DESCRIPTION
		   "Used for Mpls Trace Commands only"
	   ::= { csMplsVrConfEntry 4 }


	csMplsVrConfRowStatus    OBJECT-TYPE
	   SYNTAX        RowStatus 
	   MAX-ACCESS    read-create
	   STATUS        current
	   DESCRIPTION
		   "The existence state of this table. This object follows
                 the Row Status behaviour"
	   ::= { csMplsVrConfEntry 5 }

-- End of csMplsVrConfTable


----------------------------------------------------------------------
--
-- TE-MPLS csMplsExtensionsTable
--
----------------------------------------------------------------------
csMplsExtensionsTable  OBJECT-TYPE
   SYNTAX        SEQUENCE OF CsMplsExtensionsEntry
   MAX-ACCESS    not-accessible
   STATUS        current
   DESCRIPTION
       "This table is used to support Mpls Extensions"
   ::= { csTeMplsObjects 4 }

csMplsExtensionsEntry OBJECT-TYPE
   SYNTAX        CsMplsExtensionsEntry
   MAX-ACCESS    not-accessible
   STATUS        current
   DESCRIPTION
       "This entry is indexed by the VPN and VrID"
   INDEX         { csOrionGlobalVPNIndex, 
				   csOrionVPNVRouterIndex
				 }
      ::= { csMplsExtensionsTable 1 }


CsMplsExtensionsEntry ::= SEQUENCE {
      csMplsMetricStyle	  		   INTEGER,
	  csMplsExtensionsRowStatus    RowStatus,
	  csMplsOspfOpaqueAdminStatus  INTEGER
   }

    csMplsMetricStyle OBJECT-TYPE
	   SYNTAX INTEGER {
                wide (1),
                narrow(2),
				transition(3)
				}
            MAX-ACCESS read-create
            STATUS current
            DESCRIPTION
         "This entry is used to define the metric-style.
		   wide => csMplsMetricStyle = 1,
		   narrow => csMplsMetricStyle = 2,
		   transition => csMplsMetricStyle = 3"
	DEFVAL  { narrow }
         ::= { csMplsExtensionsEntry 1 }

  csMplsExtensionsRowStatus OBJECT-TYPE
             SYNTAX RowStatus
             MAX-ACCESS read-create
             STATUS current
             DESCRIPTION
                 "The existence state of this table. This 
				  object follows the Row Status behaviour."
          ::= { csMplsExtensionsEntry 2 }

    csMplsOspfOpaqueAdminStatus OBJECT-TYPE
	   SYNTAX INTEGER {
                enabled(1),
                disabled(2)
                }
            MAX-ACCESS read-create
            STATUS current
            DESCRIPTION
         "This entry is used to indicate if Ospf Opaque is
		  enabled or disabled on a router."
	DEFVAL  { disabled }
         ::= { csMplsExtensionsEntry 3 }

-- End of csMplsExtensionsTable

----------------------------------------------------------------------
--
-- TE-MPLS csMplsVrPathConfTable
--
----------------------------------------------------------------------
csMplsVrPathConfTable  OBJECT-TYPE
   SYNTAX        SEQUENCE OF CsMplsVrPathConfEntry
   MAX-ACCESS    not-accessible
   STATUS        current
   DESCRIPTION
       "This table is used to configure Explicitly Routed Path"
   ::= { csTeMplsObjects 5 }

csMplsVrPathConfEntry OBJECT-TYPE
   SYNTAX        CsMplsVrPathConfEntry
   MAX-ACCESS    not-accessible
   STATUS        current
   DESCRIPTION
       "This entry is indexed by the VPN and VR ID"
   INDEX         { csOrionGlobalVPNIndex, csOrionVPNVRouterIndex, 
			       csMplsVrPathName	}
      ::= { csMplsVrPathConfTable 1 }


CsMplsVrPathConfEntry ::= SEQUENCE {
      csMplsVrPathName		       DisplayString,
      csMplsVrPathExplicitRoute    OCTET STRING (SIZE (0..1024)),
	  csMplsVrPathIdentifier	   Integer32, 
	  csMplsVrPathConfRowStatus	   RowStatus
   }

	csMplsVrPathName OBJECT-TYPE
       SYNTAX     DisplayString (SIZE(0..16))
       MAX-ACCESS not-accessible
       STATUS     current
       DESCRIPTION
           "Explicit-path Name"
       ::= { csMplsVrPathConfEntry 1 }

	csMplsVrPathExplicitRoute OBJECT-TYPE
       SYNTAX     OCTET STRING (SIZE (0..1024))
       MAX-ACCESS read-create
       STATUS     current
       DESCRIPTION
           "The explicit route used to set up this LSP.
            This may either be the route configured by
            the user, or a route automatically computed
            to satisfy constraints set by the user.
            This field is a displayable string in the
            format of XXX.XXX.XXX.XXX <space> S/L <newline>
            repeated for each explicit address. The S/L character
            stands for Strict/Loose route.
            This field is meaningless if csMplsVrPathIdentifier 
			or csMplsVrPathName is not supplied"
       ::= { csMplsVrPathConfEntry 2 }

	csMplsVrPathIdentifier OBJECT-TYPE
		SYNTAX	Integer32 (1..65535)
		   MAX-ACCESS read-create
		   STATUS     current
		   DESCRIPTION
			   "Explicit-path Identifier"
		   ::= { csMplsVrPathConfEntry 3 }

	csMplsVrPathConfRowStatus    OBJECT-TYPE
	   SYNTAX        RowStatus 
	   MAX-ACCESS    read-create
	   STATUS        current
	   DESCRIPTION
		   "The existence state of this table. This object follows
                 the Row Status behaviour"
	   ::= { csMplsVrPathConfEntry 4 }

-- End of csMplsVrPathConfTable

----------------------------------------------------------------------
--
-- TE-MPLS csMplsIsisExtensionsTable
--
----------------------------------------------------------------------
csMplsIsisExtensionsTable  OBJECT-TYPE
   SYNTAX        SEQUENCE OF CsMplsIsisExtensionsEntry
   MAX-ACCESS    not-accessible
   STATUS        current
   DESCRIPTION
       "This table is used to support ISIS extensions to MPLS"
   ::= { csTeMplsObjects 6 }

csMplsIsisExtensionsEntry OBJECT-TYPE
   SYNTAX        CsMplsIsisExtensionsEntry
   MAX-ACCESS    not-accessible
   STATUS        current
   DESCRIPTION
       "This entry is indexed by the VPN and VrID"
   INDEX         { csOrionGlobalVPNIndex, csOrionVPNVRouterIndex, 
				   csMplsTrafficEnggLevel }
      ::= { csMplsIsisExtensionsTable 1 }


CsMplsIsisExtensionsEntry ::= SEQUENCE {
      csMplsTrafficEnggLevel	   INTEGER,
	  csMplsTrafficEnggAdminStatus INTEGER,
	  csMplsIsisExtensionsRowStatus    RowStatus
   }

    csMplsTrafficEnggLevel OBJECT-TYPE
	   SYNTAX INTEGER {
                level-1(1),
                level-2(2)
                }
            MAX-ACCESS not-accessible
            STATUS current
            DESCRIPTION
         "This entry is used to define the level
		   on which MPLS traffic-eng will be used.
		   Level-1 only => csMplsExtLevel = 1,
		   Level-2 only => csMplsExtLevel = 2"
	DEFVAL  { level-1 }
         ::= { csMplsIsisExtensionsEntry 1 }

    csMplsTrafficEnggAdminStatus OBJECT-TYPE
	   SYNTAX INTEGER {
                enabled(1),
                disabled(2)
                }
            MAX-ACCESS read-create
            STATUS current
            DESCRIPTION
         "This entry is used to indicate if mpls traffic-eng
		  is enabled or disabled on a level. This entry is 
		  used in conjunction with csMplsTrafficEnggLevel."
	DEFVAL  { disabled }
         ::= { csMplsIsisExtensionsEntry 2 }

  csMplsIsisExtensionsRowStatus OBJECT-TYPE
             SYNTAX RowStatus
             MAX-ACCESS read-create
             STATUS current
             DESCRIPTION
                 "The existence state of this table. This 
				  object follows the Row Status behaviour."
          ::= { csMplsIsisExtensionsEntry 3 }


-- End of csMplsIsisExtensionsTable


----------------------------------------------------------------------
--
-- TE-MPLS csMplsOspfExtensionsTable
--
----------------------------------------------------------------------
csMplsOspfExtensionsTable  OBJECT-TYPE
   SYNTAX        SEQUENCE OF CsMplsOspfExtensionsEntry
   MAX-ACCESS    not-accessible
   STATUS        current
   DESCRIPTION
       "This table is used to support Ospf Extensions for Mpls"
   ::= { csTeMplsObjects 7 }

csMplsOspfExtensionsEntry OBJECT-TYPE
   SYNTAX        CsMplsOspfExtensionsEntry
   MAX-ACCESS    not-accessible
   STATUS        current
   DESCRIPTION
       "This entry is indexed by the VPN and VrID"
   INDEX         { csOrionGlobalVPNIndex, csOrionVPNVRouterIndex, 
				   csMplsOspfAreaId	 }
      ::= { csMplsOspfExtensionsTable 1 }


CsMplsOspfExtensionsEntry ::= SEQUENCE {
      csMplsOspfAreaId					AreaID,
	  csMplsOspfAreaAdminStatus			INTEGER,
	  csMplsOspfExtensionsRowStatus		RowStatus
   }

  csMplsOspfAreaId OBJECT-TYPE
	   SYNTAX AreaID 
            MAX-ACCESS not-accessible
            STATUS current
            DESCRIPTION
         "A router running MPLS is configured to flood 
		  traffic-engineering for OSPF area csMplsOspfAreaId"
         ::= { csMplsOspfExtensionsEntry 1 }

  csMplsOspfAreaAdminStatus OBJECT-TYPE
	   SYNTAX INTEGER {
                enabled(1),
                disabled(2)
                }
            MAX-ACCESS read-create
            STATUS current
            DESCRIPTION
         "This entry is used to indicate if mpls is enabled 
		  or disabled on area. This entry is used in 
		  conjunction with csMplsOspfAreaId."
	DEFVAL  { disabled }
         ::= { csMplsOspfExtensionsEntry 2 }

  csMplsOspfExtensionsRowStatus OBJECT-TYPE
             SYNTAX RowStatus
             MAX-ACCESS read-create
             STATUS current
             DESCRIPTION
                 "The existence state of this table. This 
				  object follows the Row Status behaviour."
          ::= { csMplsOspfExtensionsEntry 3 }

-- End of csMplsOspfExtensionsTable

------------------------------------------------------------------------------
--
--	       This set of objects are used only in the varbinds of Orion Traps
--
------------------------------------------------------------------------------


    csOrionChangeTableOID OBJECT-TYPE
 	SYNTAX 	OBJECT IDENTIFIER
 	MAX-ACCESS  read-only
	STATUS	current
	DESCRIPTION
		"Object identifier of the Table, which was changed. "
	::= { csOrionVPNNotifyInfo 1 }

    csOrionChangeSource OBJECT-TYPE
	SYNTAX	INTEGER {
		cli(1),
		httpd (2),
		snmp(3)
	}
	MAX-ACCESS  read-only
	STATUS	current
	DESCRIPTION
		"The source of the configuration change (illegal)."
	::= { csOrionVPNNotifyInfo 2 }

    csOrionChangeSourceUserName OBJECT-TYPE
	SYNTAX	DisplayString 
	MAX-ACCESS  read-only
	STATUS	current
	DESCRIPTION
		"A textual string containing information about the
		user name of the source configuration change."
	::= { csOrionVPNNotifyInfo 3 }

    csOrionLogLinkSlotIndex OBJECT-TYPE
	SYNTAX  Integer32
	MAX-ACCESS  read-only
	STATUS  current
	DESCRIPTION
	    "For Logical Link up/down traps, this identifies the slot
	    index of the Logical Link."
	::= { csOrionVPNNotifyInfo 4 }

    csOrionLogLinkPortIndex OBJECT-TYPE
	SYNTAX  Integer32
	MAX-ACCESS  read-only
	STATUS  current
	DESCRIPTION
	    "For Logical Link up/down traps, this identifies the port
	    index (relative to the slot index) of the Logical Link."
	::= { csOrionVPNNotifyInfo 5 }

    csOrionLogLinkChannelIndex OBJECT-TYPE
	SYNTAX  Integer32
	MAX-ACCESS  read-only
	STATUS  current
	DESCRIPTION
	    "For Logical Link up/down traps, this identifies the channel
	    index (relative to the slot/port index) of the Logical Link.
	    If there is no channel, this object has the value -1."
	::= { csOrionVPNNotifyInfo 6 }


    csOrionLogLinkSubIfIndex OBJECT-TYPE
	SYNTAX  Integer32
	MAX-ACCESS  read-only
	STATUS  current
	DESCRIPTION
	    "For Logical Link up/down traps, this identifies the sub interface
	    index (relative to the slot/port[:chan] index) of the Logical Link.
	    If there is no sub interface, this object has the value -1."
	::= { csOrionVPNNotifyInfo 7 }

    csOrionNumConfigChanges OBJECT-TYPE
	SYNTAX	Integer32 (1..15)
	MAX-ACCESS  read-only
	STATUS	current
	DESCRIPTION
		"Number of changed objects for which the csOrionConfigChange Trap
		PDU generated. This identifies the number of VarBinds follows this
		object in the csOrionConfigChange Trap PDU."
	::= { csOrionVPNNotifyInfo 8 }

    csOrionConfigChangeType OBJECT-TYPE
	SYNTAX	INTEGER {
				delete(1),
				addModify(2)
				}
	MAX-ACCESS  read-only
	STATUS	current
	DESCRIPTION
		"For ConfigChange Traps, this identifies the type of change that was
		made on a table. For scalar objects, this always has the value 1."
	::= { csOrionVPNNotifyInfo 9 }

	csOrionPortIndex OBJECT-TYPE
	SYNTAX  Integer32
	MAX-ACCESS  read-only
	STATUS  current
	DESCRIPTION
	    "For port level alarms related  traps, this identifies the port
	    index (relative to the slot index) of the alarm origination."
	::= { csOrionVPNNotifyInfo 10 }

	csOrionRestoreBladeStatus OBJECT-TYPE
	SYNTAX	INTEGER {
				fail(1),
				success(2),
				coldStart(3)
				}
	MAX-ACCESS  read-only
	STATUS  current
	DESCRIPTION
	    "Blade Restoration status. Fail if blade is not restored successfully.
		 Success if blade restoration is successfull. Cold-start if blade 
		 reboots. Note that cold-start will not have restored data 
		 presented in the trap packet"
	::= { csOrionVPNNotifyInfo 11 }

	csOrionRestoreSlotIndex OBJECT-TYPE
	SYNTAX  Integer32
	MAX-ACCESS  read-only
	STATUS  current
	DESCRIPTION
	    "Slot number of the affected blade."
	::= { csOrionVPNNotifyInfo 12 }

	csOrionRestoreNumVRs OBJECT-TYPE
	SYNTAX	Integer32
	MAX-ACCESS  read-only
	STATUS	current
	DESCRIPTION
		"Number of VRs affected by this blade restoration trap.
		 This corresponds the number of VPN/VRs that follows."
	::= { csOrionVPNNotifyInfo 13 }

	csOrionAlarmType OBJECT-TYPE
	SYNTAX  INTEGER {
				farEndReceiveFailure(0),
				lossOfSignal(1),
				lossOfFrame(2),
				lossOfClock(3),
				alarmIndicationSignal(4),
				portIdleAlarm(5)
				}
	MAX-ACCESS  read-only
	STATUS  current
	DESCRIPTION
	    "For port level alarms related  DS3 traps, this identifies the alarm
		which is cleared now."
	::= { csOrionVPNNotifyInfo 14 }

	csOrionOc3AlarmType OBJECT-TYPE
	SYNTAX  INTEGER {
				lossOfClock(1),
				farEndProtectLineFail(2),
				nearEndProtectLineFail(3),
				protectSwtichByteFail(4),
				channelMismatchFail(5),	
				apsModeMismatch(6),
				remoteDefectIndicatorLine(7),
				noId(8),
				lossOfSignal(9),
				lossOfFrame(10),
				alarmIndicatSignalLine(11),
				alarmIndicatSignalPath(12),
				lossOfPointer(13),
				signalLabelMismatch(14),
				j1PTMismatch(15),	
				lossOfCellDeliniation(16),
				remoteDefectIndicatorPath(17),
				numOfAlarmCountDummy(18)
				}
	MAX-ACCESS  read-only
	STATUS  current
	DESCRIPTION
	    "For port level alarms related  OC3 traps, this identifies the type of
		 alarm being sent out."
	::= { csOrionVPNNotifyInfo 15 }

	csOrionAlarmAffectType OBJECT-TYPE
	SYNTAX  INTEGER {
			 	notServiceAffect(1),
				serviceAffect(2)	
				}
	MAX-ACCESS  read-only
	STATUS  current
	DESCRIPTION
	    " Indicates that it is a not service affecting alarm or a service
		  affecting alarm. "
	::= { csOrionVPNNotifyInfo 16 }

	csOrionAlarmSeverityType OBJECT-TYPE
	SYNTAX  INTEGER {
			 	minor(1),
				major(2),
				critical(3)	
				}
	MAX-ACCESS  read-only
	STATUS  current
	DESCRIPTION
	    " Indicates the severity of this alarm." 
	::= { csOrionVPNNotifyInfo 17 }


--  VPN Server Variables

--
--	These mib objects are used to configure the general list
--	of RADIUS and DNS servers used by each VPN.
--
--

    csRadiusServer	OBJECT IDENTIFIER ::= { csOrionVPNServerInfo 1 }
    csDnsServer		OBJECT IDENTIFIER ::= { csOrionVPNServerInfo 2 }

------------------------------------------------------------------------------
--
-- 		The Blades Group Info 
--
------------------------------------------------------------------------------


    csOrionBladeTable OBJECT-TYPE
	SYNTAX	SEQUENCE OF CsOrionBladeEntry
	MAX-ACCESS  not-accessible
	STATUS	current
	DESCRIPTION
		"A list of Blades which belongs to Orion box."
	::= { csOrionBladeInfo 1 }

    csOrionBladeEntry OBJECT-TYPE
	SYNTAX 	 CsOrionBladeEntry
	MAX-ACCESS  not-accessible
	STATUS	current
	DESCRIPTION
		"An entry containing management information applicable
		to a particular Blade."
	INDEX   { csOrionBladeSlotLocation }
	::= { csOrionBladeTable 1 }

    CsOrionBladeEntry ::=
	SEQUENCE {
 	csOrionBladeSlotLocation   
		Integer32,
	csOrionBladeDescr     
		DisplayString,
 	csOrionBladeType	
		INTEGER,
 	csOrionBladeState	
 		INTEGER,
	csOrionBladeEnginesNumb 
		Integer32,
	csOrionBladePortNumb 
		Integer32,
	csOrionBladeSerialNumb 	
		DisplayString,
	csOrionBladeHwVer 		
		DisplayString,
	csOrionBladeSwVer 		
		DisplayString,
	csOrionBladeReset
		INTEGER,
	csOrionBladeConfigAttributes
		OCTET STRING,
	csOrionBladeOperAttributes
		OCTET STRING,
	csOrionBladeModelNumb
		DisplayString,
	csOrionBladeCLEICode
		DisplayString,
	csOrionBladeFPGAVersion
		DisplayString,
	csOrionBladePort1MacAddr
		MacAddress,
	csOrionBladePort2MacAddr
		MacAddress,
	csOrionBladePort3MacAddr
		MacAddress,
	csOrionBladePort4MacAddr
		MacAddress,
	csOrionBladeIPSXLoaderProduct
		DisplayString,
	csOrionBladeIPSXLoaderVersion
		DisplayString,
	csOrionBladeIPSXLoaderDate
		DisplayString,
	csOrionBladeIPSXLoaderTime
		DisplayString,
	csOrionBladeTemperatureSensor1
		DisplayString,
	csOrionBladeTemperatureSensor2
		DisplayString,
	csOrionBladeTemperatureSensor3
		DisplayString,
	csOrionBladeTemperatureSensor4
		DisplayString,
	csOrionBladeShutdown
		INTEGER
	}

    csOrionBladeSlotLocation OBJECT-TYPE
	SYNTAX	Integer32 (1..26)
	MAX-ACCESS  not-accessible
	STATUS	current
	DESCRIPTION
		"Slot Location of the Blade in the Orion box."
	::= { csOrionBladeEntry 1 }

    csOrionBladeDescr OBJECT-TYPE
	SYNTAX	DisplayString (SIZE (0..255))
	MAX-ACCESS  read-only
	STATUS	current
	DESCRIPTION
		"A textual string containing information about the
		blade.  This string should include the name of the
		manufacturer and the product name."
	::= { csOrionBladeEntry 2 }

    csOrionBladeType OBJECT-TYPE
	SYNTAX INTEGER{
		process				(1),
		control				(2),
		ethernet			(3),
		ds3Unchannelized	(4),
		ds3channelized		(5),
		oc3Atm				(6),
		oc3Pos				(7),
		e3Unchannelized     (8),
        e3channelized       (9)
	}
	MAX-ACCESS  read-only
	STATUS	current
	DESCRIPTION
		"The type of blade inserted in this slot."
	::= { csOrionBladeEntry 3 }

    csOrionBladeState OBJECT-TYPE
	SYNTAX INTEGER{
		notPresent			(1),    -- there is no blade
		inactive			(2),	-- loader sw initializing or failed to initialize
		active				(3),	-- loader sw is running
		softwareLoading		(4),	-- software loading is in progress
		operational			(5),	-- software initialization is complete
		nonOperational		(6),	-- software initialization failed
		failedWithBackup	(7),	-- failed with backup active
		failedWithOutBackup	(8),	-- failed with no backup
		backup				(9),	-- working as a backup of a blade that failed
		standby				(10),	-- waiting to be kicked of incase one blade fials
		reboot				(11),	-- rebooting
		disabled			(12),	-- blade disabled
		master				(13)    -- master state
	}
	MAX-ACCESS  read-only
	STATUS	current
	DESCRIPTION
		"The current state of this blade."
	::= { csOrionBladeEntry 4 }

--    csOrionBladeConfigState: this object has been removed

    csOrionBladeEnginesNumb OBJECT-TYPE
	SYNTAX 	Integer32
 	MAX-ACCESS read-only
	STATUS     obsolete
	DESCRIPTION
		"The number of engines on the blade.

		NOTE: This object is not used."
	::= { csOrionBladeEntry 5 }

    csOrionBladePortNumb OBJECT-TYPE
	SYNTAX 	Integer32 (0..200)
	MAX-ACCESS  read-only
	STATUS	current
	DESCRIPTION
		"The number of ports on this blade (note, process
		blades have no ports)."
	::= { csOrionBladeEntry 6 }

    csOrionBladeSerialNumb OBJECT-TYPE
	SYNTAX	DisplayString
	MAX-ACCESS  read-only
	STATUS	obsolete
	DESCRIPTION
		"The serial number of the blade. This is a 
		series of alphanumeric characters which uniquely 
		identifies this blade.

		NOTE: This object is not used."
	::= { csOrionBladeEntry 7 }

    csOrionBladeHwVer OBJECT-TYPE
	SYNTAX	DisplayString 
	MAX-ACCESS  read-only
	STATUS	obsolete
	DESCRIPTION
		"A textual string containing information about the
		hardware revision version.

		NOTE: This object is not used."
	::= { csOrionBladeEntry 8 }

    csOrionBladeSwVer OBJECT-TYPE
	SYNTAX	DisplayString 
	MAX-ACCESS  read-only
	STATUS	obsolete
	DESCRIPTION
		"A textual string containing information about the
		software revision version.

		NOTE: This object is not used."
	::= { csOrionBladeEntry 9 }

	csOrionBladeReset OBJECT-TYPE
	SYNTAX 	INTEGER {
		none	(1),
		reset	(2)
	}
	MAX-ACCESS read-write
	STATUS 	current
	DESCRIPTION  "The software reset for this blade. It is an action 
		object such that when set to 'reset' will reset this blade. 
		Setting it to 'none' has no effect, and when it is retrieved 
		the value will always be 'none'. "
	::= { csOrionBladeEntry 10}

	csOrionBladeConfigAttributes OBJECT-TYPE
	SYNTAX 	OCTET STRING (SIZE (0..2000))
	MAX-ACCESS read-only
	STATUS 	deprecated
	DESCRIPTION  "Contains the configured or static parameters of this blade.
		Each parameter is represented by a type-lenth-value data structure.
		A single TLV may contain individual TLVs. The types IDs currently
		supported are :
			1 - Description (string) [sample only]
		more parameters will be added.

		NOTE: This object is deprecated and is replaced by individual
		  objects starting from csOrionBladeModelNumb."
	::= { csOrionBladeEntry 11}

	csOrionBladeOperAttributes OBJECT-TYPE
	SYNTAX 	OCTET STRING (SIZE (0..2000))
	MAX-ACCESS read-only
	STATUS 	deprecated
	DESCRIPTION  "Contains the operational or dynamic parameters of this blade. 
		Each parameter is represented by a type-lenth-value data structure.
		A single TLV may contain individual TLVs. The types IDs currently
		supported are :
			1 - Description (string) [sample only]
		more parameters will be added.

		NOTE: This object is deprecated and is replaced by individual
		  objects starting from csOrionBladeTemperatureSensor1."
	::= { csOrionBladeEntry 12}

    csOrionBladeModelNumb OBJECT-TYPE
	SYNTAX 	DisplayString (SIZE (0..40))
	MAX-ACCESS read-only
	STATUS 	current
	DESCRIPTION
		"A textual string containing information about the
		model number of the blade."
	::= { csOrionBladeEntry 13}
		
    csOrionBladeCLEICode OBJECT-TYPE
	SYNTAX 	DisplayString (SIZE (0..80))
	MAX-ACCESS read-only
	STATUS 	current
	DESCRIPTION
		"A textual string containing information about the
		CLEI of the blade."
	::= { csOrionBladeEntry 14}
		
    csOrionBladeFPGAVersion OBJECT-TYPE
	SYNTAX 	DisplayString (SIZE (0..255))
	MAX-ACCESS read-only
	STATUS 	current
	DESCRIPTION
		"A textual string containing information about the
		FPGA version of the blade."
	::= { csOrionBladeEntry 15}
		
    csOrionBladePort1MacAddr OBJECT-TYPE
	SYNTAX 	MacAddress
	MAX-ACCESS read-only
	STATUS 	current
	DESCRIPTION
		"MAC Address of ethernet port 1 on the blade.
		 Applies only to control or ethernet blade."
	::= { csOrionBladeEntry 16}
		
    csOrionBladePort2MacAddr OBJECT-TYPE
	SYNTAX 	MacAddress
	MAX-ACCESS read-only
	STATUS 	current
	DESCRIPTION
		"MAC Address of ethernet port 2 on the blade.
		 Applies only to control or ethernet blade."
	::= { csOrionBladeEntry 17}
		
    csOrionBladePort3MacAddr OBJECT-TYPE
	SYNTAX 	MacAddress
	MAX-ACCESS read-only
	STATUS 	current
	DESCRIPTION
		"MAC Address of ethernet port 3 on the blade.
		 Applies only to control or ethernet blade."
	::= { csOrionBladeEntry 18}
		
    csOrionBladePort4MacAddr OBJECT-TYPE
	SYNTAX 	MacAddress
	MAX-ACCESS read-only
	STATUS 	current
	DESCRIPTION
		"MAC Address of ethernet port 4 on the blade.
		 Applies only to control or ethernet blade."
	::= { csOrionBladeEntry 19}
		
    csOrionBladeIPSXLoaderProduct OBJECT-TYPE
	SYNTAX 	DisplayString (SIZE (0..255))
	MAX-ACCESS read-only
	STATUS 	current
	DESCRIPTION
		"A textual string containing information about the
		IPSX loader."
	::= { csOrionBladeEntry 20}
		
    csOrionBladeIPSXLoaderVersion OBJECT-TYPE
	SYNTAX 	DisplayString (SIZE (0..80))
	MAX-ACCESS read-only
	STATUS 	current
	DESCRIPTION
		"A textual string containing information about the
		version of the loader."
	::= { csOrionBladeEntry 21}
	
    csOrionBladeIPSXLoaderDate OBJECT-TYPE
	SYNTAX 	DisplayString (SIZE (0..80))
	MAX-ACCESS read-only
	STATUS 	current
	DESCRIPTION
		"A textual string containing information about the
		date of the loader."
	::= { csOrionBladeEntry 22}
	
    csOrionBladeIPSXLoaderTime  OBJECT-TYPE
	SYNTAX 	DisplayString (SIZE (0..80))
	MAX-ACCESS read-only
	STATUS 	current
	DESCRIPTION
		"A textual string containing information about the
		time of the loader."
	::= { csOrionBladeEntry 23}
	
    csOrionBladeTemperatureSensor1 OBJECT-TYPE
	SYNTAX 	DisplayString (SIZE (0..20))
	MAX-ACCESS read-only
	STATUS 	current
	DESCRIPTION
		"A textual string containing information about the
		temperature of sensor 1."
	::= { csOrionBladeEntry 24}
	
    csOrionBladeTemperatureSensor2 OBJECT-TYPE
	SYNTAX 	DisplayString (SIZE (0..20))
	MAX-ACCESS read-only
	STATUS 	current
	DESCRIPTION
		"A textual string containing information about the
		temperature of sensor 2."
	::= { csOrionBladeEntry 25}
	
    csOrionBladeTemperatureSensor3 OBJECT-TYPE
	SYNTAX 	DisplayString (SIZE (0..20))
	MAX-ACCESS read-only
	STATUS 	current
	DESCRIPTION
		"A textual string containing information about the
		temperature of sensor 3."
	::= { csOrionBladeEntry 26}
	
    csOrionBladeTemperatureSensor4 OBJECT-TYPE
	SYNTAX 	DisplayString (SIZE (0..20))
	MAX-ACCESS read-only
	STATUS 	current
	DESCRIPTION
		"A textual string containing information about the
		temperature of sensor 4."
	::= { csOrionBladeEntry 27}

	csOrionBladeShutdown OBJECT-TYPE
	SYNTAX 	INTEGER {
		none	(1),
		shutdown	(2)
	}
	MAX-ACCESS read-write
	STATUS 	current
	DESCRIPTION  "The software shutdown for this blade. It is an action 
		object such that when set to 'shutdown' will stop the file-system on this blade. 
		Setting it to 'none' has no effect, and when it is retrieved 
		the value will always be 'none'. "
	::= { csOrionBladeEntry 28}

------------------------------------------------------------------------------
--
-- 		The Engines Table 
--
------------------------------------------------------------------------------

-- definitions for process engines

    csOrionEngineTable OBJECT-TYPE
	SYNTAX	SEQUENCE OF CsOrionEngineEntry
	MAX-ACCESS  not-accessible
	STATUS	current
	DESCRIPTION
		"A list of Process Engines such as CPU, Search 
		Engine and Encryption Engine which exist in the Orion box."
	::= { csOrionBladeInfo 2 }

    csOrionEngineEntry OBJECT-TYPE
	SYNTAX 	 CsOrionEngineEntry
	MAX-ACCESS  not-accessible
	STATUS	current
	DESCRIPTION
		"An entry containing management information applicable
		to a particular process engine."
	INDEX   { csOrionBladeSlotLocation, csOrionEngineIndex }
	::= { csOrionEngineTable 1 }

    CsOrionEngineEntry ::=
	SEQUENCE {
 	csOrionEngineIndex	
		Integer32,
	csOrionEngineMemorySize	 
		Integer32,
	csOrionEngineMemoryUtil 
		Integer32,
	csOrionEngineType     
		INTEGER,
	csOrionEngineDescr
		DisplayString,
	csOrionEngineUtilization
		Integer32,
	csOrionEngineTemperature
		Integer32,
	csOrionEngineState	
 		INTEGER,
	csOrionEngineConfigAttributes
		OCTET STRING,
	csOrionEngineOperAttributes
		OCTET STRING,
	csOrionEngineLoaderProduct
		DisplayString,
	csOrionEngineLoaderVersion
		DisplayString,
	csOrionEngineLoaderDate
		DisplayString,
	csOrionEngineLoaderTime
		DisplayString,
	csOrionEngineApplicationProduct
		DisplayString,
	csOrionEngineApplicationVersion
		DisplayString,
	csOrionEngineApplicationDate
		DisplayString,
	csOrionEngineApplicationTime
		DisplayString,
	csOrionEngineSerialNumb
		DisplayString,
	csOrionEngineAssemblyNumb
		DisplayString,
	csOrionEngineCpuType
		INTEGER,
	csOrionEngineCpuVersion
		Integer32,
	csOrionEngineDataCacheSize
		Gauge32,
	csOrionEngineInstructionCacheSize
		Gauge32,
	csOrionEngineSecondaryCacheSize
		Gauge32,
	csOrionEngineLevel3CacheSize
		Gauge32,
	csOrionEngineMemoryAllocs
		Gauge32,
	csOrionEngineMemoryAllocFailures
		Gauge32,
	csOrionEngineMemoryFrees
		Gauge32,
	csOrionEngineMemoryBadFrees
		Gauge32,
	csOrionEngineMemoryBytesAllocs
		Gauge32,
	csOrionEngineMemoryBytesFreed
		Gauge32,
	csOrionEngineFreeMemory
		Gauge32,
	csOrionEngineLargestFreeMemory
		Gauge32,
	csOrionEngineFreeMemoryMedium
		Gauge32,
	csOrionEngineFreeMemoryLong
		Gauge32,
	csOrionEngineUtilizationMedium
		Integer32,
	csOrionEngineUtilizationLong
		Integer32
	}

    csOrionEngineIndex OBJECT-TYPE
	SYNTAX	Integer32 (0..65535)
	MAX-ACCESS  not-accessible
	STATUS	current
	DESCRIPTION
		"A unique value for each engine. "
	::= { csOrionEngineEntry 1 }

    csOrionEngineMemorySize OBJECT-TYPE
	SYNTAX 	 Integer32 (1..2147483647)
	MAX-ACCESS  read-only
	STATUS	obsolete
	DESCRIPTION
		"The size of the memory for the specified Engine, in bytes.

		NOTE: This object is not used."
	::= { csOrionEngineEntry 2 }

    csOrionEngineMemoryUtil OBJECT-TYPE
	SYNTAX Integer32 (0..100)
	MAX-ACCESS  read-only
	STATUS	current
	DESCRIPTION
		"The current percentage utilization of the memory for 
		the specified Engine."
	::= { csOrionEngineEntry 3 }

    csOrionEngineType OBJECT-TYPE
 	SYNTAX	INTEGER {
	    mainCpu     (1),
		cpu			(2),
		search		(3),
		encryption	(4)
	}
	MAX-ACCESS  read-only
	STATUS	current
	DESCRIPTION
		"A type of the process engine."
	::= { csOrionEngineEntry 5 }

    csOrionEngineDescr OBJECT-TYPE
	SYNTAX	DisplayString 
	MAX-ACCESS  read-only
	STATUS	obsolete
	DESCRIPTION
		" A textual string containing information about the
		process engine manufacturer and the product name.

		NOTE: This object is not used."
	::= { csOrionEngineEntry 6 }

    csOrionEngineUtilization OBJECT-TYPE
	SYNTAX 	Integer32 (0..100)
	MAX-ACCESS  read-only
	STATUS	current
	DESCRIPTION
		"A % utilization for the specified Engine."
		::= { csOrionEngineEntry 7 }

    csOrionEngineTemperature OBJECT-TYPE
 	SYNTAX Integer32 (-67..257)
	MAX-ACCESS  read-only
	STATUS	obsolete
	DESCRIPTION
		"A temperature (in Fahrenheit or Celsius near 
		the specified Engine.

		NOTE: This object is not used."
	::= { csOrionEngineEntry 8 }

	csOrionEngineState OBJECT-TYPE
	SYNTAX INTEGER{
		notPresent			(1),    -- there is no engine
		inactive			(2),	-- loader sw initializing or failed to initialize
		active				(3),	-- loader sw is running
		softwareLoading		(4),	-- software loading is in progress
		operational			(5),	-- software initialization is complete
		nonOperational		(6),	-- software initialization failed
		failedWithBackup	(7),	-- failed with backup active
		failedWithOutBackup	(8),	-- failed with no backup
		backup				(9),	-- working as a backup of a engine that failed
		standby				(10),	-- waiting to be kicked of incase one engine fails
		reboot				(11)	-- rebooting
	}
	MAX-ACCESS  read-only
	STATUS	current
	DESCRIPTION
		"The current state of this engine."
	::= { csOrionEngineEntry 9 }

	csOrionEngineConfigAttributes OBJECT-TYPE
	SYNTAX 	OCTET STRING (SIZE (0..2000))
	MAX-ACCESS read-only
	STATUS 	deprecated
	DESCRIPTION  "Contains the configured or static parameters of this engine.
		Each parameter is represented by a type-lenth-value data structure.
		A single TLV may contain individual TLVs. The types IDs currently
		supported are :
			1 - Description (string) [sample only]
		more parameters will be added.

		NOTE: This object is deprecated and is replaced by individual
		  objects starting from csOrionEngineLoaderProduct."
	::= { csOrionEngineEntry 10}

	csOrionEngineOperAttributes OBJECT-TYPE
	SYNTAX 	OCTET STRING (SIZE (0..2000))
	MAX-ACCESS read-only
	STATUS 	deprecated
	DESCRIPTION  "Contains the operational or dynamic parameters of this engine. 
		Each parameter is represented by a type-lenth-value data structure.
		A single TLV may contain individual TLVs. The types IDs currently
		supported are :
			1 - Description (string) [sample only]
		more parameters will be added.

		NOTE: This object is deprecated and is replaced by individual
		  objects starting from csOrionEngineMemoryAllocs."
	::= { csOrionEngineEntry 11}

    csOrionEngineLoaderProduct OBJECT-TYPE
	SYNTAX 	DisplayString (SIZE (0..255))
	MAX-ACCESS read-only
	STATUS 	current
	DESCRIPTION
		"A textual string containing information about the
		engine loader."
	::= { csOrionEngineEntry 12}

    csOrionEngineLoaderVersion OBJECT-TYPE
	SYNTAX 	DisplayString (SIZE (0..80))
	MAX-ACCESS read-only
	STATUS 	current
	DESCRIPTION
		"A textual string containing information about the
		version of the loader."
	::= { csOrionEngineEntry 13}

    csOrionEngineLoaderDate OBJECT-TYPE
	SYNTAX 	DisplayString (SIZE (0..80))
	MAX-ACCESS read-only
	STATUS 	current
	DESCRIPTION
		"A textual string containing information about the
		date of the loader."
	::= { csOrionEngineEntry 14}

    csOrionEngineLoaderTime OBJECT-TYPE
	SYNTAX 	DisplayString (SIZE (0..80))
	MAX-ACCESS read-only
	STATUS 	current
	DESCRIPTION
		"A textual string containing information about the
		time of the loader."
	::= { csOrionEngineEntry 15}

    csOrionEngineApplicationProduct OBJECT-TYPE
	SYNTAX 	DisplayString (SIZE (0..255))
	MAX-ACCESS read-only
	STATUS 	current
	DESCRIPTION
		"A textual string containing information about the
		application."
	::= { csOrionEngineEntry 16}

    csOrionEngineApplicationVersion OBJECT-TYPE
	SYNTAX 	DisplayString (SIZE (0..80))
	MAX-ACCESS read-only
	STATUS 	current
	DESCRIPTION
		"A textual string containing information about the
		version of the application."
	::= { csOrionEngineEntry 17}

    csOrionEngineApplicationDate OBJECT-TYPE
	SYNTAX 	DisplayString (SIZE (0..80))
	MAX-ACCESS read-only
	STATUS 	current
	DESCRIPTION
		"A textual string containing information about the
		date of the application."
	::= { csOrionEngineEntry 18}

    csOrionEngineApplicationTime OBJECT-TYPE
	SYNTAX 	DisplayString (SIZE (0..80))
	MAX-ACCESS read-only
	STATUS 	current
	DESCRIPTION
		"A textual string containing information about the
		time of the application."
	::= { csOrionEngineEntry 19}

    csOrionEngineSerialNumb OBJECT-TYPE
	SYNTAX 	DisplayString (SIZE (0..255))
	MAX-ACCESS read-only
	STATUS 	current
	DESCRIPTION
		"The serial number of the engine. This is a 
		series of alphanumeric characters which uniquely 
		identifies the engine on this blade."
	::= { csOrionEngineEntry 20 }

    csOrionEngineAssemblyNumb OBJECT-TYPE
	SYNTAX 	DisplayString (SIZE (0..255))
	MAX-ACCESS read-only
	STATUS 	current
	DESCRIPTION
		"The assembly number of the engine."
	::= { csOrionEngineEntry 21 }

    csOrionEngineCpuType OBJECT-TYPE
	SYNTAX 	INTEGER {
		mips-rm5270 (1),
		mips-rm5271 (2),
		mips-rm7000 (3),
		mips-unknown(255)
	}
	MAX-ACCESS read-only
	STATUS 	current
	DESCRIPTION
		"The type of cpu for the engine."
	::= { csOrionEngineEntry 22 }

    csOrionEngineCpuVersion OBJECT-TYPE
	SYNTAX 	Integer32
	MAX-ACCESS read-only
	STATUS 	current
	DESCRIPTION
		"The CPU version of the engine."
	::= { csOrionEngineEntry 23 }


    csOrionEngineDataCacheSize OBJECT-TYPE
	SYNTAX 	Gauge32
        UNITS   "bytes"
	MAX-ACCESS read-only
	STATUS 	current
	DESCRIPTION
		"Data cache size of the engine."
	::= { csOrionEngineEntry 24 }

    csOrionEngineInstructionCacheSize OBJECT-TYPE
	SYNTAX 	Gauge32
        UNITS   "bytes"
	MAX-ACCESS read-only
	STATUS 	current
	DESCRIPTION
		"Instruction cache size of the engine."
	::= { csOrionEngineEntry 25 }

    csOrionEngineSecondaryCacheSize OBJECT-TYPE
	SYNTAX 	Gauge32
        UNITS   "bytes"
	MAX-ACCESS read-only
	STATUS 	current
	DESCRIPTION
		"Secondary cache size of the engine."
	::= { csOrionEngineEntry 26 }

    csOrionEngineLevel3CacheSize OBJECT-TYPE
	SYNTAX 	Gauge32
        UNITS   "bytes"
	MAX-ACCESS read-only
	STATUS 	current
	DESCRIPTION
		"Level 3 cache size of the engine."
	::= { csOrionEngineEntry 27 }

    csOrionEngineMemoryAllocs OBJECT-TYPE
	SYNTAX 	Gauge32
	MAX-ACCESS read-only
	STATUS 	current
	DESCRIPTION
		"Memory allocated for the engine."
	::= { csOrionEngineEntry 28 }

    csOrionEngineMemoryAllocFailures OBJECT-TYPE
	SYNTAX 	Gauge32
	MAX-ACCESS read-only
	STATUS 	current
	DESCRIPTION
		"Memory allocation failures for the engine."
	::= { csOrionEngineEntry 29 }

    csOrionEngineMemoryFrees OBJECT-TYPE
	SYNTAX 	Gauge32
	MAX-ACCESS read-only
	STATUS 	current
	DESCRIPTION
		"Memory freed for the engine."
	::= { csOrionEngineEntry 30 }

    csOrionEngineMemoryBadFrees OBJECT-TYPE
	SYNTAX 	Gauge32
	MAX-ACCESS read-only
	STATUS 	current
	DESCRIPTION
		"Memory free failures for the engine."
	::= { csOrionEngineEntry 31 }

    csOrionEngineMemoryBytesAllocs OBJECT-TYPE
	SYNTAX 	Gauge32
        UNITS   "bytes"
	MAX-ACCESS read-only
	STATUS 	current
	DESCRIPTION
		"Bytes allocated for the engine."
	::= { csOrionEngineEntry 32 }

    csOrionEngineMemoryBytesFreed OBJECT-TYPE
	SYNTAX 	Gauge32
        UNITS   "bytes"
	MAX-ACCESS read-only
	STATUS 	current
	DESCRIPTION
		"Bytes freed for the engine."
	::= { csOrionEngineEntry 33 }

    csOrionEngineFreeMemory OBJECT-TYPE
	SYNTAX 	Gauge32
        UNITS   "bytes"
	MAX-ACCESS read-only
	STATUS 	current
	DESCRIPTION
		"Free memory for the engine."
	::= { csOrionEngineEntry 34 }

    csOrionEngineLargestFreeMemory OBJECT-TYPE
	SYNTAX 	Gauge32
        UNITS   "bytes"
	MAX-ACCESS read-only
	STATUS 	current
	DESCRIPTION
		"Size of the largest free memory block for 
		 the engine."
	::= { csOrionEngineEntry 35 }

    csOrionEngineFreeMemoryMedium OBJECT-TYPE
	SYNTAX 	Gauge32
        UNITS   "100 kbyte"
	MAX-ACCESS read-only
	STATUS 	current
	DESCRIPTION
		"Free memory, in 100 KByte unit, averaged over
		 the last 30 seconds."
	::= { csOrionEngineEntry 36 }

    csOrionEngineFreeMemoryLong OBJECT-TYPE
	SYNTAX 	Gauge32
        UNITS   "100 kbyte"
	MAX-ACCESS read-only
	STATUS 	current
	DESCRIPTION
		"Free memory, in 100 KByte unit, averaged over
		 the last 10 minutes."
	::= { csOrionEngineEntry 37 }

    csOrionEngineUtilizationMedium OBJECT-TYPE
	SYNTAX 	Integer32 (0..100)
	MAX-ACCESS read-only
	STATUS 	current
	DESCRIPTION
		"CPU utilization averaged over the last 30 seconds."
	::= { csOrionEngineEntry 38 }

    csOrionEngineUtilizationLong OBJECT-TYPE
	SYNTAX 	Integer32 (0..100)
	MAX-ACCESS read-only
	STATUS 	current
	DESCRIPTION
		"CPU utilization averaged over the last 10 minutes."
	::= { csOrionEngineEntry 39 }

--  Following are defined in the TLV attribute list but are not
--  actually supported by IPSX:
--    csOrionEngineCpuClockRate OBJECT-TYPE
--    csOrionEngineOSVersion OBJECT-TYPE



------------------------------------------------------------------------------
--
-- 		Access List Info 
--
------------------------------------------------------------------------------

--
-- Note, this access list is used exclusively by NAT.  Other services
-- will use the more general csOrionGenAclTable.
--

    csOrionAccessListTable OBJECT-TYPE
	SYNTAX	SEQUENCE OF CsOrionAccessListEntry
	MAX-ACCESS  not-accessible
	STATUS	current
	DESCRIPTION
		"A list of Access List Entries."
	::= { csOrionAccessListInfo 1 }

   csOrionAccessListEntry OBJECT-TYPE
	SYNTAX 	 CsOrionAccessListEntry
	MAX-ACCESS  not-accessible
	STATUS	current
	DESCRIPTION
		"An entry containing filtering information used to
		classify packets."
	INDEX   { csOrionGlobalVPNIndex, csOrionVPNVRouterIndex,
		csOrionVIfIndex, csOrionAccessListId }
	::= { csOrionAccessListTable 1 }

    CsOrionAccessListEntry ::=
	SEQUENCE {
	csOrionAccessListId 	
		Integer32,
 	csOrionAccessListStartAddress
		IpAddress,
	csOrionAccessListEndAddress
		IpAddress,
	csOrionAccessListPoolId
		Integer32,
	csOrionAccessListStatus
		RowStatus
	}

    csOrionAccessListId OBJECT-TYPE
	SYNTAX	Integer32  (1..65535)
	MAX-ACCESS  not-accessible
	STATUS	current
	DESCRIPTION
		"An identifier for this Access List Entry."
	::= { csOrionAccessListEntry 1 }

    csOrionAccessListStartAddress OBJECT-TYPE
	SYNTAX	IpAddress 
	MAX-ACCESS  read-create
	STATUS	current
	DESCRIPTION
		""
	::= { csOrionAccessListEntry 2 }

    csOrionAccessListEndAddress OBJECT-TYPE
	SYNTAX	IpAddress 
	MAX-ACCESS  read-create
	STATUS	current
	DESCRIPTION
		""
	::= { csOrionAccessListEntry 3 }

    csOrionAccessListPoolId OBJECT-TYPE
	SYNTAX	Integer32 
	MAX-ACCESS  read-create
	STATUS	current
	DESCRIPTION
		"The NAT Pool that is used when NAT is performed on packets
		matching this access list."
	::= { csOrionAccessListEntry 4 }

    csOrionAccessListStatus OBJECT-TYPE
	SYNTAX	RowStatus 
	MAX-ACCESS  read-create
	STATUS	current
	DESCRIPTION
		"This object is used to create/delete entries in this table."
	::= { csOrionAccessListEntry 5 }

--
-- This is the general access list table for Orion.  Other than NAT, this 
-- table is used by all the services on this Orion.
--

    csOrionGenAclTable OBJECT-TYPE
	SYNTAX	SEQUENCE OF CsOrionGenAclEntry
	MAX-ACCESS  not-accessible
	STATUS	current
	DESCRIPTION
		"A list of Access List Entries. This is the table used
		by all the services (other than NAT) provided by Orion."
	::= { csOrionAccessListInfo 2 }

   csOrionGenAclEntry OBJECT-TYPE
	SYNTAX 	 CsOrionGenAclEntry
	MAX-ACCESS  not-accessible
	STATUS	current
	DESCRIPTION
		"An entry containing filtering information used to
		classify packets."
	INDEX   { csOrionGlobalVPNIndex, csOrionVPNVRouterIndex,
		csOrionGenAclId }
	::= { csOrionGenAclTable 1 }

    CsOrionGenAclEntry ::=
	SEQUENCE {
	csOrionGenAclId 	
		Integer32,
 	csOrionGenAclSrcAddress
		IpAddress,
 	csOrionGenAclSrcMask
		IpAddress,
 	csOrionGenAclDstAddress
		IpAddress,
 	csOrionGenAclDstMask
		IpAddress,
	csOrionGenAclProt
		Integer32,
	csOrionGenAclTos
		Integer32,
	csOrionGenAclStartSrcPort
		Integer32,
	csOrionGenAclEndSrcPort
		Integer32,
	csOrionGenAclStartDstPort
		Integer32,
	csOrionGenAclEndDstPort
		Integer32,
	csOrionGenAclStatus
		RowStatus
	}

    csOrionGenAclId OBJECT-TYPE
	SYNTAX	Integer32 (1..65535)
	MAX-ACCESS  not-accessible
	STATUS	current
	DESCRIPTION
		"An identifier for this Access List Entry."
	::= { csOrionGenAclEntry 1 }

    csOrionGenAclSrcAddress OBJECT-TYPE
	SYNTAX	IpAddress 
	MAX-ACCESS  read-create
	STATUS	current
	DESCRIPTION
		""
	DEFVAL   { '00000000'H }    -- 0.0.0.0
	::= { csOrionGenAclEntry 2 }

    csOrionGenAclSrcMask OBJECT-TYPE
	SYNTAX	IpAddress 
	MAX-ACCESS  read-create
	STATUS	current
	DESCRIPTION
		""
	DEFVAL   { '00000000'H }    -- 0.0.0.0
	::= { csOrionGenAclEntry 3 }

    csOrionGenAclDstAddress OBJECT-TYPE
	SYNTAX	IpAddress 
	MAX-ACCESS  read-create
	STATUS	current
	DESCRIPTION
		""
	DEFVAL   { '00000000'H }    -- 0.0.0.0
	::= { csOrionGenAclEntry 4 }

    csOrionGenAclDstMask OBJECT-TYPE
	SYNTAX	IpAddress 
	MAX-ACCESS  read-create
	STATUS	current
	DESCRIPTION
		""
	DEFVAL   { '00000000'H }    -- 0.0.0.0
	::= { csOrionGenAclEntry 5 }

    csOrionGenAclProt OBJECT-TYPE
	SYNTAX	Integer32 
	MAX-ACCESS  read-create
	STATUS	current
	DESCRIPTION
		"The Protocol ID that a packet must contain to match
		this access list entry.  The value -1 represents a wildcard
		for this General Access List parameter."
	DEFVAL  { -1 }
	::= { csOrionGenAclEntry 6 }

    csOrionGenAclTos OBJECT-TYPE
	SYNTAX	Integer32 (-1..4)
	MAX-ACCESS  read-create
	STATUS	current
	DESCRIPTION
		"The Type of Service that a packet must contain to match
		this access list entry.

		The value -1 represents a wildcard for this General Access 
		List parameter."
	DEFVAL  { -1 }
	::= { csOrionGenAclEntry 7 }

    csOrionGenAclStartSrcPort OBJECT-TYPE
	SYNTAX	Integer32 
	MAX-ACCESS  read-create
	STATUS	current
	DESCRIPTION
		"The beginning of a range of ports that a packet's source
		port must satisfy to match this access list entry.

		The value -1 represents a wildcard for this General Access 
		List parameter."
	DEFVAL  { -1 }
	::= { csOrionGenAclEntry 8 }

    csOrionGenAclEndSrcPort OBJECT-TYPE
	SYNTAX	Integer32 
	MAX-ACCESS  read-create
	STATUS	current
	DESCRIPTION
		"The end of a range of ports that a packet's source
		port must satisfy to match this access list entry.

		The value -1 represents a wildcard for this General Access 
		List parameter."
	DEFVAL  { -1 }
	::= { csOrionGenAclEntry 9 }

    csOrionGenAclStartDstPort OBJECT-TYPE
	SYNTAX	Integer32 
	MAX-ACCESS  read-create
	STATUS	current
	DESCRIPTION
		"The beginning of a range of ports that a packet's destination
		port must satisfy to match this access list entry.

		The value -1 represents a wildcard for this General Access 
		List parameter."
	DEFVAL  { -1 }
	::= { csOrionGenAclEntry 10 }

    csOrionGenAclEndDstPort OBJECT-TYPE
	SYNTAX	Integer32 
	MAX-ACCESS  read-create
	STATUS	current
	DESCRIPTION
		"The end of a range of ports that a packet's destination
		port must satisfy to match this access list entry.

		The value -1 represents a wildcard for this General Access 
		List parameter."
	DEFVAL  { -1 }
	::= { csOrionGenAclEntry 11 }

    csOrionGenAclStatus OBJECT-TYPE
	SYNTAX	RowStatus 
	MAX-ACCESS  read-create
	STATUS	current
	DESCRIPTION
		"This object is used to create/delete entries in this table."
	::= { csOrionGenAclEntry 12 }


------------------------------------------------------------------------------
--
-- 		Firewall Info 
--
------------------------------------------------------------------------------
csOrionFwConfig		OBJECT IDENTIFIER ::= { csOrionFWInfo 1 }

csOrionFwGlobalConfig	OBJECT IDENTIFIER ::= { csOrionFwConfig 1 }
csOrionFwProxyConfig	OBJECT IDENTIFIER ::= { csOrionFwConfig 2 }
csOrionFwGenProxyConfig	OBJECT IDENTIFIER ::= { csOrionFwProxyConfig 1 }
csOrionFwFtpConfig	OBJECT IDENTIFIER ::= { csOrionFwProxyConfig 2 }
csOrionFwHttpConfig	OBJECT IDENTIFIER ::= { csOrionFwProxyConfig 3 }
csOrionFwSmtpConfig	OBJECT IDENTIFIER ::= { csOrionFwProxyConfig 4 }
csOrionFwTelnetConfig	OBJECT IDENTIFIER ::= { csOrionFwProxyConfig 5 }
csOrionFwPop3Config	OBJECT IDENTIFIER ::= { csOrionFwProxyConfig 6 }
csOrionFwPlugConfig	OBJECT IDENTIFIER ::= { csOrionFwProxyConfig 7 }
csOrionFwNntpConfig	OBJECT IDENTIFIER ::= { csOrionFwProxyConfig 8 }
csOrionFwLdapConfig	OBJECT IDENTIFIER ::= { csOrionFwProxyConfig 9 }
csOrionFwLnotesConfig	OBJECT IDENTIFIER ::= { csOrionFwProxyConfig 10 }
csOrionFwAolConfig	OBJECT IDENTIFIER ::= { csOrionFwProxyConfig 11 }
csOrionFwCompuServeConfig	OBJECT IDENTIFIER ::= { csOrionFwProxyConfig 12 }
csOrionFwNetMeetingConfig	OBJECT IDENTIFIER ::= { csOrionFwProxyConfig 13 }
csOrionFwMsSqlConfig	OBJECT IDENTIFIER ::= { csOrionFwProxyConfig 14 }
csOrionFwRshConfig	OBJECT IDENTIFIER ::= { csOrionFwProxyConfig 15 }

--
-- Global Firewall configuration parameters
--

--
-- This table is used to configure the virtual interfaces
-- that are on the 'inside' or trusted side of the firewall
--

    csOrionFwInsideIfTable OBJECT-TYPE
	SYNTAX	SEQUENCE OF CsOrionFwInsideIfEntry
	MAX-ACCESS  not-accessible
	STATUS	deprecated
	DESCRIPTION
	    "This contains the list of all the interfaces on the inside,
	    or trusted, side of the firewall.

	    NOTE: This table is no longer in use."
	::= { csOrionFwGlobalConfig 1 }

    csOrionFwInsideIfEntry OBJECT-TYPE
	SYNTAX 	 CsOrionFwInsideIfEntry
	MAX-ACCESS  not-accessible
	STATUS	deprecated
	DESCRIPTION
	    ""
	INDEX   { csOrionGlobalVPNIndex, csOrionVPNVRouterIndex, 
		csOrionFwInsideIfIf, csOrionFwInsideIfAddr }
	::= { csOrionFwInsideIfTable 1 }

    CsOrionFwInsideIfEntry ::=
	SEQUENCE {
	csOrionFwInsideIfIf
		Integer32,
	csOrionFwInsideIfAddr
		IpAddress,
	csOrionFwInsideIfMask
		IpAddress,
	csOrionFwInsideIfRowStatus
		RowStatus
	}

    csOrionFwInsideIfIf OBJECT-TYPE
	SYNTAX  Integer32
	MAX-ACCESS  not-accessible
	STATUS  deprecated
	DESCRIPTION
	    "The identifier of the 'inside' virtual interface."
	::= { csOrionFwInsideIfEntry 1 }

    csOrionFwInsideIfAddr OBJECT-TYPE
	SYNTAX  IpAddress
	MAX-ACCESS  not-accessible
	STATUS  deprecated
	DESCRIPTION
	    "The Ip address of the 'inside' virtual interface."
	::= { csOrionFwInsideIfEntry 2 }

    csOrionFwInsideIfMask OBJECT-TYPE
	SYNTAX  IpAddress
	MAX-ACCESS  read-create
	STATUS  deprecated
	DESCRIPTION
	    "The Ip Mask of the 'inside' virtual interface."
	::= { csOrionFwInsideIfEntry 3 }

    csOrionFwInsideIfRowStatus OBJECT-TYPE
	SYNTAX  RowStatus
	MAX-ACCESS  read-create
	STATUS  deprecated
	DESCRIPTION
	    "The RowStatus object for this table."
	::= { csOrionFwInsideIfEntry 4 }

--
-- This table is used to configure the virtual interfaces
-- that are on the 'Dmz' side of the firewall.  Typically, these
-- are the only interfaces to which requests from the 'outside',
-- or untrusted, interfaces can be sent.
--
-- Note, any interface that is not in the csOrionFwInsideTable
-- or the csOrionFwDmzTable is assumed to be an 'outside' interface
-- and, hence, a member of the untrusted group.
--


    csOrionFwDmzIfTable OBJECT-TYPE
	SYNTAX	SEQUENCE OF CsOrionFwDmzIfEntry
	MAX-ACCESS  not-accessible
	STATUS	deprecated
	DESCRIPTION
	    "This contains the list of all the interfaces on the DmzIf
	    side of the firewall.

	    NOTE: This table is no longer in use."
	::= { csOrionFwGlobalConfig 2 }

    csOrionFwDmzIfEntry OBJECT-TYPE
	SYNTAX 	 CsOrionFwDmzIfEntry
	MAX-ACCESS  not-accessible
	STATUS	deprecated
	DESCRIPTION
	    ""
	INDEX   { csOrionGlobalVPNIndex, csOrionVPNVRouterIndex, 
		csOrionFwDmzIf, csOrionFwDmzIfAddr }
	::= { csOrionFwDmzIfTable 1 }

    CsOrionFwDmzIfEntry ::=
	SEQUENCE {
	csOrionFwDmzIf
		Integer32,
	csOrionFwDmzIfAddr
		IpAddress,
	csOrionFwDmzIfMask
		IpAddress,
	csOrionFwDmzIfRowStatus
		RowStatus
	}

    csOrionFwDmzIf OBJECT-TYPE
	SYNTAX  Integer32
	MAX-ACCESS  not-accessible
	STATUS  deprecated
	DESCRIPTION
	    "The identifier of a 'Dmz' virtual interface."
	::= { csOrionFwDmzIfEntry 1 }

    csOrionFwDmzIfAddr OBJECT-TYPE
	SYNTAX  IpAddress
	MAX-ACCESS  not-accessible
	STATUS  deprecated
	DESCRIPTION
	    "The Ip address of a 'Dmz' virtual interface."
	::= { csOrionFwDmzIfEntry 2 }

    csOrionFwDmzIfMask OBJECT-TYPE
	SYNTAX  IpAddress
	MAX-ACCESS  read-create
	STATUS  deprecated
	DESCRIPTION
	    "The Ip Mask of a 'Dmz' virtual interface."
	::= { csOrionFwDmzIfEntry 3 }

    csOrionFwDmzIfRowStatus OBJECT-TYPE
	SYNTAX  RowStatus
	MAX-ACCESS  read-create
	STATUS  deprecated
	DESCRIPTION
	    "The RowStatus object for this table."
	::= { csOrionFwDmzIfEntry 4 }

--
-- The firewall Network Group Table.  
--
-- Note, currently, this table only supports the 'trusted' group.  
-- No other Network Groups are allowed.  Further, members of this 
-- group can only be assigned to the the inside interface.
-- 

    csOrionFwNwGroupTable OBJECT-TYPE
	SYNTAX	SEQUENCE OF CsOrionFwNwGroupEntry
	MAX-ACCESS  not-accessible
	STATUS	deprecated
	DESCRIPTION
	    "This contains definitions of all the network groups
	    referred to in other parts of the Firewall configuration.

	    NOTE: This table is no longer in use."
	::= { csOrionFwGlobalConfig 3 }

    csOrionFwNwGroupEntry OBJECT-TYPE
	SYNTAX 	 CsOrionFwNwGroupEntry
	MAX-ACCESS  not-accessible
	STATUS	deprecated
	DESCRIPTION
	    ""
	INDEX   { csOrionGlobalVPNIndex, csOrionVPNVRouterIndex,
		csOrionFwNwGroupName, csOrionFwNwGroupAddr }
	::= { csOrionFwNwGroupTable 1 }

    CsOrionFwNwGroupEntry ::=
	SEQUENCE {
	csOrionFwNwGroupName
		DisplayString,
	csOrionFwNwGroupAddr	
		IpAddress,
	csOrionFwNwGroupMask
		IpAddress,
	csOrionFwNwGroupInterface
		INTEGER,
	csOrionFwNwGroupRowStatus
		RowStatus
	}

    csOrionFwNwGroupName OBJECT-TYPE
	SYNTAX  DisplayString(SIZE(0..32))
	MAX-ACCESS  not-accessible
	STATUS  deprecated
	DESCRIPTION
	    "The Name assigned to this Network Group."
	::= { csOrionFwNwGroupEntry 1 }

    csOrionFwNwGroupAddr OBJECT-TYPE
	SYNTAX  IpAddress
	MAX-ACCESS  not-accessible
	STATUS  deprecated
	DESCRIPTION
	    "The Ip address of this member of this Network Group."
	::= { csOrionFwNwGroupEntry 2 }

    csOrionFwNwGroupMask OBJECT-TYPE
	SYNTAX  IpAddress
	MAX-ACCESS  read-create
	STATUS  deprecated
	DESCRIPTION
	    "The Ip Mask assigned to this member of this Network Group."
	::= { csOrionFwNwGroupEntry 3 }

    csOrionFwNwGroupInterface OBJECT-TYPE
	SYNTAX  INTEGER {
	    inside	(1),
	    outside	(2),
	    serviceNet	(3),
	    any		(4)
	}
	MAX-ACCESS  read-create
	STATUS  deprecated
	DESCRIPTION
	    "The Interface from which this member of this Network Group
	    can be reached."
	::= { csOrionFwNwGroupEntry 4 }

    csOrionFwNwGroupRowStatus OBJECT-TYPE
	SYNTAX  RowStatus
	MAX-ACCESS  read-create
	STATUS  deprecated
	DESCRIPTION
	    "The RowStatus object for this table."
	::= { csOrionFwNwGroupEntry 5 }

--
-- Event Logging Control Table for FIREWALL
--

    csOrionFwEvLogTable OBJECT-TYPE
	SYNTAX	SEQUENCE OF CsOrionFwEvLogEntry
	MAX-ACCESS  not-accessible
	STATUS	current
	DESCRIPTION
		"A table for Event Logging Control for FIREWALL."
	::= { csOrionFwGlobalConfig 4 }

    csOrionFwEvLogEntry OBJECT-TYPE
	SYNTAX 	 CsOrionFwEvLogEntry
	MAX-ACCESS  not-accessible
	STATUS	current
	DESCRIPTION
		"Each entry contains the event logging level
		for the FIREWALL module on a
		virtual router."
	INDEX   { csOrionGlobalVPNIndex, csOrionVPNVRouterIndex }
	::= { csOrionFwEvLogTable 1 }

    CsOrionFwEvLogEntry ::=
	SEQUENCE {
	csOrionFwEvLogLevel
		EvLogLevel
	}

    csOrionFwEvLogLevel OBJECT-TYPE
        SYNTAX EvLogLevel
        MAX-ACCESS read-write
        STATUS     current
        DESCRIPTION
               "This object is used to set the level of details for
                event logs for FIREWALL. 
	       "
        DEFVAL { major }  -- only critical and major events will be logged
        ::= { csOrionFwEvLogEntry 1 }

--
-- The General Proxy Configuration Table
--
-- This table groups together all those common parameters that
-- are supported by multiple proxies.  (Note, each proxy supports
-- a separate instance of each parameter)
--

    csOrionFwGenProxyTable OBJECT-TYPE
	SYNTAX	SEQUENCE OF CsOrionFwGenProxyEntry
	MAX-ACCESS  not-accessible
	STATUS	current
	DESCRIPTION
	    "This table specifies various configuration parameters
	    for each applicable proxy."
	::= { csOrionFwGenProxyConfig 1 }

    csOrionFwGenProxyEntry OBJECT-TYPE
	SYNTAX 	 CsOrionFwGenProxyEntry
	MAX-ACCESS  not-accessible
	STATUS	current
	DESCRIPTION
	    "Each entry specifies a set of configuration parameters
	    for a single proxy."
	INDEX   { csOrionGlobalVPNIndex, csOrionVPNVRouterIndex,
		csOrionFwGenProxyId }
	::= { csOrionFwGenProxyTable 1 }

    CsOrionFwGenProxyEntry ::=
	SEQUENCE {
	csOrionFwGenProxyId
		INTEGER,
	csOrionFwGenProxyChildLimit
		Integer32,
	csOrionFwGenProxyStatus
		INTEGER
	}

    csOrionFwGenProxyId OBJECT-TYPE
	SYNTAX  INTEGER {
	    ftp		(1),
	    http	(2),
	    telnet	(3),
	    smtp	(4),
	    pop3	(5),
	    plug	(6),
	    nntp	(7),
	    ldap	(8),
	    lnotes	(9),
	    rsh		(10),
	    aol   	(11),
	    cs		(12),  -- CompuServe
	    netm	(13),  -- NetMeeting
	    mssql	(14)   -- MS SQL/Sybase
	}
	MAX-ACCESS  not-accessible
	STATUS  current
	DESCRIPTION
	    "The proxy to which this entry applies."
	::= { csOrionFwGenProxyEntry 1 }

    csOrionFwGenProxyChildLimit OBJECT-TYPE
	SYNTAX  Integer32 (0..2147483647)
	MAX-ACCESS  read-write
	STATUS  current
	DESCRIPTION
	    "The maximum number of child processes that each of this proxy's
	    daemon allows to run at a given time.  If this option is set to
	    zero, each daemon allows an unlimited number of child processes
	    to run at any given time.  Note, this is not applicable to the
	    smtp proxy."
	DEFVAL { 64 }
	::= { csOrionFwGenProxyEntry 2 }

    csOrionFwGenProxyStatus OBJECT-TYPE
	SYNTAX  INTEGER {
	    enabled		(1),
	    disabled	(2)
	}
	MAX-ACCESS  read-write
	STATUS  current
	DESCRIPTION
	    "This is used to enable/disable a specific proxy."
	::= { csOrionFwGenProxyEntry 3 }

--
-- The Proxy Destination Table
-- This table specifies destination hosts and networks permissions
-- for each of the applicable proxies.
--

    csOrionFwDestTable OBJECT-TYPE
	SYNTAX	SEQUENCE OF CsOrionFwDestEntry
	MAX-ACCESS  not-accessible
	STATUS	deprecated
	DESCRIPTION
	    "This table specifies destination hosts and networks permissions
	    for each applicable proxy.

	    NOTE: This table has been replaced by csOrionFwAccessTable."
	::= { csOrionFwGenProxyConfig 2 }

    csOrionFwDestEntry OBJECT-TYPE
	SYNTAX 	 CsOrionFwDestEntry
	MAX-ACCESS  not-accessible
	STATUS	deprecated
	DESCRIPTION
	    "Each entry specifies a single destination host or network."
	INDEX   { csOrionGlobalVPNIndex, csOrionVPNVRouterIndex,
		csOrionFwDestProxy, csOrionFwDestIndex }
	::= { csOrionFwDestTable 1 }

    CsOrionFwDestEntry ::=
	SEQUENCE {
	csOrionFwDestProxy
		INTEGER,
	csOrionFwDestIndex	
		Integer32,
	csOrionFwDestAccess
		INTEGER,
	csOrionFwDestAddr
		IpAddress,
	csOrionFwDestMask
		IpAddress,
	csOrionFwDestRowStatus
		RowStatus
	}

    csOrionFwDestProxy OBJECT-TYPE
	SYNTAX  INTEGER {
	    ftp		(1),
	    http	(2),
	    telnet	(3),
	    smtp	(4),
		pop3	(5),
	    plug	(6),
	    nntp	(7),
	    ldap	(8),
	    lnotes	(9),
	    mssql	(10),
	    aol	(11),
	    cs	(12),
	    netm	(13)
	}
	MAX-ACCESS  not-accessible
	STATUS  deprecated
	DESCRIPTION
	    "The proxy to which this entry applies."
	::= { csOrionFwDestEntry 1 }

    csOrionFwDestIndex OBJECT-TYPE
	SYNTAX  Integer32 (1..2147483647)
	MAX-ACCESS  not-accessible
	STATUS  deprecated
	DESCRIPTION
	    "The table index for this entry applies.  This
	    identifies the order in which the destination rules
	    are applied."
	::= { csOrionFwDestEntry 2 }

    csOrionFwDestAccess OBJECT-TYPE
	SYNTAX  INTEGER {
	    permit	(1),
	    deny	(2)
	}
	MAX-ACCESS  read-create
	STATUS  deprecated
	DESCRIPTION
	    "The access policy applied to the host or network identified
	    in this entry."
	DEFVAL { permit }
	::= { csOrionFwDestEntry 3 }

    csOrionFwDestAddr OBJECT-TYPE
	SYNTAX  IpAddress
	MAX-ACCESS  read-create
	STATUS  deprecated
	DESCRIPTION
	    "The Destination address for this entry."
	DEFVAL   { '00000000'H }    -- 0.0.0.0
	::= { csOrionFwDestEntry 4 }

    csOrionFwDestMask OBJECT-TYPE
	SYNTAX  IpAddress
	MAX-ACCESS  read-create
	STATUS  deprecated
	DESCRIPTION
	    "The Destination address mask for this entry."
	DEFVAL   { '00000000'H }    -- 0.0.0.0
	::= { csOrionFwDestEntry 5 }

    csOrionFwDestRowStatus OBJECT-TYPE
	SYNTAX  RowStatus
	MAX-ACCESS  read-create
	STATUS  deprecated
	DESCRIPTION
	    "The RowStatus object for this entry."
	::= { csOrionFwDestEntry 6 }


--
-- The Proxy Host Table
-- This table specifies source hosts and networks permissions
-- for each of the applicable proxies.
--

    csOrionFwHostTable OBJECT-TYPE
	SYNTAX	SEQUENCE OF CsOrionFwHostEntry
	MAX-ACCESS  not-accessible
	STATUS	deprecated
	DESCRIPTION
	    "This table specifies source hosts and networks permissions
	    for each applicable proxy.

	    NOTE: This table has been replaces by csOrionFwAccessTable."
	::= { csOrionFwGenProxyConfig 3 }

    csOrionFwHostEntry OBJECT-TYPE
	SYNTAX 	 CsOrionFwHostEntry
	MAX-ACCESS  not-accessible
	STATUS	deprecated
	DESCRIPTION
	    "Each entry specifies a single destination host or network."
	INDEX   { csOrionGlobalVPNIndex, csOrionVPNVRouterIndex,
		csOrionFwHostProxy, csOrionFwHostIndex }
	::= { csOrionFwHostTable 1 }

    CsOrionFwHostEntry ::=
	SEQUENCE {
	csOrionFwHostProxy
		INTEGER,
	csOrionFwHostIndex	
		Integer32,
	csOrionFwHostAccess
		INTEGER,
	csOrionFwHostAddr
		IpAddress,
	csOrionFwHostMask
		IpAddress,
	csOrionFwHostRowStatus
		RowStatus
	}

    csOrionFwHostProxy OBJECT-TYPE
	SYNTAX  INTEGER {
	    ftp		(1),
	    http	(2),
	    telnet	(3),
	    smtp	(4),
		pop3	(5),
	    plug	(6),
	    nntp	(7),
	    ldap	(8),
	    lnotes	(9),
	    mssql	(10),
	    aol	(11),
	    cs	(12),
	    netm	(13)
	}
	MAX-ACCESS  not-accessible
	STATUS  deprecated
	DESCRIPTION
	    "The proxy to which this entry applies."
	::= { csOrionFwHostEntry 1 }

    csOrionFwHostIndex OBJECT-TYPE
	SYNTAX  Integer32 (1..2147483647)
	MAX-ACCESS  not-accessible
	STATUS  deprecated
	DESCRIPTION
	    "The table index for this entry applies.  This
	    identifies the order in which the host rules
	    are applied."
	::= { csOrionFwHostEntry 2 }

    csOrionFwHostAccess OBJECT-TYPE
	SYNTAX  INTEGER {
	    permit	(1),
	    deny	(2)
	}
	MAX-ACCESS  read-create
	STATUS  deprecated
	DESCRIPTION
	    "The access policy applied to the host or network identified
	    in this entry."
	DEFVAL { permit } 
	::= { csOrionFwHostEntry 3 }

    csOrionFwHostAddr OBJECT-TYPE
	SYNTAX  IpAddress
	MAX-ACCESS  read-create
	STATUS  deprecated
	DESCRIPTION
	    "The Source address for this entry."
	DEFVAL   { '00000000'H }    -- 0.0.0.0
	::= { csOrionFwHostEntry 4 }

    csOrionFwHostMask OBJECT-TYPE
	SYNTAX  IpAddress
	MAX-ACCESS  read-create
	STATUS  deprecated
	DESCRIPTION
	    "The Source address mask for this entry."
	DEFVAL   { '00000000'H }    -- 0.0.0.0
	::= { csOrionFwHostEntry 5 }

    csOrionFwHostRowStatus OBJECT-TYPE
	SYNTAX  RowStatus
	MAX-ACCESS  read-create
	STATUS  deprecated
	DESCRIPTION
	    "The RowStatus object for this entry."
	::= { csOrionFwHostEntry 6 }


--
-- The Proxy Access Table
-- This table specifies the policy to apply for a new connection.
-- This effectively replaces the csOrionFwHost and csOrionFwDest tables.
--

    csOrionFwAccessTable OBJECT-TYPE
	SYNTAX	SEQUENCE OF CsOrionFwAccessEntry
	MAX-ACCESS  not-accessible
	STATUS	current
	DESCRIPTION
	    "This table specifies the policy to apply for each new connection.
	    A connection is identified by its source id, destination id, and
	    protocol."
	::= { csOrionFwGenProxyConfig 4 }

    csOrionFwAccessEntry OBJECT-TYPE
	SYNTAX 	 CsOrionFwAccessEntry
	MAX-ACCESS  not-accessible
	STATUS	current
	DESCRIPTION
	    "Each entry specifies a single Access Policy."
	INDEX   { csOrionGlobalVPNIndex, csOrionVPNVRouterIndex,
		csOrionFwAccessPriority }
	::= { csOrionFwAccessTable 1 }

    CsOrionFwAccessEntry ::=
	SEQUENCE {
	csOrionFwAccessPriority
		Integer32,
	csOrionFwAccessSourceAddr
		IpAddress,
	csOrionFwAccessSourceMask
		IpAddress,
	csOrionFwAccessDestAddr
		IpAddress,
	csOrionFwAccessDestMask
		IpAddress,
	csOrionFwAccessAction
		INTEGER,
	csOrionFwAccessPortNumber
		Integer32,
	csOrionFwAccessPolicy
		DisplayString,
	csOrionFwAccessRowStatus
		RowStatus
	}

    csOrionFwAccessPriority OBJECT-TYPE
	SYNTAX  Integer32 (1..2147483647)
	MAX-ACCESS  not-accessible
	STATUS  current
	DESCRIPTION
	    "The priority of this Access Table entry."
	::= { csOrionFwAccessEntry 1 }

    csOrionFwAccessSourceAddr OBJECT-TYPE
	SYNTAX  IpAddress
	MAX-ACCESS  read-create
	STATUS  current
	DESCRIPTION
	    "The Address of the source of a proxy connection."
	::= { csOrionFwAccessEntry 2 }

    csOrionFwAccessSourceMask OBJECT-TYPE
	SYNTAX  IpAddress
	MAX-ACCESS  read-create
	STATUS  current
	DESCRIPTION
	    "The Mask of the source of a proxy connection."
	::= { csOrionFwAccessEntry 3 }

    csOrionFwAccessDestAddr OBJECT-TYPE
	SYNTAX  IpAddress
	MAX-ACCESS  read-create
	STATUS  current
	DESCRIPTION
	    "The Address of the destination of a proxy connection."
	::= { csOrionFwAccessEntry 4 }

    csOrionFwAccessDestMask OBJECT-TYPE
	SYNTAX  IpAddress
	MAX-ACCESS  read-create
	STATUS  current
	DESCRIPTION
	    "The Mask of the destination of a proxy connection."
	::= { csOrionFwAccessEntry 5 }

    csOrionFwAccessAction OBJECT-TYPE
	SYNTAX  INTEGER {
		permit	(1),
		deny	(2)
	}
	MAX-ACCESS  read-create
	STATUS  current
	DESCRIPTION
	    "The action to perform on connections that match the Source Id,
	    Destination Id, and the Protocol."
	DEFVAL { deny }
	::= { csOrionFwAccessEntry 6 }

    csOrionFwAccessPortNumber OBJECT-TYPE
	SYNTAX  Integer32 (1..65535)
	MAX-ACCESS  read-create
	STATUS  current
	DESCRIPTION
	    "This object identifies the port number this access entry will
		 be applied. Together with the Source Id, and the Destination Id,
		 this is used to identify a specific connection."
	::= { csOrionFwAccessEntry 7 }

    csOrionFwAccessPolicy OBJECT-TYPE
	SYNTAX  DisplayString (SIZE(0..64))
	MAX-ACCESS  read-create
	STATUS  current
	DESCRIPTION
	    "This is the name of the policy to be applied to any connection
	    that matches the Source Id, Destination Id, and Protocol defined
	    in this entry.  The definition of the policy itself can be found
	    in the corresponding protocol-specific Policy Table." 
	DEFVAL { "" }
	::= { csOrionFwAccessEntry 8 }

    csOrionFwAccessRowStatus OBJECT-TYPE
	SYNTAX		RowStatus
	MAX-ACCESS	read-create
	STATUS		current
	DESCRIPTION
	    "A row status type for this Table entry."
	::= { csOrionFwAccessEntry 9 }


--
--
--

    csOrionFwProxyDaemonTable OBJECT-TYPE
	SYNTAX	SEQUENCE OF CsOrionFwProxyDaemonEntry
	MAX-ACCESS  not-accessible
	STATUS	current
	DESCRIPTION
	    "This is a list of daemon ports along with the protocol
		 that uses it."
	::= { csOrionFwGenProxyConfig 5 }

    csOrionFwProxyDaemonEntry OBJECT-TYPE
	SYNTAX 	 CsOrionFwProxyDaemonEntry
	MAX-ACCESS  not-accessible
	STATUS	current
	DESCRIPTION
	    "Each entry specifies a daemon port and the protocol."
	INDEX   { csOrionGlobalVPNIndex, csOrionVPNVRouterIndex,
		csOrionFwProxyDaemonPortNumber }
	::= { csOrionFwProxyDaemonTable 1 }

    CsOrionFwProxyDaemonEntry ::=
	SEQUENCE {
	csOrionFwProxyDaemonPortNumber
		Integer32,
	csOrionFwProxyDaemonProtocol
		INTEGER,
	csOrionFwProxyDaemonRowStatus
		RowStatus
	}

    csOrionFwProxyDaemonPortNumber OBJECT-TYPE
	SYNTAX  Integer32 (1..65535)
	MAX-ACCESS  not-accessible
	STATUS  current
	DESCRIPTION
	    "The port number of this daemon."
	::= { csOrionFwProxyDaemonEntry 1 }

    csOrionFwProxyDaemonProtocol OBJECT-TYPE
	SYNTAX  INTEGER {
	    ftp		(1),
	    http	(2),
	    telnet	(3),
	    smtp	(4),
	    pop3	(5),
	    plug	(6),
	    nntp	(7),
	    ldap	(8),
	    lnotes	(9),
	    rsh		(10),
	    aol   	(11),
	    cs		(12),  -- CompuServe
	    netm 	(13),  -- NetMeeting
	    mssql	(14)   -- MS SQL/Sybase
	}
	MAX-ACCESS  read-create
	STATUS  current
	DESCRIPTION
	    "The protocol that uses this daemon. This is a mandatory
		 during creation of entry."
	::= { csOrionFwProxyDaemonEntry 2 }

	csOrionFwProxyDaemonRowStatus OBJECT-TYPE
	SYNTAX  RowStatus
	MAX-ACCESS  read-create
	STATUS  current
	DESCRIPTION
	    "The RowStatus object for this entry."
	::= { csOrionFwProxyDaemonEntry 3 }


--
-- FTP Proxy configuration
--
-- This section contains parameters specific to the
-- FTP Proxy used by the Firewall.
--
    csOrionFwFtpConfigTable OBJECT-TYPE
	SYNTAX	SEQUENCE OF CsOrionFwFtpConfigEntry
	MAX-ACCESS  not-accessible
	STATUS	deprecated
	DESCRIPTION
	    "This table specifies Ftp functions that are permitted or
	    denied.

	    NOTE: This table has been replaced by csOrionFwFtpPolicyTable."
	::= { csOrionFwFtpConfig 1 }

    csOrionFwFtpConfigEntry OBJECT-TYPE
	SYNTAX 	 CsOrionFwFtpConfigEntry
	MAX-ACCESS  not-accessible
	STATUS	deprecated
	DESCRIPTION
	    "Each entry specifies a set of FTP proxy configuration parameters
	    for a single firewall instance."
	INDEX   { csOrionGlobalVPNIndex, csOrionVPNVRouterIndex }
	::= { csOrionFwFtpConfigTable 1 }

    CsOrionFwFtpConfigEntry ::=
	SEQUENCE {
	csOrionFwFtpLog
		Unsigned32,
	csOrionFwFtpFunctionIds
		Unsigned32
	}

    csOrionFwFtpLog OBJECT-TYPE
	SYNTAX		Unsigned32
	MAX-ACCESS  read-write
	STATUS		deprecated
	DESCRIPTION
	    "The ftp functions that are logged by this ftp proxy.
		It is a bitmap where each bit represents a function.
		The following is the bit assingment,
			abor	(0),
			acct	(1),
			allo	(2),
			appe	(3),
			cdup	(4),
			cwd		(5),
			dele	(6),
			help	(7),
			list	(8),
			mkd		(9),
			mode	(10),
			nlst	(11),
			noop	(12),
			pass	(13),
			pasv	(14),
			port	(15),
			pwd		(16),
			quit	(17),
			retr	(18),
			rmd		(19),
			rnfr	(20),
			rnto	(21),
			stor	(22),
			stou	(23),
			stru	(24),
			type	(25),
			user	(26),
			xcup	(27),
			xcwd	(28),
			xmkd	(29),
			xpwd	(30),
			xrmd	(31) " 
	::= { csOrionFwFtpConfigEntry 1 }

    csOrionFwFtpFunctionIds OBJECT-TYPE
	SYNTAX		Unsigned32 
	MAX-ACCESS  read-write
	STATUS		deprecated
	DESCRIPTION
	    "A set of specific ftp functions. It is a bitmap where
		each bit represents a specific function that will be 
		suported by this proxy. The following is the bit assignment,
			abor	(0),
			acct	(1),
			allo	(2),
			appe	(3),
			cdup	(4),
			cwd		(5),
			dele	(6),
			help	(7),
			list	(8),
			mkd		(9),
			mode	(10),
			nlst	(11),
			noop	(12),
			pass	(13),
			pasv	(14),
			port	(15),
			pwd		(16),
			quit	(17),
			retr	(18),
			rmd		(19),
			rnfr	(20),
			rnto	(21),
			stor	(22),
			stou	(23),
			stru	(24),
			type	(25),
			user	(26),
			xcup	(27),
			xcwd	(28),
			xmkd	(29),
			xpwd	(30),
			xrmd	(31) " 
	::= { csOrionFwFtpConfigEntry 2 }

--
-- The Ftp Policy Table
-- This table specifies policies to apply to Ftp proxy connections.
--
--

    csOrionFwFtpPolicyTable OBJECT-TYPE
	SYNTAX	SEQUENCE OF CsOrionFwFtpPolicyEntry
	MAX-ACCESS  not-accessible
	STATUS	current
	DESCRIPTION
	    "This table specifies individual Ftp Policies.  The Fw Access
	    Table identifies the specific policies to apply to specific
	    Ftp connections."
	::= { csOrionFwFtpConfig 2 }

    csOrionFwFtpPolicyEntry OBJECT-TYPE
	SYNTAX 	 CsOrionFwFtpPolicyEntry
	MAX-ACCESS  not-accessible
	STATUS	current
	DESCRIPTION
	    "Each entry specifies a single FtpPolicy Policy."
	INDEX   { csOrionGlobalVPNIndex, csOrionVPNVRouterIndex,
		csOrionFwFtpPolicyName }
	::= { csOrionFwFtpPolicyTable 1 }

    CsOrionFwFtpPolicyEntry ::=
	SEQUENCE {
	csOrionFwFtpPolicyName
		DisplayString,
	csOrionFwFtpPolicyAuthenticate	
		INTEGER,
	csOrionFwFtpPolicyTimeout
		Integer32,
	csOrionFwFtpPolicyHandoffAddr
		DisplayString,
	csOrionFwFtpPolicyLog
		OCTET STRING,
	csOrionFwFtpPolicyFunctionIds
		OCTET STRING,
	csOrionFwFtpPolicyDynamicPacketFilter
		INTEGER,
	csOrionFwFtpPolicyRowStatus
		RowStatus
	}

    csOrionFwFtpPolicyName OBJECT-TYPE
	SYNTAX  DisplayString (SIZE(1..64))
	MAX-ACCESS  not-accessible
	STATUS  current
	DESCRIPTION
	    "The name used to identify this Ftp Policy entry."
	::= { csOrionFwFtpPolicyEntry 1 }

    csOrionFwFtpPolicyAuthenticate OBJECT-TYPE
	SYNTAX  INTEGER {
	    enable	(1),
	    disable	(2)
	}
	MAX-ACCESS  read-create
	STATUS  current
	DESCRIPTION
	    "This flag indicates if additional user authentication
		 is required."
	DEFVAL { disable }
	::= { csOrionFwFtpPolicyEntry 2 }

    csOrionFwFtpPolicyTimeout OBJECT-TYPE
	SYNTAX  Integer32 (1..2147483647)
	MAX-ACCESS  read-create
	STATUS  current
	DESCRIPTION
	    "The number of seconds the proxy is idle before disconnecting."
	DEFVAL { 7200 }
	::= { csOrionFwFtpPolicyEntry 3 }

    csOrionFwFtpPolicyHandoffAddr OBJECT-TYPE
	SYNTAX  DisplayString (SIZE(0..128))
	MAX-ACCESS  read-create
	STATUS  current
	DESCRIPTION
	    "The host to which this proxy hands the proxy request."
	DEFVAL { "" }
	::= { csOrionFwFtpPolicyEntry 4 }

    csOrionFwFtpPolicyLog OBJECT-TYPE
	SYNTAX	OCTET STRING (SIZE(5))
	MAX-ACCESS  read-create
	STATUS	current
	DESCRIPTION
	    "The ftp functions that are logged by this ftp proxy.
		It is a bitmap where each bit represents a function.
		The following is the bit assingment,
			abor	(0),
			acct	(1),
			allo	(2),
			appe	(3),
			cdup	(4),
			cwd		(5),
			dele	(6),
			help	(7),
			list	(8),
			mkd		(9),
			mode	(10),
			nlst	(11),
			noop	(12),
			pass	(13),
			pasv	(14),
			port	(15),
			pwd		(16),
			quit	(17),
			rein	(18),
			rest	(19),
			retr	(20),
			rmd		(21),
			rnfr	(22),
			rnto	(23),
			site	(24),
			size	(25),
			smnt	(26),
			stat	(27),
			stor	(28),
			stou	(29),
			stru	(30),
			syst	(31),
			type	(32),
			user	(33),
			xcup	(34),
			xcwd	(35),
			xmkd	(36),
			xpwd	(37),
			xrmd	(38) "
	DEFVAL{ '0000000000'H }  -- all functions are not logged.
	::= { csOrionFwFtpPolicyEntry 5 }

    csOrionFwFtpPolicyFunctionIds OBJECT-TYPE
	SYNTAX		OCTET STRING (SIZE(5)) 
	MAX-ACCESS  read-create
	STATUS		current
	DESCRIPTION
	    "A set of specific ftp functions. It is a bitmap where
		each bit represents a specific function that will be 
		suported by this proxy. The following is the bit assignment,
			abor	(0),
			acct	(1),
			allo	(2),
			appe	(3),
			cdup	(4),
			cwd		(5),
			dele	(6),
			help	(7),
			list	(8),
			mkd		(9),
			mode	(10),
			nlst	(11),
			noop	(12),
			pass	(13),
			pasv	(14),
			port	(15),
			pwd		(16),
			quit	(17),
			rein	(18),
			rest	(19),
			retr	(20),
			rmd		(21),
			rnfr	(22),
			rnto	(23),
			site	(24),
			size	(25),
			smnt	(26),
			stat	(27),
			stor	(28),
			stou	(29),
			stru	(30),
			syst	(31),
			type	(32),
			user	(33),
			xcup	(34),
			xcwd	(35),
			xmkd	(36),
			xpwd	(37),
			xrmd	(38) "
	DEFVAL{ '7FFFFFFFFF'H }  -- all functions are allowed.
	::= { csOrionFwFtpPolicyEntry 6 }

	csOrionFwFtpPolicyDynamicPacketFilter OBJECT-TYPE
	SYNTAX	INTEGER {
	    enable	(1),
	    disable	(2)
	} 
	MAX-ACCESS  read-create
	STATUS	current
	DESCRIPTION
	    "When enabled, allows the ftp proxy to, create dynamic 
		packet filter for data transfer (layer 2 forwarding)"
	DEFVAL{ disable }
	::= { csOrionFwFtpPolicyEntry 7 }

    csOrionFwFtpPolicyRowStatus OBJECT-TYPE
	SYNTAX	RowStatus 
	MAX-ACCESS  read-create
	STATUS	current
	DESCRIPTION
	    "The Row Status object for this table."
	::= { csOrionFwFtpPolicyEntry 8 }

--
-- HTTP Proxy configuration
--
-- This section contains parameters specific to the
-- HTTP Proxy used by the Firewall.
--

    csOrionFwHttpConfigTable OBJECT-TYPE
	SYNTAX	SEQUENCE OF CsOrionFwHttpConfigEntry
	MAX-ACCESS  not-accessible
	STATUS	deprecated
	DESCRIPTION
	    "This table specifies a set of Http proxy configuration
	    parameters.

	    NOTE: This table has been replaced by csOrionFwHttpPolicyTable."
	::= { csOrionFwHttpConfig 1 }

    csOrionFwHttpConfigEntry OBJECT-TYPE
	SYNTAX 	 CsOrionFwHttpConfigEntry
	MAX-ACCESS  not-accessible
	STATUS	deprecated
	DESCRIPTION
	    "Each entry specifies a set of Http proxy configuration
	    parameters for a single Http instance."
	INDEX   { csOrionGlobalVPNIndex, csOrionVPNVRouterIndex }
	::= { csOrionFwHttpConfigTable 1 }

    CsOrionFwHttpConfigEntry ::=
	SEQUENCE {
	csOrionFwHttpLog 
		Unsigned32,
	csOrionFwHttpOurname 
		DisplayString,
	csOrionFwHttpFeatureIds
		Unsigned32,
	csOrionFwHttpFunctionIds
		Unsigned32,
	csOrionFwHttpHeaderIds
		Unsigned32
	}

    csOrionFwHttpLog OBJECT-TYPE
	SYNTAX		Unsigned32 
	MAX-ACCESS  read-write
	STATUS		deprecated
	DESCRIPTION
	    "The http functions that are logged by the http proxy.
		It is a bitmap where each bit represents an http function
		that can be logged. The following is the bit assignment,
			binary	(0),
			dir		(1),
			exec	(2),
			ftp		(3),			
			httpreq	(4),
			http	(5),
			read	(6),
			retr	(7),
			stor    (8),
			text	(9),
			type	(10),
			write	(11)"
	::= { csOrionFwHttpConfigEntry 1 }

    csOrionFwHttpOurname OBJECT-TYPE
	SYNTAX  DisplayString (SIZE(0..128))
	MAX-ACCESS  read-write
	STATUS  deprecated
	DESCRIPTION
	    "The host and domain name that the HTTP proxy uses when
	    putting its own name into non-transparent forarded URL's."
	::= { csOrionFwHttpConfigEntry 2 }

    csOrionFwHttpFeatureIds OBJECT-TYPE
	SYNTAX		Unsigned32 
	MAX-ACCESS  read-write
	STATUS		deprecated
	DESCRIPTION
	    "A set of specific http features. It is a bitmap where
		each bit represents an http feature supported by this proxy. 
		The following is the bit assignment,
			activex		(0),
			frames		(1),
			java		(2),
			script	    (3)" 
	::= { csOrionFwHttpConfigEntry 3 }

    csOrionFwHttpFunctionIds OBJECT-TYPE
	SYNTAX		Unsigned32 
	MAX-ACCESS  read-write
	STATUS		deprecated
	DESCRIPTION
	    "A set of specific http functions. It is a bitmap where 
		each bit represents an http function supported by this
		proxy. The following is the bit assignment,
			binary	(0),
			dir		(1),
			exec	(2),
			ftp		(3),			
			httpreq	(4),
			http	(5),
			read	(6),
			retr	(7),
			stor    (8),
			text	(9),
			type	(10),
			write	(11)"
	::= { csOrionFwHttpConfigEntry 4 }

    csOrionFwHttpHeaderIds OBJECT-TYPE
	SYNTAX		Unsigned32 
	MAX-ACCESS  read-write
	STATUS		deprecated
	DESCRIPTION
	    "A set of specific http headers. It is a bitmap where 
		each bit represents an http header supported by this
		proxy. The following is the bit assignment,
			accept-charset	  (0),
			accept-encoding	  (1),
			accept-language	  (2),
			allow			  (3),
			content-encoding  (4),
			content-language  (5),
			date			  (6),
			expires			  (7),
			from			  (8),
			if-modified-since (9),
			last-modified    (10),
			link			 (11),
			mime-version	 (12),
			pragma           (13),
			referer          (14),
			retry-after		 (15),
			server           (16),
			title			 (17),
			uri				 (18),
			user-agent       (19),
			www-authenticate (20)"
	::= { csOrionFwHttpConfigEntry 5 }


--
-- The Http Policy Table
-- This table specifies policies to apply to Http proxy connections.
--
--

    csOrionFwHttpPolicyTable OBJECT-TYPE
	SYNTAX	SEQUENCE OF CsOrionFwHttpPolicyEntry
	MAX-ACCESS  not-accessible
	STATUS	current
	DESCRIPTION
	    "This table specifies individual Http Policies.  The Fw Access
	    Table identifies the specific policies to apply to specific
	    Http connections."
	::= { csOrionFwHttpConfig 2 }

    csOrionFwHttpPolicyEntry OBJECT-TYPE
	SYNTAX 	 CsOrionFwHttpPolicyEntry
	MAX-ACCESS  not-accessible
	STATUS	current
	DESCRIPTION
	    "Each entry specifies a single HttpPolicy Policy."
	INDEX   { csOrionGlobalVPNIndex, csOrionVPNVRouterIndex,
		csOrionFwHttpPolicyName }
	::= { csOrionFwHttpPolicyTable 1 }

    CsOrionFwHttpPolicyEntry ::=
	SEQUENCE {
	csOrionFwHttpPolicyName
		DisplayString,
	csOrionFwHttpPolicyAuthenticate	
		INTEGER,
	csOrionFwHttpPolicyTimeout
		Integer32,
	csOrionFwHttpPolicyHandoffAddr
		DisplayString,
	csOrionFwHttpPolicyOurname
		DisplayString,
	csOrionFwHttpPolicyLog
		OCTET STRING,
	csOrionFwHttpPolicyFunctionIds
		OCTET STRING,
	csOrionFwHttpPolicyFeatures
		OCTET STRING,
	csOrionFwHttpPolicyHeader
		OCTET STRING,
	csOrionFwHttpPolicyRowStatus
		RowStatus
	}

    csOrionFwHttpPolicyName OBJECT-TYPE
	SYNTAX  DisplayString (SIZE(1..64))
	MAX-ACCESS  not-accessible
	STATUS  current
	DESCRIPTION
	    "The name used to identify this Http Policy entry."
	::= { csOrionFwHttpPolicyEntry 1 }

    csOrionFwHttpPolicyAuthenticate OBJECT-TYPE
	SYNTAX  INTEGER {
	    enable	(1),
	    disable	(2)
	}
	MAX-ACCESS  read-create
	STATUS  current
	DESCRIPTION
	    "This flag indicates if additional user authentication
		 is required."
	DEFVAL { disable }
	::= { csOrionFwHttpPolicyEntry 2 }

    csOrionFwHttpPolicyTimeout OBJECT-TYPE
	SYNTAX  Integer32 (1..2147483647)
	MAX-ACCESS  read-create
	STATUS  current
	DESCRIPTION
	    "The number of seconds the proxy is idle before disconnecting."
	DEFVAL { 30 }
	::= { csOrionFwHttpPolicyEntry 3 }

    csOrionFwHttpPolicyHandoffAddr OBJECT-TYPE
	SYNTAX  DisplayString (SIZE(0..128))
	MAX-ACCESS  read-create
	STATUS  current
	DESCRIPTION
	    "The host to which this proxy hands the proxy request."
	DEFVAL { "" }
	::= { csOrionFwHttpPolicyEntry 4 }

    csOrionFwHttpPolicyOurname OBJECT-TYPE
	SYNTAX  DisplayString (SIZE(0..128))
	MAX-ACCESS  read-create
	STATUS  current
	DESCRIPTION
	    "The host and domain name that the HTTP proxy uses when
	    putting its own name into non-transparent forarded URL's."
	::= { csOrionFwHttpPolicyEntry 5 }

    csOrionFwHttpPolicyLog OBJECT-TYPE
	SYNTAX	OCTET STRING (SIZE(2))
	MAX-ACCESS  read-create
	STATUS	current
	DESCRIPTION
	    "The Http functions that are logged by this Http proxy.
		It is a bitmap where each bit represents a function.
		By default, all functions are not logged.

		The following is the bit assignment,
			bin		(0),	-- binary
			dir		(1),	-- directory
			exec	(2),	-- execute
			ftp		(3),	-- ftp
			hreq	(4),	-- http request
			http	(5),	-- http
			read	(6),	-- read
			retr	(7),	-- retrieve
			stor    (8),	-- store
			text	(9),	-- text
			type	(10),	-- type
			wrte	(11)	-- write"
	DEFVAL{ '0000'H }  -- all functions are not logged.
	::= { csOrionFwHttpPolicyEntry 6 }

    csOrionFwHttpPolicyFunctionIds OBJECT-TYPE
	SYNTAX	OCTET STRING (SIZE(2))
	MAX-ACCESS  read-create
	STATUS	current
	DESCRIPTION
	    "A set of specific http functions. It is a bitmap where
		each bit represents a specific function that will be 
		suported by this proxy. 

		The following is the bit assignment,
			bin		(0),	-- binary
			dir		(1),	-- directory
			exec	(2),	-- execute
			ftp		(3),	-- ftp
			hreq	(4),	-- http request
			http	(5),	-- http
			read	(6),	-- read
			retr	(7),	-- retrieve
			stor    (8),	-- store
			text	(9),	-- text
			type	(10),	-- type
			wrte	(11)	-- write"
	DEFVAL{ '0FFF'H }  -- all functions are allowed.
	::= { csOrionFwHttpPolicyEntry 7 }

    csOrionFwHttpPolicyFeatures OBJECT-TYPE
	SYNTAX	OCTET STRING (SIZE(1))
	MAX-ACCESS  read-create
	STATUS	current
	DESCRIPTION
	    "A set of specific http features. It is a bitmap where
		each bit represents a specific features that will be 
		suported by this proxy. 
		By default, all features are allowed.

		The following is the bit assignment,
			actx	(0),	-- activex
			fram	(1),	-- frames
			htm2	(2),	-- html 2
			java	(3),	-- java
			kanj	(4),	-- kanji
			legk	(5),	-- legacy kanji
			mpf		(6),	-- multi part form
			scrp	(7),	-- java script"
	DEFVAL{ 'FF'H }  -- all features are allowed.
	::= { csOrionFwHttpPolicyEntry 8 }

    csOrionFwHttpPolicyHeader OBJECT-TYPE
	SYNTAX	OCTET STRING (SIZE(3))
	MAX-ACCESS  read-create
	STATUS	current
	DESCRIPTION
	    "A set of specific http headers. It is a bitmap where
		each bit represents a specific header that will be 
		suported by this proxy. 

		By default, all http headers are supported.

		The following is the bit assignment,
			achr	(0),	-- accept charset
			aenc	(1),	-- accept encoding
			alng	(2),	-- accept language
			alow	(3),	-- allow
			cenc	(4),	-- content encoding
			clng	(5),	-- content language
			date	(6),	-- date
			exp		(7),	-- expires
			from	(8),	-- from
			imod	(9),	-- if modified since
			lmod	(10),	-- last modified
			lnk		(11),	-- link
			mime	(12),	-- mime version
			prgm	(13),	-- pragma
			refr	(14),	-- referer
			reta	(15),	-- retry after
			serv	(16),	-- server
			titl	(17),	-- title
			uri		(18),	-- uniform resource locator
			user	(19),	-- user agent
			www		(20),	-- www authenticate"
	DEFVAL{ '1FFFFF'H }  -- all headers are allowed.
	::= { csOrionFwHttpPolicyEntry 9 }

    csOrionFwHttpPolicyRowStatus OBJECT-TYPE
	SYNTAX	RowStatus 
	MAX-ACCESS  read-create
	STATUS	current
	DESCRIPTION
	    "The Row Status object for this table."
	::= { csOrionFwHttpPolicyEntry 10 }


--
-- The Http Port Multi-Value Table
--  
--

    csOrionFwHttpPortTable OBJECT-TYPE
	SYNTAX	SEQUENCE OF CsOrionFwHttpPortEntry
	MAX-ACCESS  not-accessible
	STATUS	current
	DESCRIPTION
	    "This table defines the specific ports that a particular
	     HTTP policy will permit or deny."
	::= { csOrionFwHttpConfig 3 }

    csOrionFwHttpPortEntry OBJECT-TYPE
	SYNTAX 	 CsOrionFwHttpPortEntry
	MAX-ACCESS  not-accessible
	STATUS	current
	DESCRIPTION
	    "Each entry specifies a single Http Policy."
	INDEX   { csOrionGlobalVPNIndex, csOrionVPNVRouterIndex,
		csOrionFwHttpPortPolicyName }
	::= { csOrionFwHttpPortTable 1 }

    CsOrionFwHttpPortEntry ::=
	SEQUENCE {
	csOrionFwHttpPortPolicyName
		DisplayString,
	csOrionFwHttpPortNumber
		Integer32,
	csOrionFwHttpPortAccess
		INTEGER,
	csOrionFwHttpPortRowStatus
		RowStatus
	}

    csOrionFwHttpPortPolicyName OBJECT-TYPE
	SYNTAX  DisplayString (SIZE(1..64))
	MAX-ACCESS  not-accessible
	STATUS  current
	DESCRIPTION
	    "The policy name this port access is applied to."
	::= { csOrionFwHttpPortEntry 1 }

	csOrionFwHttpPortNumber OBJECT-TYPE
	SYNTAX  Integer32 (1..65535)
	MAX-ACCESS  read-create
	STATUS  current
	DESCRIPTION
	    "The port number."
	::= { csOrionFwHttpPortEntry 2 }

	csOrionFwHttpPortAccess OBJECT-TYPE
	SYNTAX  INTEGER {
	    permit	(1),
	    deny	(2)
	}
	MAX-ACCESS  read-create
	STATUS  current
	DESCRIPTION
	    "The access to this port number."
	DEFVAL { deny }
	::= { csOrionFwHttpPortEntry 3 }

	csOrionFwHttpPortRowStatus OBJECT-TYPE
	SYNTAX  RowStatus
	MAX-ACCESS  read-create
	STATUS  current
	DESCRIPTION
	    "The RowStatus object for this entry."
	::= { csOrionFwHttpPortEntry 4 }

--
-- Smtp Proxy Configuration
--

    csOrionFwSmtpConfigTable OBJECT-TYPE
	SYNTAX	SEQUENCE OF CsOrionFwSmtpConfigEntry
	MAX-ACCESS  not-accessible
	STATUS	deprecated
	DESCRIPTION
	    "This table specifies a set of Smtp proxy configuration
	    parameters.

	    NOTE: This table has been replaced by csOrionFwSmtpPolicyTable."
	::= { csOrionFwSmtpConfig 1 }

    csOrionFwSmtpConfigEntry OBJECT-TYPE
	SYNTAX 	 CsOrionFwSmtpConfigEntry
	MAX-ACCESS  not-accessible
	STATUS	deprecated
	DESCRIPTION
	    "Each entry specifies a set of Smtp proxy configuration
	    parameters for a single Smtp instance."
	INDEX   { csOrionGlobalVPNIndex, csOrionVPNVRouterIndex }
	::= { csOrionFwSmtpConfigTable 1 }

    CsOrionFwSmtpConfigEntry ::=
	SEQUENCE {
	csOrionFwSmtpBadAdmin 
		DisplayString,
	csOrionFwSmtpBadDir 
		DisplayString,
	csOrionFwSmtpMaxChildren 
		Integer32,
	csOrionFwSmtpWakeup 
		Integer32,
	csOrionFwSmtpInternalMailHub
		DisplayString,
	csOrionFwSmtpLocalDomain
		DisplayString,
	csOrionFwSmtpLogging
		INTEGER,
	csOrionFwSmtpLogRelay
		INTEGER,
	csOrionFwSmtpLogSpam
		INTEGER,
	csOrionFwSmtpMaxBytes
		Integer32,
	csOrionFwSmtpMaxRecip
		Integer32,
	csOrionFwSmtpSpamReply
		Integer32,
	csOrionFwSmtpRelayReply
		Integer32
	}

    csOrionFwSmtpBadAdmin OBJECT-TYPE
	SYNTAX  DisplayString
	MAX-ACCESS  read-write
	STATUS  deprecated
	DESCRIPTION
	    "The username to which the smapd server forwards mail that
	    it cannot deliver."
	DEFVAL {""}
	::= { csOrionFwSmtpConfigEntry 1 }

    csOrionFwSmtpBadDir OBJECT-TYPE
	SYNTAX  DisplayString
	MAX-ACCESS  read-write
	STATUS  deprecated
	DESCRIPTION
	    "The directory in which the smapd server places any spooled mail
	    that it cannot deliver."
	DEFVAL {""}
	::= { csOrionFwSmtpConfigEntry 2 }

    csOrionFwSmtpMaxChildren OBJECT-TYPE
	SYNTAX  Integer32 (1..2147483647)
	MAX-ACCESS  read-write
	STATUS  deprecated
	DESCRIPTION
	    "The maximum number of child processes the smapd server can
	    fork to handle mail."
	::= { csOrionFwSmtpConfigEntry 3 }

    csOrionFwSmtpWakeup OBJECT-TYPE
	SYNTAX  Integer32 (1..2147483647)
	MAX-ACCESS  read-write
	STATUS  deprecated
	DESCRIPTION
	    "The number of seconds the smapd server sleeps between scans of 
	    spool directory for undelivered mail."
	::= { csOrionFwSmtpConfigEntry 4 }

    csOrionFwSmtpInternalMailHub OBJECT-TYPE
	SYNTAX  DisplayString (SIZE(0..80))
	MAX-ACCESS  read-write
	STATUS  deprecated
	DESCRIPTION
	    "This object identifies the Internal Mail Hub using either
	    an IP address or a domain name."
	DEFVAL { "" }
	::= { csOrionFwSmtpConfigEntry 5 }

    csOrionFwSmtpLocalDomain OBJECT-TYPE
	SYNTAX  DisplayString (SIZE(0..80))
	MAX-ACCESS  read-write
	STATUS  deprecated
	DESCRIPTION
	    "Local domain that the firewall is serving -- IP address
	    or domain name."
	DEFVAL {""}
	::= { csOrionFwSmtpConfigEntry 6 }

    csOrionFwSmtpLogging OBJECT-TYPE
	SYNTAX  INTEGER {
		none	(1),
		normal	(2)
	}
	MAX-ACCESS  read-write
	STATUS  deprecated
	DESCRIPTION
	    "Specifies if normal or no logging is to be done on SMTP proxy."
	DEFVAL { normal }
	::= { csOrionFwSmtpConfigEntry 7 }

    csOrionFwSmtpLogRelay OBJECT-TYPE
	SYNTAX  INTEGER {
		none	(1),
		reject	(2)
	}
	MAX-ACCESS  read-write
	STATUS  deprecated
	DESCRIPTION
	    "Logs the rejection of mail relay attempts."
	DEFVAL { none }
	::= { csOrionFwSmtpConfigEntry 8 }

    csOrionFwSmtpLogSpam OBJECT-TYPE
	SYNTAX  INTEGER {
		none	(1),
		reject	(2)
	}
	MAX-ACCESS  read-write
	STATUS  deprecated
	DESCRIPTION
	    "Logs the rejection of mail spam attempts."
	DEFVAL { none }
	::= { csOrionFwSmtpConfigEntry 9 }

    csOrionFwSmtpMaxBytes OBJECT-TYPE
	SYNTAX  Integer32 (0..2147483647)
	MAX-ACCESS  read-write
	STATUS  deprecated
	DESCRIPTION
	    "Maximum  number of bytes of the mail content.  The value 0
	    indicates no maximum."
	DEFVAL { 0 }
	::= { csOrionFwSmtpConfigEntry 10 }

    csOrionFwSmtpMaxRecip OBJECT-TYPE
	SYNTAX  Integer32 (1..2147483647)
	MAX-ACCESS  read-write
	STATUS  deprecated
	DESCRIPTION
	    "The maximum number of recipients of the mail message.  The
	    value 0 indicates no maximum."
	DEFVAL { 1 }
	::= { csOrionFwSmtpConfigEntry 11 }

    csOrionFwSmtpSpamReply OBJECT-TYPE
	SYNTAX  Integer32 
	MAX-ACCESS  read-write
	STATUS  deprecated
	DESCRIPTION
	    "This object controls the type of response the SMTP proxy
	    makes back to the connected SMTP server when nuisance mail
	    is detected:

		554 - Explicitly reject and notify the connected server.
		250 - Acknowledge acceptance of the message but drop it
		      at the firewall."
	DEFVAL { 554 }
	::= { csOrionFwSmtpConfigEntry 12 }

    csOrionFwSmtpRelayReply OBJECT-TYPE
	SYNTAX  Integer32
	MAX-ACCESS  read-write
	STATUS  deprecated
	DESCRIPTION
	    "This object controls the type of response the SMTP proxy
	    makes back to the connected SMTP server when unauthorized
	    mail relaying is detected:

		550 - Explicitly reject and notify the connected server.
		250 - Acknowledge acceptance of the message but drop it
		      at the firewall."
	DEFVAL { 550 }
	::= { csOrionFwSmtpConfigEntry 13 }


--
-- The SMTP Policy Table
--

    csOrionFwSmtpPolicyTable OBJECT-TYPE
	SYNTAX	SEQUENCE OF CsOrionFwSmtpPolicyEntry
	MAX-ACCESS  not-accessible
	STATUS	current
	DESCRIPTION
	    "This table specifies individual SMTP Policies.  The Fw Access
	    Table identifies the specific policies to apply to specific
	    SMTP connections."
	::= { csOrionFwSmtpConfig 2 }

    csOrionFwSmtpPolicyEntry OBJECT-TYPE
	SYNTAX 	 CsOrionFwSmtpPolicyEntry
	MAX-ACCESS  not-accessible
	STATUS	current
	DESCRIPTION
	    "Each entry specifies a single SmtpPolicy Policy."
	INDEX   { csOrionGlobalVPNIndex, csOrionVPNVRouterIndex,
		csOrionFwSmtpPolicyName }
	::= { csOrionFwSmtpPolicyTable 1 }

    CsOrionFwSmtpPolicyEntry ::=
	SEQUENCE {
	csOrionFwSmtpPolicyName
		DisplayString,
	csOrionFwSmtpPolicyTimeout
		Integer32,
	csOrionFwSmtpPolicyInternalMailHub
		DisplayString,
	csOrionFwSmtpPolicyBadEmailAdmin
		DisplayString,
	csOrionFwSmtpPolicyLocalDomain
		DisplayString,
	csOrionFwSmtpPolicyMaxBytes
		Integer32,
	csOrionFwSmtpPolicyMaxRecipients
		Integer32,
	csOrionFwSmtpPolicyLogging
		INTEGER,
	csOrionFwSmtpPolicyLogRelay
		INTEGER,
	csOrionFwSmtpPolicyRelayReply
		INTEGER,
	csOrionFwSmtpPolicyLogSpam
		INTEGER,
	csOrionFwSmtpPolicySpamReply
		INTEGER,
	csOrionFwSmtpPolicyRowStatus
		RowStatus,
	csOrionFwSmtpPolicyMimeCheck
		INTEGER
	}

    csOrionFwSmtpPolicyName OBJECT-TYPE
	SYNTAX  DisplayString (SIZE(1..64))
	MAX-ACCESS  not-accessible
	STATUS  current
	DESCRIPTION
	    "The name used to identify this Smtp Policy entry."
	::= { csOrionFwSmtpPolicyEntry 1 }

	csOrionFwSmtpPolicyTimeout OBJECT-TYPE
	SYNTAX  Integer32 (1..2147483647)
	MAX-ACCESS  read-create
	STATUS  current
	DESCRIPTION
	    "The timeout limit on idle connection in seconds."
	DEFVAL { 120 }
	::= { csOrionFwSmtpPolicyEntry 2 }

	csOrionFwSmtpPolicyInternalMailHub OBJECT-TYPE
	SYNTAX  DisplayString (SIZE(1..128))
	MAX-ACCESS  read-create
	STATUS  current
	DESCRIPTION
	    "The default internal mail hub for email to go to if 
		 the destination mail for the protected domain(see ..)."
	DEFVAL { "" }
	::= { csOrionFwSmtpPolicyEntry 3 }

	csOrionFwSmtpPolicyBadEmailAdmin OBJECT-TYPE
	SYNTAX  DisplayString (SIZE(1..64))
	MAX-ACCESS  read-create
	STATUS  current
	DESCRIPTION
	    "The administrator that will receive email notification
		 of any bad email."
	DEFVAL { "" }
	::= { csOrionFwSmtpPolicyEntry 4 }

	csOrionFwSmtpPolicyLocalDomain OBJECT-TYPE
	SYNTAX  DisplayString (SIZE(1..64))
	MAX-ACCESS  read-create
	STATUS  current
	DESCRIPTION
	    "The domain currently being protected by the firewall."
	DEFVAL { "" }
	::= { csOrionFwSmtpPolicyEntry 5 }

	csOrionFwSmtpPolicyMaxBytes OBJECT-TYPE
	SYNTAX  Integer32 (0..2147483647)
	MAX-ACCESS  read-create
	STATUS  current
	DESCRIPTION
	    "This is the maximum size (in bytes) of the mail body that the
		 proxy will accept. Any data beyond the maximum size is dropped.
		 NOTE: zero (0) means no limit restriction."
	DEFVAL { 0 }
	::= { csOrionFwSmtpPolicyEntry 6 }

	csOrionFwSmtpPolicyMaxRecipients OBJECT-TYPE
	SYNTAX  Integer32 (0..2147483647)
	MAX-ACCESS  read-create
	STATUS  current
	DESCRIPTION
	    "This is the maximum recipients that the proxy will 
		 allow at any given email. 
		 NOTE: zero (0) means no limit restriction."
	DEFVAL { 0 }
	::= { csOrionFwSmtpPolicyEntry 7 }

	csOrionFwSmtpPolicyLogging OBJECT-TYPE
	SYNTAX  INTEGER {
		none	(1),
		normal	(2)
	}
	MAX-ACCESS  read-create
	STATUS  current
	DESCRIPTION
	    "Indicates if normal or no logging is to be done."
	DEFVAL { normal }
	::= { csOrionFwSmtpPolicyEntry 8 }

	csOrionFwSmtpPolicyLogRelay OBJECT-TYPE
	SYNTAX  INTEGER {
		none	(1),
		reject	(2)
	}
	MAX-ACCESS  read-create
	STATUS  current
	DESCRIPTION
	    "Indicates if normal or no logging is to be done."
	DEFVAL { none }
	::= { csOrionFwSmtpPolicyEntry 9 }

	csOrionFwSmtpPolicyRelayReply OBJECT-TYPE
	SYNTAX  INTEGER {
		ok		(250),  -- requested mail action okay
		unavail	(550)   -- mailbox unavailable
	}
	MAX-ACCESS  read-create
	STATUS  current
	DESCRIPTION
	    "This object controls the type of response the SMTP proxy
	     makes back to the connected SMTP server when unauthorized
	     mail relaying is detected."
	DEFVAL { ok }
	::= { csOrionFwSmtpPolicyEntry 10 }

	csOrionFwSmtpPolicyLogSpam OBJECT-TYPE
	SYNTAX  INTEGER {
		none	(1),
		reject	(2)
	}
	MAX-ACCESS  read-create
	STATUS  current
	DESCRIPTION
	    "Indicates if normal or no logging is to be done."
	DEFVAL { none }
	::= { csOrionFwSmtpPolicyEntry 11 }

	csOrionFwSmtpPolicySpamReply OBJECT-TYPE
	SYNTAX  INTEGER {
		ok		(250), -- requested mail action okay
		failed	(554)  -- Transaction failed
	}
	MAX-ACCESS  read-create
	STATUS  current
	DESCRIPTION
	    "This object controls the type of response the SMTP proxy
	     makes back to the connected SMTP server when unauthorized
	     mail relaying is detected."
	DEFVAL { ok }
	::= { csOrionFwSmtpPolicyEntry 12 }

    csOrionFwSmtpPolicyRowStatus OBJECT-TYPE
	SYNTAX  RowStatus
	MAX-ACCESS  read-create
	STATUS  current
	DESCRIPTION
	    "Row status for this entry."
	::= { csOrionFwSmtpPolicyEntry 13 }

	csOrionFwSmtpPolicyMimeCheck OBJECT-TYPE
	SYNTAX  INTEGER {
	    enable	(1),
	    disable	(2)
	}
	MAX-ACCESS  read-create
	STATUS  current
	DESCRIPTION
	    "This object controls whether the proxy attempts
		to validate the syntax of all MIME attachments within
		the email message"
	DEFVAL { disable }
	::= { csOrionFwSmtpPolicyEntry 14 }

--
-- The SMTP Relay Multi-Value Table
--  
--

	csOrionFwSmtpRelayTable OBJECT-TYPE
	SYNTAX	SEQUENCE OF CsOrionFwSmtpRelayEntry
	MAX-ACCESS  not-accessible
	STATUS	current
	DESCRIPTION
	    "This table defines the specific email relay that a 
	     particular SMTP policy will permit or deny."
	::= { csOrionFwSmtpConfig 3 }

    csOrionFwSmtpRelayEntry OBJECT-TYPE
	SYNTAX 	 CsOrionFwSmtpRelayEntry
	MAX-ACCESS  not-accessible
	STATUS	current
	DESCRIPTION
	    "Each entry specifies a single email relay."
	INDEX   { csOrionGlobalVPNIndex, csOrionVPNVRouterIndex,
		csOrionFwSmtpRelayPolicyName, csOrionFwSmtpRelaySource }
	::= { csOrionFwSmtpRelayTable 1 }

    CsOrionFwSmtpRelayEntry ::=
	SEQUENCE {
	csOrionFwSmtpRelayPolicyName
		DisplayString,
	csOrionFwSmtpRelaySource
		DisplayString,
	csOrionFwSmtpRelayAccess
		INTEGER,
	csOrionFwSmtpRelayRowStatus
		RowStatus
	}

    csOrionFwSmtpRelayPolicyName OBJECT-TYPE
	SYNTAX  DisplayString (SIZE(1..64))
	MAX-ACCESS  not-accessible
	STATUS  current
	DESCRIPTION
	    "The policy name this email relay access is applied to."
	::= { csOrionFwSmtpRelayEntry 1 }

	csOrionFwSmtpRelaySource OBJECT-TYPE
	SYNTAX  DisplayString (SIZE(1..128))
	MAX-ACCESS  not-accessible
	STATUS  current
	DESCRIPTION
	    "The source id (IP address, IP address with mask, network IP address,
		 network IP address with mask) of the email relay."
	::= { csOrionFwSmtpRelayEntry 2 }

	csOrionFwSmtpRelayAccess OBJECT-TYPE
	SYNTAX  INTEGER {
	    permit	(1),
	    deny	(2)
	}
	MAX-ACCESS  read-create
	STATUS  current
	DESCRIPTION
	    "The access to this email relay."
	DEFVAL { deny }
	::= { csOrionFwSmtpRelayEntry 3 }

	csOrionFwSmtpRelayRowStatus OBJECT-TYPE
	SYNTAX  RowStatus
	MAX-ACCESS  read-create
	STATUS  current
	DESCRIPTION
	    "The row status object for this entry."
	::= { csOrionFwSmtpRelayEntry 4 }



--
-- The SMTP Spam Multi-Value Table
--  
--

	csOrionFwSmtpSpamTable OBJECT-TYPE
	SYNTAX	SEQUENCE OF CsOrionFwSmtpSpamEntry
	MAX-ACCESS  not-accessible
	STATUS	current
	DESCRIPTION
	    "This table defines the specific spam email that a 
	     particular SMTP policy will permit or deny."
	::= { csOrionFwSmtpConfig 4 }

    csOrionFwSmtpSpamEntry OBJECT-TYPE
	SYNTAX 	 CsOrionFwSmtpSpamEntry
	MAX-ACCESS  not-accessible
	STATUS	current
	DESCRIPTION
	    "Each entry specifies a single spamm email."
	INDEX   { csOrionGlobalVPNIndex, csOrionVPNVRouterIndex,
		csOrionFwSmtpSpamPolicyName, csOrionFwSmtpSpamSource }
	::= { csOrionFwSmtpSpamTable 1 }

    CsOrionFwSmtpSpamEntry ::=
	SEQUENCE {
	csOrionFwSmtpSpamPolicyName
		DisplayString,
	csOrionFwSmtpSpamSource
		DisplayString,
	csOrionFwSmtpSpamAccess
		INTEGER,
	csOrionFwSmtpSpamRowStatus
		RowStatus
	}

    csOrionFwSmtpSpamPolicyName OBJECT-TYPE
	SYNTAX  DisplayString (SIZE(1..64))
	MAX-ACCESS  not-accessible
	STATUS  current
	DESCRIPTION
	    "The policy name this spam email access is applied to."
	::= { csOrionFwSmtpSpamEntry 1 }

	csOrionFwSmtpSpamSource OBJECT-TYPE
	SYNTAX  DisplayString (SIZE(1..128))
	MAX-ACCESS  not-accessible
	STATUS  current
	DESCRIPTION
	    "The source id (IP address, IP address with mask, network IP address,
		 network IP address with mask) of the spam email."
	::= { csOrionFwSmtpSpamEntry 2 }

	csOrionFwSmtpSpamAccess OBJECT-TYPE
	SYNTAX  INTEGER {
	    permit	(1),
	    deny	(2)
	}
	MAX-ACCESS  read-create
	STATUS  current
	DESCRIPTION
	    "The access to this spam email."
	DEFVAL { deny }
	::= { csOrionFwSmtpSpamEntry 3 }

	csOrionFwSmtpSpamRowStatus OBJECT-TYPE
	SYNTAX  RowStatus
	MAX-ACCESS  read-create
	STATUS  current
	DESCRIPTION
	    "The row status object for this entry."
	::= { csOrionFwSmtpSpamEntry 4 }


--
-- The Telnet Policy Table
--
--

    csOrionFwTelnetPolicyTable OBJECT-TYPE
	SYNTAX	SEQUENCE OF CsOrionFwTelnetPolicyEntry
	MAX-ACCESS  not-accessible
	STATUS	current
	DESCRIPTION
	    "This table specifies individual Telnet Policies. The Fw Access
	    Table identifies the specific policies to apply to specific
	    Telnet connections."
	::= { csOrionFwTelnetConfig 1 }

    csOrionFwTelnetPolicyEntry OBJECT-TYPE
	SYNTAX 	 CsOrionFwTelnetPolicyEntry
	MAX-ACCESS  not-accessible
	STATUS	current
	DESCRIPTION
	    "Each entry specifies a single Telnet Policy."
	INDEX   { csOrionGlobalVPNIndex, csOrionVPNVRouterIndex,
		csOrionFwTelnetPolicyName }
	::= { csOrionFwTelnetPolicyTable 1 }

    CsOrionFwTelnetPolicyEntry ::=
	SEQUENCE {
	csOrionFwTelnetPolicyName
		DisplayString,
	csOrionFwTelnetPolicyAuthenticate	
		INTEGER,
	csOrionFwTelnetPolicyTimeout
		Integer32,
	csOrionFwTelnetPolicyPasswordChange
		INTEGER,
	csOrionFwTelnetPolicyPrompt
		DisplayString,
	csOrionFwTelnetPolicyXGateway
		INTEGER,
	csOrionFwTelnetPolicyRowStatus
		RowStatus
	}

    csOrionFwTelnetPolicyName OBJECT-TYPE
	SYNTAX  DisplayString (SIZE(1..64))
	MAX-ACCESS  not-accessible
	STATUS  current
	DESCRIPTION
	    "The name used to identify this Telnet Policy entry."
	::= { csOrionFwTelnetPolicyEntry 1 }

    csOrionFwTelnetPolicyAuthenticate OBJECT-TYPE
	SYNTAX  INTEGER {
	    enable	(1),
	    disable	(2)
	}
	MAX-ACCESS  read-create
	STATUS  current
	DESCRIPTION
	    "This flag indicates if additional user authentication
		 is required."
	DEFVAL { disable }
	::= { csOrionFwTelnetPolicyEntry 2 }

    csOrionFwTelnetPolicyTimeout OBJECT-TYPE
	SYNTAX  Integer32 (1..2147483647)
	MAX-ACCESS  read-create
	STATUS  current
	DESCRIPTION
	    "The number of seconds the proxy is idle before disconnecting."
	DEFVAL { 7200 }
	::= { csOrionFwTelnetPolicyEntry 3 }

    csOrionFwTelnetPolicyPasswordChange OBJECT-TYPE
	SYNTAX  INTEGER {
		allowed		(1),
		notAllowed	(2)
	}
	MAX-ACCESS  read-create
	STATUS  current
	DESCRIPTION
	    "This object indicates whether the user is allowed to 
		 change the password."
	DEFVAL { notAllowed }
	::= { csOrionFwTelnetPolicyEntry 4 }

    csOrionFwTelnetPolicyPrompt OBJECT-TYPE
	SYNTAX  DisplayString (SIZE(0..32))
	MAX-ACCESS  read-create
	STATUS  current
	DESCRIPTION
	    "The command line promt the proxy should use for telnet sessions."
	DEFVAL { "telnet>" }
	::= { csOrionFwTelnetPolicyEntry 5 }

    csOrionFwTelnetPolicyXGateway OBJECT-TYPE
	SYNTAX  INTEGER {
		allowed		(1),
		notAllowed	(2)
	}
	MAX-ACCESS  read-create
	STATUS  current
	DESCRIPTION
	    "This object indicates whether or not the client is allowed to
		 use X proxy."
	DEFVAL { notAllowed }
	::= { csOrionFwTelnetPolicyEntry 6 }

    csOrionFwTelnetPolicyRowStatus OBJECT-TYPE
	SYNTAX	RowStatus 
	MAX-ACCESS  read-create
	STATUS	current
	DESCRIPTION
	    "The Row Status object for this table."
	::= { csOrionFwTelnetPolicyEntry 7 }



--
-- The POP3 Policy Table
--
--

    csOrionFwPop3PolicyTable OBJECT-TYPE
	SYNTAX	SEQUENCE OF CsOrionFwPop3PolicyEntry
	MAX-ACCESS  not-accessible
	STATUS	current
	DESCRIPTION
	    "This table specifies individual POP3 Policies. The Fw Access
	    Table identifies the specific policies to apply to specific
	    POP3 connections."
	::= { csOrionFwPop3Config 1 }

    csOrionFwPop3PolicyEntry OBJECT-TYPE
	SYNTAX 	 CsOrionFwPop3PolicyEntry
	MAX-ACCESS  not-accessible
	STATUS	current
	DESCRIPTION
	    "Each entry specifies a single POP3 Policy."
	INDEX   { csOrionGlobalVPNIndex, csOrionVPNVRouterIndex,
		csOrionFwPop3PolicyName }
	::= { csOrionFwPop3PolicyTable 1 }

    CsOrionFwPop3PolicyEntry ::=
	SEQUENCE {
	csOrionFwPop3PolicyName
		DisplayString,
	csOrionFwPop3PolicyAuthenticate	
		INTEGER,
	csOrionFwPop3PolicyTimeout
		Integer32,
	csOrionFwPop3PolicyPopServer
		DisplayString,
	csOrionFwPop3PolicyRowStatus
		RowStatus
	}

    csOrionFwPop3PolicyName OBJECT-TYPE
	SYNTAX  DisplayString (SIZE(1..64))
	MAX-ACCESS  not-accessible
	STATUS  current
	DESCRIPTION
	    "The name used to identify this POP3 Policy entry."
	::= { csOrionFwPop3PolicyEntry 1 }

    csOrionFwPop3PolicyAuthenticate OBJECT-TYPE
	SYNTAX  INTEGER {
	    enable	(1),
	    disable	(2)
	}
	MAX-ACCESS  read-create
	STATUS  current
	DESCRIPTION
	    "This flag indicates if additional user authentication
		 is required."
	DEFVAL { disable }
	::= { csOrionFwPop3PolicyEntry 2 }

    csOrionFwPop3PolicyTimeout OBJECT-TYPE
	SYNTAX  Integer32 (1..2147483647)
	MAX-ACCESS  read-create
	STATUS  current
	DESCRIPTION
	    "The number of seconds the proxy is idle before disconnecting."
	DEFVAL { 7200 }
	::= { csOrionFwPop3PolicyEntry 3 }

    csOrionFwPop3PolicyPopServer OBJECT-TYPE
	SYNTAX  DisplayString (SIZE(0..128))
	MAX-ACCESS  read-create
	STATUS  current
	DESCRIPTION
	    "The default internal POP server for email."
	DEFVAL { "" }
	::= { csOrionFwPop3PolicyEntry 4 }

    csOrionFwPop3PolicyRowStatus OBJECT-TYPE
	SYNTAX	RowStatus 
	MAX-ACCESS  read-create
	STATUS	current
	DESCRIPTION
	    "The Row Status object for this table."
	::= { csOrionFwPop3PolicyEntry 7 }


--
-- The PLUG Policy Table
--
--

    csOrionFwPlugPolicyTable OBJECT-TYPE
	SYNTAX	SEQUENCE OF CsOrionFwPlugPolicyEntry
	MAX-ACCESS  not-accessible
	STATUS	current
	DESCRIPTION
	    "This table specifies individual PLUG Policies. The Fw Access
	    Table identifies the specific policies to apply to specific
	    PLUG connections."
	::= { csOrionFwPlugConfig 1 }

    csOrionFwPlugPolicyEntry OBJECT-TYPE
	SYNTAX 	 CsOrionFwPlugPolicyEntry
	MAX-ACCESS  not-accessible
	STATUS	current
	DESCRIPTION
	    "Each entry specifies a single PLUG Policy."
	INDEX   { csOrionGlobalVPNIndex, csOrionVPNVRouterIndex,
		csOrionFwPlugPolicyName }
	::= { csOrionFwPlugPolicyTable 1 }

    CsOrionFwPlugPolicyEntry ::=
	SEQUENCE {
	csOrionFwPlugPolicyName
		DisplayString,
	csOrionFwPlugPolicyAuthenticate	
		INTEGER,
	csOrionFwPlugPolicyTimeout
		Integer32,
	csOrionFwPlugPolicyRemoteServer
		DisplayString,
	csOrionFwPlugPolicyRemotePort
		Integer32,
	csOrionFwPlugPolicyRowStatus
		RowStatus
	}

    csOrionFwPlugPolicyName OBJECT-TYPE
	SYNTAX  DisplayString (SIZE(1..64))
	MAX-ACCESS  not-accessible
	STATUS  current
	DESCRIPTION
	    "The name used to identify this PLUG Policy entry."
	::= { csOrionFwPlugPolicyEntry 1 }

    csOrionFwPlugPolicyAuthenticate OBJECT-TYPE
	SYNTAX  INTEGER {
	    enable	(1),
	    disable	(2)
	}
	MAX-ACCESS  read-create
	STATUS  deprecated
	DESCRIPTION
	    "This flag indicates if additional user authentication
		 is required.

	     NOTE: Authenticate attribute is not applicable
	         to this kind of application."
	DEFVAL { disable }
	::= { csOrionFwPlugPolicyEntry 2 }

    csOrionFwPlugPolicyTimeout OBJECT-TYPE
	SYNTAX  Integer32 (1..2147483647)
	MAX-ACCESS  read-create
	STATUS  current
	DESCRIPTION
	    "The number of seconds the proxy is idle before disconnecting."
	DEFVAL { 7200 }
	::= { csOrionFwPlugPolicyEntry 3 }

    csOrionFwPlugPolicyRemoteServer OBJECT-TYPE
	SYNTAX  DisplayString (SIZE(0..128))
	MAX-ACCESS  read-create
	STATUS  current
	DESCRIPTION
	    "The remote server."
	DEFVAL { "" }
	::= { csOrionFwPlugPolicyEntry 4 }

    csOrionFwPlugPolicyRemotePort OBJECT-TYPE
	SYNTAX  Integer32 (1..65535)
	MAX-ACCESS  read-create
	STATUS  current
	DESCRIPTION
	    "The remote server's port number."
	::= { csOrionFwPlugPolicyEntry 5 }

    csOrionFwPlugPolicyRowStatus OBJECT-TYPE
	SYNTAX	RowStatus 
	MAX-ACCESS  read-create
	STATUS	current
	DESCRIPTION
	    "The Row Status object for this table."
	::= { csOrionFwPlugPolicyEntry 6 }



--
-- The NNTP Policy Table
--
--

    csOrionFwNntpPolicyTable OBJECT-TYPE
	SYNTAX	SEQUENCE OF CsOrionFwNntpPolicyEntry
	MAX-ACCESS  not-accessible
	STATUS	current
	DESCRIPTION
	    "This table specifies individual NNTP Policies. The Fw Access
	    Table identifies the specific policies to apply to specific
	    NNTP connections."
	::= { csOrionFwNntpConfig 1 }

    csOrionFwNntpPolicyEntry OBJECT-TYPE
	SYNTAX 	 CsOrionFwNntpPolicyEntry
	MAX-ACCESS  not-accessible
	STATUS	current
	DESCRIPTION
	    "Each entry specifies a single NNTP Policy."
	INDEX   { csOrionGlobalVPNIndex, csOrionVPNVRouterIndex,
		csOrionFwNntpPolicyName }
	::= { csOrionFwNntpPolicyTable 1 }

    CsOrionFwNntpPolicyEntry ::=
	SEQUENCE {
	csOrionFwNntpPolicyName
		DisplayString,
	csOrionFwNntpPolicyAuthenticate	
		INTEGER,
	csOrionFwNntpPolicyTimeout
		Integer32,
	csOrionFwNntpPolicyRemoteServer
		DisplayString,
	csOrionFwNntpPolicyRemotePort
		Integer32,
	csOrionFwNntpPolicyRowStatus
		RowStatus
	}

    csOrionFwNntpPolicyName OBJECT-TYPE
	SYNTAX  DisplayString (SIZE(1..64))
	MAX-ACCESS  not-accessible
	STATUS  current
	DESCRIPTION
	    "The name used to identify this NNTP Policy entry."
	::= { csOrionFwNntpPolicyEntry 1 }

    csOrionFwNntpPolicyAuthenticate OBJECT-TYPE
	SYNTAX  INTEGER {
	    enable	(1),
	    disable	(2)
	}
	MAX-ACCESS  read-create
	STATUS  deprecated
	DESCRIPTION
	    "This flag indicates if additional user authentication
		 is required.

	     NOTE: Authenticate attribute is not applicable
	         to this kind of application."
	DEFVAL { disable }
	::= { csOrionFwNntpPolicyEntry 2 }

    csOrionFwNntpPolicyTimeout OBJECT-TYPE
	SYNTAX  Integer32 (1..2147483647)
	MAX-ACCESS  read-create
	STATUS  current
	DESCRIPTION
	    "The number of seconds the proxy is idle before disconnecting."
	DEFVAL { 7200 }
	::= { csOrionFwNntpPolicyEntry 3 }

    csOrionFwNntpPolicyRemoteServer OBJECT-TYPE
	SYNTAX  DisplayString (SIZE(0..128))
	MAX-ACCESS  read-create
	STATUS  current
	DESCRIPTION
	    "The internal NEWS server."
	DEFVAL { "" }
	::= { csOrionFwNntpPolicyEntry 4 }

    csOrionFwNntpPolicyRemotePort OBJECT-TYPE
	SYNTAX  Integer32 (1..2147483647)
	MAX-ACCESS  read-create
	STATUS  current
	DESCRIPTION
	    "The internal NEWS server's port number."
	DEFVAL { 119 }
	::= { csOrionFwNntpPolicyEntry 5 }

    csOrionFwNntpPolicyRowStatus OBJECT-TYPE
	SYNTAX	RowStatus 
	MAX-ACCESS  read-create
	STATUS	current
	DESCRIPTION
	    "The Row Status object for this table."
	::= { csOrionFwNntpPolicyEntry 6 }



--
-- The LDAP Policy Table
--
--

    csOrionFwLdapPolicyTable OBJECT-TYPE
	SYNTAX	SEQUENCE OF CsOrionFwLdapPolicyEntry
	MAX-ACCESS  not-accessible
	STATUS	current
	DESCRIPTION
	    "This table specifies individual LDAP Policies. The Fw Access
	    Table identifies the specific policies to apply to specific
	    LDAP connections."
	::= { csOrionFwLdapConfig 1 }

    csOrionFwLdapPolicyEntry OBJECT-TYPE
	SYNTAX 	 CsOrionFwLdapPolicyEntry
	MAX-ACCESS  not-accessible
	STATUS	current
	DESCRIPTION
	    "Each entry specifies a single LDAP Policy."
	INDEX   { csOrionGlobalVPNIndex, csOrionVPNVRouterIndex,
		csOrionFwLdapPolicyName }
	::= { csOrionFwLdapPolicyTable 1 }

    CsOrionFwLdapPolicyEntry ::=
	SEQUENCE {
	csOrionFwLdapPolicyName
		DisplayString,
	csOrionFwLdapPolicyAuthenticate	
		INTEGER,
	csOrionFwLdapPolicyTimeout
		Integer32,
	csOrionFwLdapPolicyRemoteServer
		DisplayString,
	csOrionFwLdapPolicyRemotePort
		Integer32,
	csOrionFwLdapPolicyRowStatus
		RowStatus
	}

    csOrionFwLdapPolicyName OBJECT-TYPE
	SYNTAX  DisplayString (SIZE(1..64))
	MAX-ACCESS  not-accessible
	STATUS  current
	DESCRIPTION
	    "The name used to identify this LDAP Policy entry."
	::= { csOrionFwLdapPolicyEntry 1 }

    csOrionFwLdapPolicyAuthenticate OBJECT-TYPE
	SYNTAX  INTEGER {
	    enable	(1),
	    disable	(2)
	}
	MAX-ACCESS  read-create
	STATUS  deprecated
	DESCRIPTION
	    "This flag indicates if additional user authentication
		 is required.

	     NOTE: Authenticate attribute is not applicable
	         to this kind of application."
	DEFVAL { disable }
	::= { csOrionFwLdapPolicyEntry 2 }

    csOrionFwLdapPolicyTimeout OBJECT-TYPE
	SYNTAX  Integer32 (1..2147483647)
	MAX-ACCESS  read-create
	STATUS  current
	DESCRIPTION
	    "The number of seconds the proxy is idle before disconnecting."
	DEFVAL { 7200 }
	::= { csOrionFwLdapPolicyEntry 3 }

    csOrionFwLdapPolicyRemoteServer OBJECT-TYPE
	SYNTAX  DisplayString (SIZE(0..128))
	MAX-ACCESS  read-create
	STATUS  current
	DESCRIPTION
	    "The internal LDAP server."
	DEFVAL { "" }
	::= { csOrionFwLdapPolicyEntry 4 }

    csOrionFwLdapPolicyRemotePort OBJECT-TYPE
	SYNTAX  Integer32 (1..65535)
	MAX-ACCESS  read-create
	STATUS  current
	DESCRIPTION
	    "The internal LDAP server's port number."
	DEFVAL { 389 }
	::= { csOrionFwLdapPolicyEntry 5 }

    csOrionFwLdapPolicyRowStatus OBJECT-TYPE
	SYNTAX	RowStatus 
	MAX-ACCESS  read-create
	STATUS	current
	DESCRIPTION
	    "The Row Status object for this table."
	::= { csOrionFwLdapPolicyEntry 6 }



--
-- The LNOTES Policy Table
--
--

    csOrionFwLnotesPolicyTable OBJECT-TYPE
	SYNTAX	SEQUENCE OF CsOrionFwLnotesPolicyEntry
	MAX-ACCESS  not-accessible
	STATUS	current
	DESCRIPTION
	    "This table specifies individual LNOTES Policies. The Fw Access
	    Table identifies the specific policies to apply to specific
	    LNOTES connections."
	::= { csOrionFwLnotesConfig 1 }

    csOrionFwLnotesPolicyEntry OBJECT-TYPE
	SYNTAX 	 CsOrionFwLnotesPolicyEntry
	MAX-ACCESS  not-accessible
	STATUS	current
	DESCRIPTION
	    "Each entry specifies a single LNOTES Policy."
	INDEX   { csOrionGlobalVPNIndex, csOrionVPNVRouterIndex,
		csOrionFwLnotesPolicyName }
	::= { csOrionFwLnotesPolicyTable 1 }

    CsOrionFwLnotesPolicyEntry ::=
	SEQUENCE {
	csOrionFwLnotesPolicyName
		DisplayString,
	csOrionFwLnotesPolicyAuthenticate	
		INTEGER,
	csOrionFwLnotesPolicyTimeout
		Integer32,
	csOrionFwLnotesPolicyRemoteServer
		DisplayString,
	csOrionFwLnotesPolicyRemotePort
		Integer32,
	csOrionFwLnotesPolicyRowStatus
		RowStatus
	}

    csOrionFwLnotesPolicyName OBJECT-TYPE
	SYNTAX  DisplayString (SIZE(1..64))
	MAX-ACCESS  not-accessible
	STATUS  current
	DESCRIPTION
	    "The name used to identify this LNOTES Policy entry."
	::= { csOrionFwLnotesPolicyEntry 1 }

    csOrionFwLnotesPolicyAuthenticate OBJECT-TYPE
	SYNTAX  INTEGER {
	    enable	(1),
	    disable	(2)
	}
	MAX-ACCESS  read-create
	STATUS  deprecated
	DESCRIPTION
	    "This flag indicates if additional user authentication
		 is required.

	     NOTE: Authenticate attribute is not applicable
	         to this kind of application."
	DEFVAL { disable }
	::= { csOrionFwLnotesPolicyEntry 2 }

    csOrionFwLnotesPolicyTimeout OBJECT-TYPE
	SYNTAX  Integer32 (1..2147483647)
	MAX-ACCESS  read-create
	STATUS  current
	DESCRIPTION
	    "The number of seconds the proxy is idle before disconnecting."
	DEFVAL { 7200 }
	::= { csOrionFwLnotesPolicyEntry 3 }

    csOrionFwLnotesPolicyRemoteServer OBJECT-TYPE
	SYNTAX  DisplayString (SIZE(0..128))
	MAX-ACCESS  read-create
	STATUS  current
	DESCRIPTION
	    "The internal Lotus Notes server."
	DEFVAL { "" }
	::= { csOrionFwLnotesPolicyEntry 4 }

    csOrionFwLnotesPolicyRemotePort OBJECT-TYPE
	SYNTAX  Integer32 (1..65535)
	MAX-ACCESS  read-create
	STATUS  current
	DESCRIPTION
	    "The internal Lotus Notes server's port number."
	DEFVAL { 1352 }
	::= { csOrionFwLnotesPolicyEntry 5 }

    csOrionFwLnotesPolicyRowStatus OBJECT-TYPE
	SYNTAX	RowStatus 
	MAX-ACCESS  read-create
	STATUS	current
	DESCRIPTION
	    "The Row Status object for this table."
	::= { csOrionFwLnotesPolicyEntry 6 }


--
-- The AOL Policy Table
--
--

    csOrionFwAolPolicyTable OBJECT-TYPE
	SYNTAX	SEQUENCE OF CsOrionFwAolPolicyEntry
	MAX-ACCESS  not-accessible
	STATUS	current
	DESCRIPTION
	    "This table specifies individual AOL Policies. The Fw Access
	    Table identifies the specific policies to apply to specific
	    AOL connections."
	::= { csOrionFwAolConfig 1 }

    csOrionFwAolPolicyEntry OBJECT-TYPE
	SYNTAX 	 CsOrionFwAolPolicyEntry
	MAX-ACCESS  not-accessible
	STATUS	current
	DESCRIPTION
	    "Each entry specifies a single AOL Policy."
	INDEX   { csOrionGlobalVPNIndex, csOrionVPNVRouterIndex,
		csOrionFwAolPolicyName }
	::= { csOrionFwAolPolicyTable 1 }

    CsOrionFwAolPolicyEntry ::=
	SEQUENCE {
	csOrionFwAolPolicyName
		DisplayString,
	csOrionFwAolPolicyTimeout
		Integer32,
	csOrionFwAolPolicyRemoteServer
		DisplayString,
	csOrionFwAolPolicyRemotePort
		Integer32,
	csOrionFwAolPolicyRowStatus
		RowStatus
	}

    csOrionFwAolPolicyName OBJECT-TYPE
	SYNTAX  DisplayString (SIZE(1..64))
	MAX-ACCESS  not-accessible
	STATUS  current
	DESCRIPTION
	    "The name used to identify this AOL Policy entry."
	::= { csOrionFwAolPolicyEntry 1 }

    csOrionFwAolPolicyTimeout OBJECT-TYPE
	SYNTAX  Integer32 (1..2147483647)
	MAX-ACCESS  read-create
	STATUS  current
	DESCRIPTION
	    "The number of seconds the proxy is idle before disconnecting."
	DEFVAL { 7200 }
	::= { csOrionFwAolPolicyEntry 2 }

    csOrionFwAolPolicyRemoteServer OBJECT-TYPE
	SYNTAX  DisplayString (SIZE(0..128))
	MAX-ACCESS  read-create
	STATUS  current
	DESCRIPTION
	    "The internal AOL server."
	DEFVAL { "" }
	::= { csOrionFwAolPolicyEntry 3 }

    csOrionFwAolPolicyRemotePort OBJECT-TYPE
	SYNTAX  Integer32 (1..65535)
	MAX-ACCESS  read-create
	STATUS  current
	DESCRIPTION
	    "The internal AOL server's port number."
	DEFVAL { 5190 }
	::= { csOrionFwAolPolicyEntry 4 }

    csOrionFwAolPolicyRowStatus OBJECT-TYPE
	SYNTAX	RowStatus 
	MAX-ACCESS  read-create
	STATUS	current
	DESCRIPTION
	    "The Row Status object for this table."
	::= { csOrionFwAolPolicyEntry 5 }


--
-- The CompuServe Policy Table
--
--

    csOrionFwCompuServePolicyTable OBJECT-TYPE
	SYNTAX	SEQUENCE OF CsOrionFwCompuServePolicyEntry
	MAX-ACCESS  not-accessible
	STATUS	current
	DESCRIPTION
	    "This table specifies individual CompuServe Policies. The Fw Access
	    Table identifies the specific policies to apply to specific
	    CompuServe connections."
	::= { csOrionFwCompuServeConfig 1 }

    csOrionFwCompuServePolicyEntry OBJECT-TYPE
	SYNTAX 	 CsOrionFwCompuServePolicyEntry
	MAX-ACCESS  not-accessible
	STATUS	current
	DESCRIPTION
	    "Each entry specifies a single CompuServe Policy."
	INDEX   { csOrionGlobalVPNIndex, csOrionVPNVRouterIndex,
		csOrionFwCompuServePolicyName }
	::= { csOrionFwCompuServePolicyTable 1 }

    CsOrionFwCompuServePolicyEntry ::=
	SEQUENCE {
	csOrionFwCompuServePolicyName
		DisplayString,
	csOrionFwCompuServePolicyTimeout
		Integer32,
	csOrionFwCompuServePolicyRemoteServer
		DisplayString,
	csOrionFwCompuServePolicyRemotePort
		Integer32,
	csOrionFwCompuServePolicyRowStatus
		RowStatus
	}

    csOrionFwCompuServePolicyName OBJECT-TYPE
	SYNTAX  DisplayString (SIZE(1..64))
	MAX-ACCESS  not-accessible
	STATUS  current
	DESCRIPTION
	    "The name used to identify this CompuServe Policy entry."
	::= { csOrionFwCompuServePolicyEntry 1 }

    csOrionFwCompuServePolicyTimeout OBJECT-TYPE
	SYNTAX  Integer32 (1..2147483647)
	MAX-ACCESS  read-create
	STATUS  current
	DESCRIPTION
	    "The number of seconds the proxy is idle before disconnecting."
	DEFVAL { 7200 }
	::= { csOrionFwCompuServePolicyEntry 2 }

    csOrionFwCompuServePolicyRemoteServer OBJECT-TYPE
	SYNTAX  DisplayString (SIZE(0..128))
	MAX-ACCESS  read-create
	STATUS  current
	DESCRIPTION
	    "The internal CompuServe server."
	DEFVAL { "" }
	::= { csOrionFwCompuServePolicyEntry 3 }

    csOrionFwCompuServePolicyRemotePort OBJECT-TYPE
	SYNTAX  Integer32 (1..65535)
	MAX-ACCESS  read-create
	STATUS  current
	DESCRIPTION
	    "The internal CompuServe server's port number."
	DEFVAL { 4144 }
	::= { csOrionFwCompuServePolicyEntry 4 }

    csOrionFwCompuServePolicyRowStatus OBJECT-TYPE
	SYNTAX	RowStatus 
	MAX-ACCESS  read-create
	STATUS	current
	DESCRIPTION
	    "The Row Status object for this table."
	::= { csOrionFwCompuServePolicyEntry 5 }


--
-- The NetMeeting Policy Table
--
--

    csOrionFwNetMeetingPolicyTable OBJECT-TYPE
	SYNTAX	SEQUENCE OF CsOrionFwNetMeetingPolicyEntry
	MAX-ACCESS  not-accessible
	STATUS	current
	DESCRIPTION
	    "This table specifies individual NetMeeting Policies. The Fw Access
	    Table identifies the specific policies to apply to specific
	    NetMeeting connections."
	::= { csOrionFwNetMeetingConfig 1 }

    csOrionFwNetMeetingPolicyEntry OBJECT-TYPE
	SYNTAX 	 CsOrionFwNetMeetingPolicyEntry
	MAX-ACCESS  not-accessible
	STATUS	current
	DESCRIPTION
	    "Each entry specifies a single NetMeeting Policy."
	INDEX   { csOrionGlobalVPNIndex, csOrionVPNVRouterIndex,
		csOrionFwNetMeetingPolicyName }
	::= { csOrionFwNetMeetingPolicyTable 1 }

    CsOrionFwNetMeetingPolicyEntry ::=
	SEQUENCE {
	csOrionFwNetMeetingPolicyName
		DisplayString,
	csOrionFwNetMeetingPolicyTimeout
		Integer32,
	csOrionFwNetMeetingPolicyRemoteServer
		DisplayString,
	csOrionFwNetMeetingPolicyRemotePort
		Integer32,
	csOrionFwNetMeetingPolicyRowStatus
		RowStatus
	}

    csOrionFwNetMeetingPolicyName OBJECT-TYPE
	SYNTAX  DisplayString (SIZE(1..64))
	MAX-ACCESS  not-accessible
	STATUS  current
	DESCRIPTION
	    "The name used to identify this NetMeeting Policy entry."
	::= { csOrionFwNetMeetingPolicyEntry 1 }

    csOrionFwNetMeetingPolicyTimeout OBJECT-TYPE
	SYNTAX  Integer32 (1..2147483647)
	MAX-ACCESS  read-create
	STATUS  current
	DESCRIPTION
	    "The number of seconds the proxy is idle before disconnecting."
	DEFVAL { 7200 }
	::= { csOrionFwNetMeetingPolicyEntry 2 }

    csOrionFwNetMeetingPolicyRemoteServer OBJECT-TYPE
	SYNTAX  DisplayString (SIZE(0..128))
	MAX-ACCESS  read-create
	STATUS  current
	DESCRIPTION
	    "The internal NetMeeting server."
	DEFVAL { "" }
	::= { csOrionFwNetMeetingPolicyEntry 3 }

    csOrionFwNetMeetingPolicyRemotePort OBJECT-TYPE
	SYNTAX  Integer32 (1..65535)
	MAX-ACCESS  read-create
	STATUS  current
	DESCRIPTION
	    "The internal NetMeeting server's port number."
	DEFVAL { 1503 }
	::= { csOrionFwNetMeetingPolicyEntry 4 }

    csOrionFwNetMeetingPolicyRowStatus OBJECT-TYPE
	SYNTAX	RowStatus 
	MAX-ACCESS  read-create
	STATUS	current
	DESCRIPTION
	    "The Row Status object for this table."
	::= { csOrionFwNetMeetingPolicyEntry 5 }


--
-- The MsSql Policy Table
--
--

    csOrionFwMsSqlPolicyTable OBJECT-TYPE
	SYNTAX	SEQUENCE OF CsOrionFwMsSqlPolicyEntry
	MAX-ACCESS  not-accessible
	STATUS	current
	DESCRIPTION
	    "This table specifies individual Microsoft SQL/Sybase 
	    Policies. The Fw Access Table identifies the specific 
	    policies to apply to specific Microsoft SQL/Sybase
	    connections."
	::= { csOrionFwMsSqlConfig 1 }

    csOrionFwMsSqlPolicyEntry OBJECT-TYPE
	SYNTAX 	 CsOrionFwMsSqlPolicyEntry
	MAX-ACCESS  not-accessible
	STATUS	current
	DESCRIPTION
	    "Each entry specifies a single Microsoft SQL/Sybase Policy."
	INDEX   { csOrionGlobalVPNIndex, csOrionVPNVRouterIndex,
		csOrionFwMsSqlPolicyName }
	::= { csOrionFwMsSqlPolicyTable 1 }

    CsOrionFwMsSqlPolicyEntry ::=
	SEQUENCE {
	csOrionFwMsSqlPolicyName
		DisplayString,
	csOrionFwMsSqlPolicyTimeout
		Integer32,
	csOrionFwMsSqlPolicyRemoteServer
		DisplayString,
	csOrionFwMsSqlPolicyRemotePort
		Integer32,
	csOrionFwMsSqlPolicyRowStatus
		RowStatus
	}

    csOrionFwMsSqlPolicyName OBJECT-TYPE
	SYNTAX  DisplayString (SIZE(1..64))
	MAX-ACCESS  not-accessible
	STATUS  current
	DESCRIPTION
	    "The name used to identify this Microsoft SQL/Sybase Policy entry."
	::= { csOrionFwMsSqlPolicyEntry 1 }

    csOrionFwMsSqlPolicyTimeout OBJECT-TYPE
	SYNTAX  Integer32 (1..2147483647)
	MAX-ACCESS  read-create
	STATUS  current
	DESCRIPTION
	    "The number of seconds the proxy is idle before disconnecting."
	DEFVAL { 7200 }
	::= { csOrionFwMsSqlPolicyEntry 2 }

    csOrionFwMsSqlPolicyRemoteServer OBJECT-TYPE
	SYNTAX  DisplayString (SIZE(0..128))
	MAX-ACCESS  read-create
	STATUS  current
	DESCRIPTION
	    "The internal Microsoft SQL or Sybase server."
	::= { csOrionFwMsSqlPolicyEntry 3 }

    csOrionFwMsSqlPolicyRemotePort OBJECT-TYPE
	SYNTAX  Integer32 (1..65535)
	MAX-ACCESS  read-create
	STATUS  current
	DESCRIPTION
	    "The internal Microsoft SQL or Sybase server's port number."
	DEFVAL { 1433 }
	::= { csOrionFwMsSqlPolicyEntry 4 }

    csOrionFwMsSqlPolicyRowStatus OBJECT-TYPE
	SYNTAX	RowStatus 
	MAX-ACCESS  read-create
	STATUS	current
	DESCRIPTION
	    "The Row Status object for this table."
	::= { csOrionFwMsSqlPolicyEntry 5 }


--
-- The Rsh Policy Table
--
--

    csOrionFwRshPolicyTable OBJECT-TYPE
	SYNTAX	SEQUENCE OF CsOrionFwRshPolicyEntry
	MAX-ACCESS  not-accessible
	STATUS	current
	DESCRIPTION
	    "This table specifies individual Remote Shell (RSH) Policies. 
	    The Fw Access Table identifies the specific policies to apply 
	    to specific RSH connections."
	::= { csOrionFwRshConfig 1 }

    csOrionFwRshPolicyEntry OBJECT-TYPE
	SYNTAX 	 CsOrionFwRshPolicyEntry
	MAX-ACCESS  not-accessible
	STATUS	current
	DESCRIPTION
	    "Each entry specifies a single RSH Policy."
	INDEX   { csOrionGlobalVPNIndex, csOrionVPNVRouterIndex,
		csOrionFwRshPolicyName }
	::= { csOrionFwRshPolicyTable 1 }

    CsOrionFwRshPolicyEntry ::=
	SEQUENCE {
	csOrionFwRshPolicyName
		DisplayString,
	csOrionFwRshPolicyTimeout
		Integer32,
	csOrionFwRshPolicyRemoteServer
		DisplayString,
	csOrionFwRshPolicyRowStatus
		RowStatus
	}

    csOrionFwRshPolicyName OBJECT-TYPE
	SYNTAX  DisplayString (SIZE(1..64))
	MAX-ACCESS  not-accessible
	STATUS  current
	DESCRIPTION
	    "The name used to identify this RSH Policy entry."
	::= { csOrionFwRshPolicyEntry 1 }

    csOrionFwRshPolicyTimeout OBJECT-TYPE
	SYNTAX  Integer32 (1..2147483647)
	MAX-ACCESS  read-create
	STATUS  current
	DESCRIPTION
	    "The number of seconds the proxy is idle before disconnecting.
	     For RSH proxy, the idle timer is triggered if no activities
	     are detected on BOTH control and error connections."
	DEFVAL { 7200 }
	::= { csOrionFwRshPolicyEntry 2 }

    csOrionFwRshPolicyRemoteServer OBJECT-TYPE
	SYNTAX  DisplayString (SIZE(0..128))
	MAX-ACCESS  read-create
	STATUS  current
	DESCRIPTION
	    "The internal RSH server."
	DEFVAL { "" }
	::= { csOrionFwRshPolicyEntry 3 }

    csOrionFwRshPolicyRowStatus OBJECT-TYPE
	SYNTAX	RowStatus 
	MAX-ACCESS  read-create
	STATUS	current
	DESCRIPTION
	    "The Row Status object for this table."
	::= { csOrionFwRshPolicyEntry 4 }


------------------------------------------------------------------------------
--
--	       Packet Filter group
--
------------------------------------------------------------------------------

--
-- This table specifies a set of packet filters applied to each of the virtual
-- interfaces on a particular virtual router.
--

    csOrionVrPktFilterTable OBJECT-TYPE
	SYNTAX	SEQUENCE OF CsOrionVrPktFilterEntry
	MAX-ACCESS  not-accessible
	STATUS	current
	DESCRIPTION
	    "This table specifies a set of filters to be applied to
	    packets received over each the interfaces over this virtual
	    router.  Filters can be configured either to permit a packet,
	    deny a packet, or send the packet to a firewall proxy."
	::= { csOrionPktFilterInfo 1 }

    csOrionVrPktFilterEntry OBJECT-TYPE
	SYNTAX 	 CsOrionVrPktFilterEntry
	MAX-ACCESS  not-accessible
	STATUS	current
	DESCRIPTION
	    "Each filter specifies whether packets satisfying a specific
	    access list entry are permitted or denied to be passed along
	    their route."
	INDEX { csOrionGlobalVPNIndex, csOrionVPNVRouterIndex, 
		csOrionVrPktFilterIndex }
	::= { csOrionVrPktFilterTable 1 }

    CsOrionVrPktFilterEntry ::=
	SEQUENCE {
	csOrionVrPktFilterIndex
		Integer32,
	csOrionVrPktFilterAclId
		Integer32,
	csOrionVrPktFilterAction
		INTEGER,
	csOrionVrPktFilterDirection
		INTEGER,
	csOrionVrPktFilterRowStatus
		RowStatus,
	csOrionVrPktFilterTcpStatus
		INTEGER,
	csOrionVrPktFilterHitCounter
		Integer32,
	csOrionVrPktFilterCounterStatus
		INTEGER,
	csOrionVrPktFilterEvlogStatus
		INTEGER
	}

    csOrionVrPktFilterIndex OBJECT-TYPE
	SYNTAX		Integer32 (1..2147483647)
	MAX-ACCESS	not-accessible
	STATUS		current
	DESCRIPTION
	    "The Index of this particular Packet Filter."
	::= { csOrionVrPktFilterEntry 1 }

    csOrionVrPktFilterAclId OBJECT-TYPE
	SYNTAX		Integer32 (0..65535)
	MAX-ACCESS	read-create
	STATUS		current
	DESCRIPTION
	    "The Id of an access list entry (from csOrionGenAclTable).
	    All packets transmitted or received on any of the virtual 
	    interfaces on this virtual router that satisfy that access 
	    list entry are acted upon by this filter."
	::= { csOrionVrPktFilterEntry 2 }

    csOrionVrPktFilterAction OBJECT-TYPE
	SYNTAX		INTEGER {
		permit	(1),
		deny	(2),
		firewall(3)
	}
	MAX-ACCESS	read-create
	STATUS		current
	DESCRIPTION
	    "The action performed by this filter."
	::= { csOrionVrPktFilterEntry 3 }

    csOrionVrPktFilterDirection OBJECT-TYPE
	SYNTAX		INTEGER {
		in	(1),
		out	(2)
	} 
	MAX-ACCESS	read-create
	STATUS		current
	DESCRIPTION
	    "The direction of packets on which this filter is applied."
	::= { csOrionVrPktFilterEntry 4 }
	
    csOrionVrPktFilterRowStatus OBJECT-TYPE
	SYNTAX		RowStatus
	MAX-ACCESS	read-create
	STATUS		current
	DESCRIPTION
	    "A row status type for this Table entry."
	::= { csOrionVrPktFilterEntry 5 }

	csOrionVrPktFilterTcpStatus OBJECT-TYPE
	SYNTAX		INTEGER {
		dontCare	(1),
		setup		(2),
		established	(3)
	} 
	MAX-ACCESS	read-create
	STATUS		current
	DESCRIPTION
	    "The state of the TCP."
	DEFVAL { dontCare }
	::= { csOrionVrPktFilterEntry 6 }

	csOrionVrPktFilterHitCounter OBJECT-TYPE
	SYNTAX  Integer32 (0..2147483647)
	MAX-ACCESS  read-only
	STATUS  current
	DESCRIPTION
	    "When csOrionVrPktFilterHitCounter is enabled, the counter be
		 incremented everytime a packet that corresponds to the
		 packet filter is received."
	DEFVAL { 0 }
	::= { csOrionVrPktFilterEntry 7 }

	csOrionVrPktFilterCounterStatus OBJECT-TYPE
	SYNTAX		INTEGER {
		enable	(1),
		disable	(2)
	} 
	MAX-ACCESS	read-create
	STATUS		current
	DESCRIPTION
	    "The status of csOrionVrPktFilterHitCounter. Will also be enabled
		 as a result of enabling csOrionVrPktFilterEvlogStatus."
	DEFVAL { disable }
	::= { csOrionVrPktFilterEntry 8 }

	csOrionVrPktFilterEvlogStatus OBJECT-TYPE
	SYNTAX		INTEGER {
		enable	(1),
		disable	(2)
	} 
	MAX-ACCESS	read-create
	STATUS		current
	DESCRIPTION
	    "If enabled, event logs will be sent when a packet hits this packet filter.
		 Will also result to csOrionVrPktFilterCounterStatus enabled."
	DEFVAL { disable }
	::= { csOrionVrPktFilterEntry 9 }


--
-- This table specifies a set of packet filters applied on a specific
-- virtual interface.
--

    csOrionViPktFilterTable OBJECT-TYPE
	SYNTAX	SEQUENCE OF CsOrionViPktFilterEntry
	MAX-ACCESS  not-accessible
	STATUS	current
	DESCRIPTION
	    "This table specifies a set of filters to be applied to
	    packets received over this virtual interface.  Filters can 
	    be configured either to permit a packet, deny a packet, or 
	    send the packet to a firewall proxy."
	::= { csOrionPktFilterInfo 2 }

    csOrionViPktFilterEntry OBJECT-TYPE
	SYNTAX 	 CsOrionViPktFilterEntry
	MAX-ACCESS  not-accessible
	STATUS	current
	DESCRIPTION
	    "Each filter specifies whether packets satisfying a specific
	    access list entry are permitted or denied to be passed along
	    their route."
	INDEX { csOrionGlobalVPNIndex, csOrionVPNVRouterIndex, csOrionVIfIndex,
		csOrionViPktFilterIndex }
	::= { csOrionViPktFilterTable 1 }

    CsOrionViPktFilterEntry ::=
	SEQUENCE {
	csOrionViPktFilterIndex
		Integer32,
	csOrionViPktFilterAclId
		Integer32,
	csOrionViPktFilterAction
		INTEGER,
	csOrionViPktFilterDirection
		INTEGER,
	csOrionViPktFilterRowStatus
		RowStatus,
	csOrionViPktFilterTcpStatus
		INTEGER,
	csOrionViPktFilterHitCounter
		Integer32,
	csOrionViPktFilterCounterStatus
		INTEGER,
	csOrionViPktFilterEvlogStatus
		INTEGER
	}

    csOrionViPktFilterIndex OBJECT-TYPE
	SYNTAX		Integer32 (1..2147483647)
	MAX-ACCESS	not-accessible
	STATUS		current
	DESCRIPTION
	    "The Index of this particular Packet Filter."
	::= { csOrionViPktFilterEntry 1 }

    csOrionViPktFilterAclId OBJECT-TYPE
	SYNTAX		Integer32 (0..65535)
	MAX-ACCESS	read-create
	STATUS		current
	DESCRIPTION
	    "The Id of an access list entry (from csOrionGenAclTable).
	    All packets transmitted or received on this virtual interface
	    that access list entry are acted upon by this filter."
	::= { csOrionViPktFilterEntry 2 }

    csOrionViPktFilterAction OBJECT-TYPE
	SYNTAX		INTEGER {
		permit	(1),
		deny	(2),
		firewall(3)
	}
	MAX-ACCESS	read-create
	STATUS		current
	DESCRIPTION
	    "The action performed by this filter."
	::= { csOrionViPktFilterEntry 3 }

    csOrionViPktFilterDirection OBJECT-TYPE
	SYNTAX		INTEGER {
		in	(1),
		out	(2)
	} 
	MAX-ACCESS	read-create
	STATUS		current
	DESCRIPTION
	    "The direction of packets on which this filter is applied."
	::= { csOrionViPktFilterEntry 4 }
	
    csOrionViPktFilterRowStatus OBJECT-TYPE
	SYNTAX		RowStatus
	MAX-ACCESS	read-create
	STATUS		current
	DESCRIPTION
	    "A row status type for this Table entry."
	::= { csOrionViPktFilterEntry 5 }

	csOrionViPktFilterTcpStatus OBJECT-TYPE
	SYNTAX		INTEGER {
		dontCare	(1),
		setup		(2),
		established	(3)
	} 
	MAX-ACCESS	read-create
	STATUS		current
	DESCRIPTION
	    "The state of the TCP."
	DEFVAL { dontCare }
	::= { csOrionViPktFilterEntry 6 }

	csOrionViPktFilterHitCounter OBJECT-TYPE
	SYNTAX  Integer32 (0..2147483647)
	MAX-ACCESS  read-only
	STATUS  current
	DESCRIPTION
	    "When csOrionViPktFilterHitCounter is enabled, the counter be
		 incremented everytime a packet that corresponds to the
		 packet filter is received."
	DEFVAL { 0 }
	::= { csOrionViPktFilterEntry 7 }

	csOrionViPktFilterCounterStatus OBJECT-TYPE
	SYNTAX		INTEGER {
		enable	(1),
		disable	(2)
	} 
	MAX-ACCESS	read-create
	STATUS		current
	DESCRIPTION
	    "The status of csOrionViPktFilterHitCounter. Will also be enabled
		 as a result of enabling csOrionViPktFilterEvlogStatus."
	DEFVAL { disable }
	::= { csOrionViPktFilterEntry 8 }

	csOrionViPktFilterEvlogStatus OBJECT-TYPE
	SYNTAX		INTEGER {
		enable	(1),
		disable	(2)
	} 
	MAX-ACCESS	read-create
	STATUS		current
	DESCRIPTION
	    "If enabled, event logs will be sent when a packet hits this packet filter.
		 Will also result to csOrionViPktFilterCounterStatus reset and enabled."
	DEFVAL { disable }
	::= { csOrionViPktFilterEntry 9 }


------------------------------------------------------------------------------
--
-- 		NAT Info 
--
------------------------------------------------------------------------------


    csOrionNatPoolTable OBJECT-TYPE
	SYNTAX	SEQUENCE OF CsOrionNatPoolEntry
	MAX-ACCESS  not-accessible
	STATUS	current
	DESCRIPTION
		"A list of Access List Entries."
	::= { csOrionNatInfo 1 }

   csOrionNatPoolEntry OBJECT-TYPE
	SYNTAX 	 CsOrionNatPoolEntry
	MAX-ACCESS  not-accessible
	STATUS	current
	DESCRIPTION
		"An entry containing filtering information used to
		classify packets."
	INDEX   { csOrionGlobalVPNIndex, csOrionVPNVRouterIndex,
		csOrionNatPoolId }
	::= { csOrionNatPoolTable 1 }

    CsOrionNatPoolEntry ::=
	SEQUENCE {
	csOrionNatPoolId 	
		Integer32,
 	csOrionNatPoolStartAddress
		IpAddress,
	csOrionNatPoolEndAddress
		IpAddress,
 	csOrionNatPoolStartPort
		Integer32,
	csOrionNatPoolEndPort
		Integer32,
	csOrionNatPoolStatus
		RowStatus
	}

    csOrionNatPoolId OBJECT-TYPE
	SYNTAX	Integer32  (1..65535)
	MAX-ACCESS  not-accessible
	STATUS	current
	DESCRIPTION
		"An identifier for this Nat Pool Entry."
	::= { csOrionNatPoolEntry 1 }

    csOrionNatPoolStartAddress OBJECT-TYPE
	SYNTAX	IpAddress 
	MAX-ACCESS  read-create
	STATUS	current
	DESCRIPTION
		""
	::= { csOrionNatPoolEntry 2 }

    csOrionNatPoolEndAddress OBJECT-TYPE
	SYNTAX	IpAddress 
	MAX-ACCESS  read-create
	STATUS	current
	DESCRIPTION
		""
	::= { csOrionNatPoolEntry 3 }

    csOrionNatPoolStartPort OBJECT-TYPE
	SYNTAX	Integer32 
	MAX-ACCESS  read-create
	STATUS	current
	DESCRIPTION
		""
	::= { csOrionNatPoolEntry 4 }

    csOrionNatPoolEndPort OBJECT-TYPE
	SYNTAX	Integer32 
	MAX-ACCESS  read-create
	STATUS	current
	DESCRIPTION
		""
	::= { csOrionNatPoolEntry 5 }

    csOrionNatPoolStatus OBJECT-TYPE
	SYNTAX	RowStatus 
	MAX-ACCESS  read-create
	STATUS	current
	DESCRIPTION
		""
	::= { csOrionNatPoolEntry 6 }


    csOrionNatTranslationTable OBJECT-TYPE
	SYNTAX	SEQUENCE OF CsOrionNatTranslationEntry
	MAX-ACCESS  not-accessible
	STATUS	current
	DESCRIPTION
		"This contains the NAT translation entries."
	::= { csOrionNatInfo 2 }

   csOrionNatTranslationEntry OBJECT-TYPE
	SYNTAX 	 CsOrionNatTranslationEntry
	MAX-ACCESS  not-accessible
	STATUS	current
	DESCRIPTION
		"An entry containing IP address, port and the protocol information corresponding to 
		a session."
	INDEX   { csOrionGlobalVPNIndex, csOrionVPNVRouterIndex, csOrionNatInsideLocalAddr,  csOrionNatInsideLocalPort,
			csOrionNatOutsideGlobalAddr, csOrionNatOutsideGlobalPort, csOrionNatProtocol}
	::= { csOrionNatTranslationTable 1 }


    CsOrionNatTranslationEntry ::=
	SEQUENCE {
	csOrionNatInsideLocalAddr 	
		IpAddress,
 	csOrionNatInsideLocalPort
		Integer32,
	csOrionNatOutsideGlobalAddr
		IpAddress,
 	csOrionNatOutsideGlobalPort
		Integer32,
	csOrionNatProtocol
		Integer32,
	csOrionNatInsideGlobalAddr 	
		IpAddress,
 	csOrionNatInsideGlobalPort
		Integer32
	}

    csOrionNatInsideLocalAddr OBJECT-TYPE
	SYNTAX	IpAddress  
	MAX-ACCESS  not-accessible
	STATUS	current
	DESCRIPTION
		""
	::= { csOrionNatTranslationEntry 1 }

    csOrionNatInsideLocalPort OBJECT-TYPE
	SYNTAX	Integer32 
	MAX-ACCESS  not-accessible
	STATUS	current
	DESCRIPTION
		""
	::= { csOrionNatTranslationEntry 2 }

    csOrionNatOutsideGlobalAddr OBJECT-TYPE
	SYNTAX	IpAddress 
	MAX-ACCESS  not-accessible
	STATUS	current
	DESCRIPTION
		""
	::= { csOrionNatTranslationEntry 3 }

    csOrionNatOutsideGlobalPort OBJECT-TYPE
	SYNTAX	Integer32 
	MAX-ACCESS  not-accessible
	STATUS	current
	DESCRIPTION
		""
	::= { csOrionNatTranslationEntry 4 }

    csOrionNatProtocol OBJECT-TYPE
	SYNTAX	Integer32 
	MAX-ACCESS  not-accessible
	STATUS	current
	DESCRIPTION
		""
	::= { csOrionNatTranslationEntry 5 }

    csOrionNatInsideGlobalAddr OBJECT-TYPE
	SYNTAX	IpAddress  
	MAX-ACCESS  read-only
	STATUS	current
	DESCRIPTION
		""
	::= { csOrionNatTranslationEntry 6 }

    csOrionNatInsideGlobalPort OBJECT-TYPE
	SYNTAX	Integer32 
	MAX-ACCESS  read-only
	STATUS	current
	DESCRIPTION
		""
	::= { csOrionNatTranslationEntry 7 }

 
    csOrionNatStaticTranslationTable OBJECT-TYPE
	SYNTAX	SEQUENCE OF CsOrionNatStaticTranslationEntry
	MAX-ACCESS  not-accessible
	STATUS	current
	DESCRIPTION
		""
	::= { csOrionNatInfo 3 }

   csOrionNatStaticTranslationEntry OBJECT-TYPE
	SYNTAX 	 CsOrionNatStaticTranslationEntry
	MAX-ACCESS  not-accessible
	STATUS	current
	DESCRIPTION
		""
	INDEX   { csOrionGlobalVPNIndex, csOrionVPNVRouterIndex, csOrionNatStaticInsideLocalAddress}
	::= { csOrionNatStaticTranslationTable 1 }

    CsOrionNatStaticTranslationEntry ::=
	SEQUENCE {
	csOrionNatStaticInsideLocalAddress 	
		IpAddress,
 	csOrionNatStaticInsideGlobalAddress
		IpAddress,
	csOrionNatStaticTranslationStatus
		RowStatus,
	csOrionNatStaticNetmask 
		IpAddress,
	csOrionNatStaticTranslationType	
		INTEGER
	}

    csOrionNatStaticInsideLocalAddress OBJECT-TYPE
	SYNTAX	IpAddress  
	MAX-ACCESS  not-accessible
	STATUS	current
	DESCRIPTION
		"An identifier for this Nat Pool Entry.
		The address as known in the private network."
	::= { csOrionNatStaticTranslationEntry 1 }

    csOrionNatStaticInsideGlobalAddress OBJECT-TYPE
	SYNTAX	IpAddress 
	MAX-ACCESS  read-create
	STATUS	current
	DESCRIPTION
		"The address as know in the outside world."
	::= { csOrionNatStaticTranslationEntry 2 }

    csOrionNatStaticTranslationStatus OBJECT-TYPE
	SYNTAX	RowStatus 
	MAX-ACCESS  read-create
	STATUS	current
	DESCRIPTION
		""
	::= { csOrionNatStaticTranslationEntry 3 }

	csOrionNatStaticNetmask OBJECT-TYPE
	SYNTAX	IpAddress 
	MAX-ACCESS  read-create
	STATUS	current
	DESCRIPTION
		"The network mask.
		 For one-to-one static NAT translation, mask should be zero."
	DEFVAL   { '00000000'H }    -- 0.0.0.0
	::= { csOrionNatStaticTranslationEntry 4 }

	csOrionNatStaticTranslationType OBJECT-TYPE
	SYNTAX		INTEGER {
		src		(1),
		dst		(2)
	}
	MAX-ACCESS	read-create
	STATUS		current
	DESCRIPTION
	    "Source address translation will be for outgoing packets and
		destination address translation will be for incoming packets."
	DEFVAL { src }
	::= { csOrionNatStaticTranslationEntry 5 }



	csOrionNatStaticVITranslationTable OBJECT-TYPE
	SYNTAX	SEQUENCE OF CsOrionNatStaticVITranslationEntry
	MAX-ACCESS  not-accessible
	STATUS	current
	DESCRIPTION
		""
	::= { csOrionNatInfo 4 }

   csOrionNatStaticVITranslationEntry OBJECT-TYPE
	SYNTAX 	 CsOrionNatStaticVITranslationEntry
	MAX-ACCESS  not-accessible
	STATUS	current
	DESCRIPTION
		""
	INDEX   { csOrionGlobalVPNIndex, csOrionVPNVRouterIndex,
			csOrionNatStaticIfIndex, csOrionNatStaticVIInsideLocalAddress}
	::= { csOrionNatStaticVITranslationTable 1 }

    CsOrionNatStaticVITranslationEntry ::=
	SEQUENCE {
	csOrionNatStaticIfIndex	
		Integer32,
	csOrionNatStaticVIInsideLocalAddress 	
		IpAddress,
 	csOrionNatStaticVIInsideGlobalAddress
		IpAddress,
	csOrionNatStaticVINetmask 
		IpAddress,
	csOrionNatStaticVITranslationType	
		INTEGER,
	csOrionNatStaticVITranslationStatus
		RowStatus
	}

	csOrionNatStaticIfIndex OBJECT-TYPE
	SYNTAX   Integer32
	MAX-ACCESS not-accessible
	STATUS   current
	DESCRIPTION
		"The VI where to apply the static NAT translation."
	::= { csOrionNatStaticVITranslationEntry 1 }

    csOrionNatStaticVIInsideLocalAddress OBJECT-TYPE
	SYNTAX	IpAddress  
	MAX-ACCESS  not-accessible
	STATUS	current
	DESCRIPTION
		"An identifier for this Nat Pool Entry.
		The address as known in the private network."
	::= { csOrionNatStaticVITranslationEntry 2 }

    csOrionNatStaticVIInsideGlobalAddress OBJECT-TYPE
	SYNTAX	IpAddress 
	MAX-ACCESS  read-create
	STATUS	current
	DESCRIPTION
		"The address as know in the outside world."
	::= { csOrionNatStaticVITranslationEntry 3 }

	csOrionNatStaticVINetmask OBJECT-TYPE
	SYNTAX	IpAddress 
	MAX-ACCESS  read-create
	STATUS	current
	DESCRIPTION
		"The network mask.
		 For one-to-one static NAT translation, mask should be zero."
	DEFVAL   { '00000000'H }    -- 0.0.0.0
	::= { csOrionNatStaticVITranslationEntry 4 }

	csOrionNatStaticVITranslationType OBJECT-TYPE
	SYNTAX		INTEGER {
		src		(1),
		dst		(2)
	}
	MAX-ACCESS	read-create
	STATUS		current
	DESCRIPTION
	    "Source address translation will be for outgoing packets and
		destination address translation will be for incoming packets."
	::= { csOrionNatStaticVITranslationEntry 5 }

	csOrionNatStaticVITranslationStatus OBJECT-TYPE
	SYNTAX	RowStatus 
	MAX-ACCESS  read-create
	STATUS	current
	DESCRIPTION
		""
	::= { csOrionNatStaticVITranslationEntry 6 }



------------------------------------------------------------------------------
--
--	        Ip Sec Info    
--
------------------------------------------------------------------------------

-- Transform Set Table

    csOrionIpSecTransformTable OBJECT-TYPE
	SYNTAX	SEQUENCE OF CsOrionIpSecTransformEntry
	MAX-ACCESS  not-accessible
	STATUS	current
	DESCRIPTION
		"A table for IPSEC transforms."
	::= { csOrionEncryptInfo 1 }

    csOrionIpSecTransformEntry OBJECT-TYPE
	SYNTAX 	 CsOrionIpSecTransformEntry
	MAX-ACCESS  not-accessible
	STATUS	current
	DESCRIPTION
		"Each entry contains a specific set of IPSEC Transforms
		for use by a Security Association."
	INDEX   { csOrionGlobalVPNIndex, csOrionVPNVRouterIndex, 
			csOrionIpSecTransformName }
	::= { csOrionIpSecTransformTable 1 }

    CsOrionIpSecTransformEntry ::=
	SEQUENCE {
	csOrionIpSecTransformName
 		DisplayString,
	csOrionIpSecTransform1
		DisplayString,
	csOrionIpSecTransform2
 		DisplayString,
	csOrionIpSecTransform3
 		DisplayString,
	csOrionIpSecTransformInitVector
		INTEGER,
	csOrionIpSecTransformMode
		INTEGER,
	csOrionIpSecTransformStatus
		RowStatus
	}

    csOrionIpSecTransformName OBJECT-TYPE
	SYNTAX	DisplayString (SIZE(0..80))
	MAX-ACCESS  not-accessible
	STATUS	current
	DESCRIPTION
		"An index for the IpSec Transform Set table."
	::= { csOrionIpSecTransformEntry 1 }

    csOrionIpSecTransform1 OBJECT-TYPE
	SYNTAX	DisplayString (SIZE(0..80))
	MAX-ACCESS  read-create
	STATUS	current
	DESCRIPTION
		"The first Transform in the IpSec Transform Set table."
	DEFVAL { "" }
	::= { csOrionIpSecTransformEntry 2 }

    csOrionIpSecTransform2 OBJECT-TYPE
	SYNTAX	DisplayString (SIZE(0..80))
	MAX-ACCESS  read-create
	STATUS	current
	DESCRIPTION
		"The second Transform in the IpSec Transform Set table.
		If no transform is specified, this object will have a
		zero length string."
	DEFVAL { "" }
	::= { csOrionIpSecTransformEntry 3 }

    csOrionIpSecTransform3 OBJECT-TYPE
	SYNTAX	DisplayString (SIZE(0..80))
	MAX-ACCESS  read-create
	STATUS	current
	DESCRIPTION
		"The third Transform in the IpSec Transform Set table.
		If no transform is specified, this object will have a
		zero length string."
	DEFVAL { "" }
	::= { csOrionIpSecTransformEntry 4 }

    csOrionIpSecTransformInitVector OBJECT-TYPE
	SYNTAX	 INTEGER
	{
		four	(4),
		eight	(8)
	}
	MAX-ACCESS  read-create
	STATUS	current
	DESCRIPTION
		"The size of the Initial Vector used by the IPSEC Transform
		Set."
	DEFVAL { eight }
	::= { csOrionIpSecTransformEntry 5 }

    csOrionIpSecTransformMode OBJECT-TYPE
	SYNTAX	 INTEGER
	{
		tunnel		(1),
		transport	(2)
	}
	MAX-ACCESS  read-create
	STATUS	current
	DESCRIPTION
		"The ipsec mode used by this IPSEC Transform Set."
	DEFVAL { tunnel }
	::= { csOrionIpSecTransformEntry 6 }

    csOrionIpSecTransformStatus OBJECT-TYPE
	SYNTAX		RowStatus 
	MAX-ACCESS	read-create
	STATUS		current
	DESCRIPTION
	       "A row status type for the IpSec Transform Table."
	::= { csOrionIpSecTransformEntry 7 }


-- Dynamic Crypto Map Table

    csOrionDynamicCryptoMapTable OBJECT-TYPE
	SYNTAX	SEQUENCE OF CsOrionDynamicCryptoMapEntry
	MAX-ACCESS  not-accessible
	STATUS	current
	DESCRIPTION
		"A table for Dynamic Crypto Map."
	::= { csOrionEncryptInfo 2 }

    csOrionDynamicCryptoMapEntry OBJECT-TYPE
	SYNTAX 	 CsOrionDynamicCryptoMapEntry
	MAX-ACCESS  not-accessible
	STATUS	current
	DESCRIPTION
		"Each entry contains a specific set of Dynamic Crypto Map
		for use by a Security Association."
	INDEX   { csOrionGlobalVPNIndex, csOrionVPNVRouterIndex, 
			csOrionDynamicCryptoMapName, csOrionDynamicCryptoMapNumber }
	::= { csOrionDynamicCryptoMapTable 1 }

    CsOrionDynamicCryptoMapEntry ::=
	SEQUENCE {
	csOrionDynamicCryptoMapName
 		DisplayString,
	csOrionDynamicCryptoMapNumber
		Integer32,
	csOrionDynamicCryptoMapMatchAddress
 		Integer32,
	csOrionDynamicCryptoMapPeer
 		IpAddress,
	csOrionDynamicCryptoMapTransformSet1
		DisplayString,
	csOrionDynamicCryptoMapTransformSet2
		DisplayString,
	csOrionDynamicCryptoMapTransformSet3
		DisplayString,
	csOrionDynamicCryptoMapTransformSet4
		DisplayString,
	csOrionDynamicCryptoMapTransformSet5
		DisplayString,
	csOrionDynamicCryptoMapTransformSet6
		DisplayString,
	csOrionDynamicCryptoMapSessionKeyLifetimeSec
		Integer32,
	csOrionDynamicCryptoMapSessionKeyLifetimeBytes
		Integer32,
	csOrionDynamicCryptoMapPfs
		INTEGER,
	csOrionDynamicCryptoMapStatus
		RowStatus
	}

    csOrionDynamicCryptoMapName OBJECT-TYPE
	SYNTAX	DisplayString (SIZE(0..80))
	MAX-ACCESS  not-accessible
	STATUS	current
	DESCRIPTION
		"An index for the Dynamic Crypto Map Table."
	::= { csOrionDynamicCryptoMapEntry 1 }

    csOrionDynamicCryptoMapNumber OBJECT-TYPE
	SYNTAX	Integer32
	MAX-ACCESS  not-accessible
	STATUS	current
	DESCRIPTION
		"An index for the Dynamic Crypto Map Table."
	::= { csOrionDynamicCryptoMapEntry 2 }

    csOrionDynamicCryptoMapMatchAddress OBJECT-TYPE
	SYNTAX	Integer32 (0..65535)
	MAX-ACCESS  read-create
	STATUS	current
	DESCRIPTION
		"Access List ID used by this Dynamic Crypto Map."
	::= { csOrionDynamicCryptoMapEntry 3 }

    csOrionDynamicCryptoMapPeer OBJECT-TYPE
	SYNTAX	IpAddress
	MAX-ACCESS  read-create
	STATUS	current
	DESCRIPTION
		"Peer Address for this Dynamic Crypto Map."
	::= { csOrionDynamicCryptoMapEntry 4 }

    csOrionDynamicCryptoMapTransformSet1 OBJECT-TYPE
	SYNTAX	DisplayString (SIZE(0..80))
	MAX-ACCESS  read-create
	STATUS	current
	DESCRIPTION
		"A transform set used by this Dynamic Crypto Map."
	::= { csOrionDynamicCryptoMapEntry 5 }

    csOrionDynamicCryptoMapTransformSet2 OBJECT-TYPE
	SYNTAX	DisplayString (SIZE(0..80))
	MAX-ACCESS  read-create
	STATUS	current
	DESCRIPTION
		"A transform set used by this Dynamic Crypto Map."
	::= { csOrionDynamicCryptoMapEntry 6 }

    csOrionDynamicCryptoMapTransformSet3 OBJECT-TYPE
	SYNTAX	DisplayString (SIZE(0..80))
	MAX-ACCESS  read-create
	STATUS	current
	DESCRIPTION
		"A transform set used by this Dynamic Crypto Map."
	::= { csOrionDynamicCryptoMapEntry 7 }

    csOrionDynamicCryptoMapTransformSet4 OBJECT-TYPE
	SYNTAX	DisplayString (SIZE(0..80))
	MAX-ACCESS  read-create
	STATUS	current
	DESCRIPTION
		"A transform set used by this Dynamic Crypto Map."
	::= { csOrionDynamicCryptoMapEntry 8 }

    csOrionDynamicCryptoMapTransformSet5 OBJECT-TYPE
	SYNTAX	DisplayString (SIZE(0..80))
	MAX-ACCESS  read-create
	STATUS	current
	DESCRIPTION
		"A transform set used by this Dynamic Crypto Map."
	::= { csOrionDynamicCryptoMapEntry 9 }

    csOrionDynamicCryptoMapTransformSet6 OBJECT-TYPE
	SYNTAX	DisplayString (SIZE(0..80))
	MAX-ACCESS  read-create
	STATUS	current
	DESCRIPTION
		"A transform set used by this Dynamic Crypto Map."
	::= { csOrionDynamicCryptoMapEntry 10 }

    csOrionDynamicCryptoMapSessionKeyLifetimeSec OBJECT-TYPE
	SYNTAX	Integer32
	MAX-ACCESS  read-create
	STATUS	current
	DESCRIPTION
		"A Session key lifetime in seconds used by this Dynamic Crypto Map."
	::= { csOrionDynamicCryptoMapEntry 11 }

    csOrionDynamicCryptoMapSessionKeyLifetimeBytes OBJECT-TYPE
	SYNTAX	Integer32
	MAX-ACCESS  read-create
	STATUS	current
	DESCRIPTION
		"A Session key lifetime in bytes used by this Dynamic Crypto Map."
	::= { csOrionDynamicCryptoMapEntry 12 }

    csOrionDynamicCryptoMapPfs OBJECT-TYPE
	SYNTAX	INTEGER
	{
			group1 (1),
			group2 (2),
			none   (3)
	}
	MAX-ACCESS  read-create
	STATUS	current
	DESCRIPTION
		"This object is used to request Perfect Forward Secrecy for 
		 this Dynamic Crypto Map."
	::= { csOrionDynamicCryptoMapEntry 13 }

    csOrionDynamicCryptoMapStatus OBJECT-TYPE
	SYNTAX	RowStatus
	MAX-ACCESS  read-create
	STATUS	current
	DESCRIPTION
		"A row status type for the Dynamic Crypto Map."
	::= { csOrionDynamicCryptoMapEntry 14 }



-- Manual Crypto Map Table

    csOrionManualCryptoMapTable OBJECT-TYPE
	SYNTAX	SEQUENCE OF CsOrionManualCryptoMapEntry
	MAX-ACCESS  not-accessible
	STATUS	current
	DESCRIPTION
		"A table for Manual Crypto Map."
	::= { csOrionEncryptInfo 3 }

    csOrionManualCryptoMapEntry OBJECT-TYPE
	SYNTAX 	 CsOrionManualCryptoMapEntry
	MAX-ACCESS  not-accessible
	STATUS	current
	DESCRIPTION
		"Each entry contains a specific set of Manual Crypto Map
		for use by a Security Association."
	INDEX   { csOrionGlobalVPNIndex, csOrionVPNVRouterIndex, 
			csOrionManualCryptoMapName, csOrionManualCryptoMapNumber }
	::= { csOrionManualCryptoMapTable 1 }

    CsOrionManualCryptoMapEntry ::=
	SEQUENCE {
	csOrionManualCryptoMapName
 		DisplayString,
	csOrionManualCryptoMapNumber
		Integer32,
	csOrionManualCryptoMapMatchAddress
 		Integer32,
	csOrionManualCryptoMapTransformSet
		DisplayString,
	csOrionManualCryptoMapInboundAHKey
		OCTET STRING,
	csOrionManualCryptoMapInboundAHSPI
		Integer32,
	csOrionManualCryptoMapOutboundAHKey
		OCTET STRING,
	csOrionManualCryptoMapOutboundAHSPI
		Integer32,
	csOrionManualCryptoMapInboundESPKey
		OCTET STRING,
	csOrionManualCryptoMapInboundESPSPI
		Integer32,
	csOrionManualCryptoMapInboundESPAuthKey
		OCTET STRING,
	csOrionManualCryptoMapOutboundESPKey
		OCTET STRING,
	csOrionManualCryptoMapOutboundESPSPI
		Integer32,
	csOrionManualCryptoMapOutboundESPAuthKey
		OCTET STRING,
	csOrionManualCryptoMapStatus
		RowStatus
	}

    csOrionManualCryptoMapName OBJECT-TYPE
	SYNTAX	DisplayString (SIZE(0..80))
	MAX-ACCESS  not-accessible
	STATUS	current
	DESCRIPTION
		"An index for the Manual Crypto Map Table."
	::= { csOrionManualCryptoMapEntry 1 }

    csOrionManualCryptoMapNumber OBJECT-TYPE
	SYNTAX	Integer32 (1..10000)
	MAX-ACCESS  not-accessible
	STATUS	current
	DESCRIPTION
		"An index for the Manual Crypto Map Table."
	::= { csOrionManualCryptoMapEntry 2 }

    csOrionManualCryptoMapMatchAddress OBJECT-TYPE
	SYNTAX	Integer32
	MAX-ACCESS  read-create
	STATUS	current
	DESCRIPTION
		"Access List ID used by this Manual Crypto Map."
	DEFVAL { 0 }
	::= { csOrionManualCryptoMapEntry 3 }

    csOrionManualCryptoMapTransformSet OBJECT-TYPE
	SYNTAX	DisplayString (SIZE(0..80))
	MAX-ACCESS  read-create
	STATUS	current
	DESCRIPTION
		"A transform set used by this Manual Crypto Map."
	DEFVAL { "" }
	::= { csOrionManualCryptoMapEntry 5 }

    csOrionManualCryptoMapInboundAHKey OBJECT-TYPE
	SYNTAX	OCTET STRING (SIZE (0..256))
	MAX-ACCESS  read-create
	STATUS	current
	DESCRIPTION
		"An inbound AH key used by this Manual Crypto Map."
	DEFVAL { "" }
	::= { csOrionManualCryptoMapEntry 6 }

    csOrionManualCryptoMapInboundAHSPI OBJECT-TYPE
	SYNTAX	Integer32
	MAX-ACCESS  read-create
	STATUS	current
	DESCRIPTION
		"An inbound AH SPI used by this Manual Crypto Map."
	DEFVAL { 0 }
	::= { csOrionManualCryptoMapEntry 7 }

    csOrionManualCryptoMapOutboundAHKey OBJECT-TYPE
	SYNTAX	OCTET STRING (SIZE (0..256))
	MAX-ACCESS  read-create
	STATUS	current
	DESCRIPTION
		"An outbound AH key used by this Manual Crypto Map."
	DEFVAL { "" }
	::= { csOrionManualCryptoMapEntry 8 }

    csOrionManualCryptoMapOutboundAHSPI OBJECT-TYPE
	SYNTAX	Integer32
	MAX-ACCESS  read-create
	STATUS	current
	DESCRIPTION
		"An outbound AH SPI used by this Manual Crypto Map."
	DEFVAL { 0 }
	::= { csOrionManualCryptoMapEntry 9 }

    csOrionManualCryptoMapInboundESPKey OBJECT-TYPE
	SYNTAX	OCTET STRING (SIZE (0..256))
	MAX-ACCESS  read-create
	STATUS	current
	DESCRIPTION
		"An inbound ESP key used by this Manual Crypto Map."
	DEFVAL { "" }
	::= { csOrionManualCryptoMapEntry 10 }

    csOrionManualCryptoMapInboundESPSPI OBJECT-TYPE
	SYNTAX	Integer32
	MAX-ACCESS  read-create
	STATUS	current
	DESCRIPTION
		"An inbound ESP SPI used by this Manual Crypto Map."
	DEFVAL { 0 }
	::= { csOrionManualCryptoMapEntry 11 }

    csOrionManualCryptoMapInboundESPAuthKey OBJECT-TYPE
	SYNTAX	OCTET STRING (SIZE (0..256))
	MAX-ACCESS  read-create
	STATUS	current
	DESCRIPTION
		"An inbound ESP authentication key used by this Manual Crypto Map."
	DEFVAL { "" }
	::= { csOrionManualCryptoMapEntry 12 }

    csOrionManualCryptoMapOutboundESPKey OBJECT-TYPE
	SYNTAX	OCTET STRING (SIZE (0..256))
	MAX-ACCESS  read-create
	STATUS	current
	DESCRIPTION
		"An outbound ESP key used by this Manual Crypto Map."
	DEFVAL { "" }
	::= { csOrionManualCryptoMapEntry 13 }

    csOrionManualCryptoMapOutboundESPSPI OBJECT-TYPE
	SYNTAX	Integer32
	MAX-ACCESS  read-create
	STATUS	current
	DESCRIPTION
		"An outbound ESP SPI used by this Manual Crypto Map."
	DEFVAL { 0 }
	::= { csOrionManualCryptoMapEntry 14 }

    csOrionManualCryptoMapOutboundESPAuthKey OBJECT-TYPE
	SYNTAX	OCTET STRING (SIZE (0..256))
	MAX-ACCESS  read-create
	STATUS	current
	DESCRIPTION
		"An outbound ESP authentication key used by this Manual Crypto Map."
	DEFVAL { "" }
	::= { csOrionManualCryptoMapEntry 15 }

    csOrionManualCryptoMapStatus OBJECT-TYPE
	SYNTAX	RowStatus
	MAX-ACCESS  read-create
	STATUS	current
	DESCRIPTION
		"A row status type for the Manual Crypto Map."
	::= { csOrionManualCryptoMapEntry 16 }

--
-- IKE Crypto Map Table
--

    csOrionIKECryptoMapTable OBJECT-TYPE
	SYNTAX	SEQUENCE OF CsOrionIKECryptoMapEntry
	MAX-ACCESS  not-accessible
	STATUS	current
	DESCRIPTION
		"A table for IKE Crypto Map."
	::= { csOrionEncryptInfo 4 }

    csOrionIKECryptoMapEntry OBJECT-TYPE
	SYNTAX 	 CsOrionIKECryptoMapEntry
	MAX-ACCESS  not-accessible
	STATUS	current
	DESCRIPTION
		"Each entry contains a specific set of IKE Crypto Map
		for use by a Security Association."
	INDEX   { csOrionGlobalVPNIndex, csOrionVPNVRouterIndex, 
			csOrionIKECryptoMapName, csOrionIKECryptoMapNumber }
	::= { csOrionIKECryptoMapTable 1 }

    CsOrionIKECryptoMapEntry ::=
	SEQUENCE {
	csOrionIKECryptoMapName
 		DisplayString,
	csOrionIKECryptoMapNumber
		Integer32,
	csOrionIKECryptoMapFlag
		Unsigned32,
	csOrionIKECryptoMapMatchAddress
 		Integer32,
	csOrionIKECryptoMapPfsGroup
		INTEGER,
	csOrionIKECryptoMapKey
		OCTET STRING,
	csOrionIKECryptoMapTransformSet1
		DisplayString,
	csOrionIKECryptoMapTransformSet2
		DisplayString,
	csOrionIKECryptoMapTransformSet3
		DisplayString,
	csOrionIKECryptoMapTransformSet4
		DisplayString,
	csOrionIKECryptoMapTransformSet5
		DisplayString,
	csOrionIKECryptoMapTransformSet6
		DisplayString,
	csOrionIKECryptoMapPolicy
		DisplayString,
	csOrionIKECryptoMapLocalIdentity
		LongDisplayString,
	csOrionIKECryptoMapSaLifetimeSoftSec
		Integer32,
	csOrionIKECryptoMapSaLifetimeSoftKbytes
		Integer32,
	csOrionIKECryptoMapSaLifetimeHardSec
		Integer32,
	csOrionIKECryptoMapSaLifetimeHardKbytes
		Integer32,
	csOrionIKECryptoMapStatus
		RowStatus,
	csOrionIKECryptoMapType
		INTEGER,
	csOrionIKECryptoMapIdleTimeout
		Integer32
	}

    csOrionIKECryptoMapName OBJECT-TYPE
	SYNTAX	DisplayString (SIZE(0..80))
	MAX-ACCESS  not-accessible
	STATUS	current
	DESCRIPTION
		"An index for the IKE Crypto Map Table."
	::= { csOrionIKECryptoMapEntry 1 }

    csOrionIKECryptoMapNumber OBJECT-TYPE
	SYNTAX	Integer32 (1..10000)
	MAX-ACCESS  not-accessible
	STATUS	current
	DESCRIPTION
		"An index for the IKE Crypto Map Table."
	::= { csOrionIKECryptoMapEntry 2 }

    csOrionIKECryptoMapFlag OBJECT-TYPE
	SYNTAX	Unsigned32
	MAX-ACCESS  read-create
	STATUS	current
	DESCRIPTION
		"Each bit within this object enables a specific feature
		within the Crypto Map.  Below is a list of the features
		and their corresponding bits identifiers.

			feature			bit
		------------------------------------------------------
			pfs                   0
			pfs-identify          1
			sa-per-net            5 -- note, sa-per-host & sa-per-net 
			sa-per-host           6 -- are mutually exclusive
			sa-per-protocol       7
			sa-per-port           8
			main-mode            10 -- main-mode and aggressive-mode
			aggressive-mode      11 -- are mutually exclusive
			copy-df              21
			dont-verify-padding  22
			always-plain         29
			passby               30
			deny                 31

		end of description.
		NOTE: default value varies depending on csOrionIKECryptoMapType.
		      'isakmp'       - default is 1056 (0x420  main-mode and sa-per-net)
			  'isakmpDialup' - default is 1088 (0x440  main-mode and sa-per-host)."
	::= { csOrionIKECryptoMapEntry 3 }

    csOrionIKECryptoMapMatchAddress OBJECT-TYPE
	SYNTAX	Integer32
	MAX-ACCESS  read-create
	STATUS	current
	DESCRIPTION
		"Access List ID used by this IKE Crypto Map."
	DEFVAL { 0 }
	::= { csOrionIKECryptoMapEntry 4 }

    csOrionIKECryptoMapPfsGroup OBJECT-TYPE
	SYNTAX	INTEGER
	{
			group1 (1),
			group2 (2),
			-- group3 (3),	group 3 & 4 not yet implemented
			-- group4 (4),
			group5 (5)
	}
	MAX-ACCESS  read-create
	STATUS	current
	DESCRIPTION
		"If one of the pfs features is enabled in 
		csOrionIKECryptoMapFlags, this object is used to identify
		the Diffie-Helman group used for this IKE Crypto Map."
	DEFVAL { group1 }
	::= { csOrionIKECryptoMapEntry 5 }

    csOrionIKECryptoMapKey OBJECT-TYPE
	SYNTAX  OCTET STRING (SIZE(0..255))
	MAX-ACCESS  read-create
	STATUS  current
	DESCRIPTION
		""
	DEFVAL { "" }
	::= { csOrionIKECryptoMapEntry 6 }

    csOrionIKECryptoMapTransformSet1 OBJECT-TYPE
	SYNTAX	DisplayString (SIZE(0..80))
	MAX-ACCESS  read-create
	STATUS	current
	DESCRIPTION
		"A transform set used by this IKE Crypto Map."
	DEFVAL { "" }
	::= { csOrionIKECryptoMapEntry 7 }

    csOrionIKECryptoMapTransformSet2 OBJECT-TYPE
	SYNTAX	DisplayString (SIZE(0..80))
	MAX-ACCESS  read-create
	STATUS	current
	DESCRIPTION
		"A transform set used by this IKE Crypto Map."
	DEFVAL { "" }
	::= { csOrionIKECryptoMapEntry 8 }

    csOrionIKECryptoMapTransformSet3 OBJECT-TYPE
	SYNTAX	DisplayString (SIZE(0..80))
	MAX-ACCESS  read-create
	STATUS	current
	DESCRIPTION
		"A transform set used by this IKE Crypto Map."
	DEFVAL { "" }
	::= { csOrionIKECryptoMapEntry 9 }

    csOrionIKECryptoMapTransformSet4 OBJECT-TYPE
	SYNTAX	DisplayString (SIZE(0..80))
	MAX-ACCESS  read-create
	STATUS	current
	DESCRIPTION
		"A transform set used by this IKE Crypto Map."
	DEFVAL { "" }
	::= { csOrionIKECryptoMapEntry 10 }

    csOrionIKECryptoMapTransformSet5 OBJECT-TYPE
	SYNTAX	DisplayString (SIZE(0..80))
	MAX-ACCESS  read-create
	STATUS	current
	DESCRIPTION
		"A transform set used by this IKE Crypto Map."
	DEFVAL { "" }
	::= { csOrionIKECryptoMapEntry 11 }

    csOrionIKECryptoMapTransformSet6 OBJECT-TYPE
	SYNTAX	DisplayString (SIZE(0..80))
	MAX-ACCESS  read-create
	STATUS	current
	DESCRIPTION
		"A transform set used by this IKE Crypto Map."
	DEFVAL { "" }
	::= { csOrionIKECryptoMapEntry 12 }

    csOrionIKECryptoMapPolicy OBJECT-TYPE
	SYNTAX	DisplayString (SIZE(0..80))
	MAX-ACCESS  read-create
	STATUS	current
	DESCRIPTION
		"The IKE Policy used by this Crypto Map.  This references
		an entry in csOrionIKEPolicyTable."
	DEFVAL { "" }
	::= { csOrionIKECryptoMapEntry 13 }

    csOrionIKECryptoMapLocalIdentity OBJECT-TYPE
	SYNTAX	LongDisplayString (SIZE(0..512))
	MAX-ACCESS  read-create
	STATUS	current
	DESCRIPTION
		"The Local IKE Identity for this Crypto Map entry.  This
		can be either a hostname or an IP address (in dotted
		decimal format)."
	DEFVAL { "" }
	::= { csOrionIKECryptoMapEntry 14 }

    csOrionIKECryptoMapSaLifetimeSoftSec OBJECT-TYPE
	SYNTAX	Integer32 (60..2147483647)
	MAX-ACCESS  read-create
	STATUS	deprecated
	DESCRIPTION
		"The soft rekey interval lifetime in seconds used by this IKE 
		Crypto Map Entry. This defines the period of time that 
		elapses between ISAKMP phase II rekeys.

		This object is deprecated because its value is derived from
		csOrionIKECryptoMapSaLifetimeHardSec and is really not
		negotiated."
	::= { csOrionIKECryptoMapEntry 15 }

    csOrionIKECryptoMapSaLifetimeSoftKbytes OBJECT-TYPE
	SYNTAX	Integer32 (256..2147483647)
	MAX-ACCESS  read-create
	STATUS	current
	DESCRIPTION
		"The soft rekey interval lifetime in kilobytes used by this 
		IKE Crypto Map Entry. This defines the maximum amount of data
		transferred between ISAKMP phase II rekeys.

		This object is deprecated because its value is derived from
		csOrionIKECryptoMapSaLifetimeHardKbytes and is really not
		negotiated."
	::= { csOrionIKECryptoMapEntry 16 }

    csOrionIKECryptoMapSaLifetimeHardSec OBJECT-TYPE
	SYNTAX	Integer32 (0 | 60..2147483647)
	MAX-ACCESS  read-create
	STATUS	current
	DESCRIPTION
		"The number of seconds that elapse before the SA is 
		completely deleted. If this occurs on an active connection,
		a new ISAKMP negotiation starting at phase I takes place
		and a new SA is initiated.

		0 is a special value and indicates that this particular 
		Lifetime parameter is not to be conveyed to the remote side 
		in any proposal that might be sent."
	DEFVAL { 28800 }
	::= { csOrionIKECryptoMapEntry 17 }

    csOrionIKECryptoMapSaLifetimeHardKbytes OBJECT-TYPE
	SYNTAX	Integer32 (0 | 256..2147483647)
	MAX-ACCESS  read-create
	STATUS	current
	DESCRIPTION
		"The number of kilobytes transferred before the SA is 
		completely deleted. 

		0 is a special value and indicates that this particular 
		Lifetime parameter is not to be conveyed to the remote side 
		in any proposal that might be sent."
	DEFVAL { 4096 }
	::= { csOrionIKECryptoMapEntry 18 }

    csOrionIKECryptoMapStatus OBJECT-TYPE
	SYNTAX	RowStatus
	MAX-ACCESS  read-create
	STATUS	current
	DESCRIPTION
		"A row status type for the IKE Crypto Map."
	::= { csOrionIKECryptoMapEntry 19 }

	csOrionIKECryptoMapType OBJECT-TYPE
	SYNTAX	INTEGER 
	{
		isakmp			(1),
		isakmpDialup	(2)
	}
	MAX-ACCESS  read-create
	STATUS	current
	DESCRIPTION
		"This object indicates if this IKE Crytomap is used as a regular
		 crytomap or for dial-up. Its value is only set during creation.
		 Therefore, it must not be modified once created."
	DEFVAL { isakmp }
	::= { csOrionIKECryptoMapEntry 20 }

	csOrionIKECryptoMapIdleTimeout OBJECT-TYPE
	SYNTAX	Integer32 (0 | 60..2147483647)
        UNITS    "seconds"
	MAX-ACCESS  read-create
	STATUS	current
	DESCRIPTION
		"The idle timeout in seconds of the dialup connection.
		 This will be used only when the csOrionIKECryptoMapType
		 is 'isakmpDialup' otherwise its value is zero.

		 Setting this object to 0 will turn the timer off. The
		 minimum valid timeout value for a dialup connection is
		 60, i.e., 1 minute."
	DEFVAL { 1800 }   -- 30 minutes
	::= { csOrionIKECryptoMapEntry 21 }

--
-- IKE Policy Table
--

    csOrionIKEPolicyTable OBJECT-TYPE
	SYNTAX	SEQUENCE OF CsOrionIKEPolicyEntry
	MAX-ACCESS  not-accessible
	STATUS	current
	DESCRIPTION
		"A table for IKE Crypto Map."
	::= { csOrionEncryptInfo 5 }

    csOrionIKEPolicyEntry OBJECT-TYPE
	SYNTAX 	 CsOrionIKEPolicyEntry
	MAX-ACCESS  not-accessible
	STATUS	current
	DESCRIPTION
		"Each entry contains a specific set of IKE Crypto Map
		for use by a Security Association."
	INDEX   { csOrionGlobalVPNIndex, csOrionVPNVRouterIndex, 
			csOrionIKEPolicyName, csOrionIKEPolicyPriority }
	::= { csOrionIKEPolicyTable 1 }

    CsOrionIKEPolicyEntry ::=
	SEQUENCE {
	csOrionIKEPolicyName
 		DisplayString,
	csOrionIKEPolicyPriority
		Integer32,
	csOrionIKEPolicyHash
		INTEGER,
	csOrionIKEPolicyEncryption
 		INTEGER,
	csOrionIKEPolicySaLifetimeSoftSec
		Integer32,
	csOrionIKEPolicySaLifetimeSoftKbytes
		Integer32,
	csOrionIKEPolicySaLifetimeHardSec
		Integer32,
	csOrionIKEPolicySaLifetimeHardKbytes
		Integer32,
	csOrionIKEPolicyAuthentication
		INTEGER,
	csOrionIKEPolicyPfsGroup
		INTEGER,
	csOrionIKEPolicyStatus
		RowStatus
	}

    csOrionIKEPolicyName OBJECT-TYPE
	SYNTAX  DisplayString (SIZE(0..80))
	MAX-ACCESS  not-accessible
	STATUS  current
	DESCRIPTION
		"The name assigned to this set of IKE Policies."
	::= { csOrionIKEPolicyEntry 1 }

    csOrionIKEPolicyPriority OBJECT-TYPE
	SYNTAX  Integer32 (1..10000)
	MAX-ACCESS  not-accessible
	STATUS  current
	DESCRIPTION
		"The priority assigned to this IKE Policy Entry."
	::= { csOrionIKEPolicyEntry 2 }

    csOrionIKEPolicyHash OBJECT-TYPE
	SYNTAX  INTEGER {
		hmacMd5		(1),
		hmacSha		(2)
	}
	MAX-ACCESS  read-create
	STATUS  current
	DESCRIPTION
		"The Hash algorithm employed by this IKE Policy Entry."
	DEFVAL { hmacSha }
	::= { csOrionIKEPolicyEntry 3 }

    csOrionIKEPolicyEncryption OBJECT-TYPE
	SYNTAX  INTEGER {
		desCbc		(1),
		tripleDesCbc	(2)
	}
	MAX-ACCESS  read-create
	STATUS  current
	DESCRIPTION
		"The Encryption algorithm employed by this IKE Policy Entry."
	DEFVAL { tripleDesCbc }
	::= { csOrionIKEPolicyEntry 4 }

    csOrionIKEPolicySaLifetimeSoftSec OBJECT-TYPE
	SYNTAX	Integer32 (60..2147483647)
	MAX-ACCESS  read-create
	STATUS	deprecated
	DESCRIPTION
                "The soft rekey interval lifetime in seconds used by this IKE
                Crypto Map Entry. This defines the period of time that
                elapses between ISAKMP phase II rekeys.

		This object is deprecated because its value is derived from
		csOrionIKEPolicySaLifetimeHardSec and is really not
		negotiated."
	::= { csOrionIKEPolicyEntry 5 }

    csOrionIKEPolicySaLifetimeSoftKbytes OBJECT-TYPE
	SYNTAX	Integer32 (256..2147483647)
	MAX-ACCESS  read-create
	STATUS	deprecated
	DESCRIPTION
                "The soft rekey interval lifetime in kilobytes used by this
                IKE Crypto Map Entry. This defines the maximum amount of data
                transferred between ISAKMP phase II rekeys.

		This object is deprecated because its value is derived from
		csOrionIKEPolicySaLifetimeHardKbytes and is really not
		negotiated."
	::= { csOrionIKEPolicyEntry 6 }

    csOrionIKEPolicySaLifetimeHardSec OBJECT-TYPE
	SYNTAX	Integer32 (0 | 60..2147483647)
	MAX-ACCESS  read-create
	STATUS	current
	DESCRIPTION
                "The number of seconds that elapse before the SA is
                completely deleted. If this occurs on an active connection,
                a new ISAKMP negotiation starting at phase I takes place
                and a new SA is initiated.

                0 is a special value and indicates that this particular
                Lifetime parameter is not to be conveyed to the remote side
                in any proposal that might be sent."
	DEFVAL { 10800 }
	::= { csOrionIKEPolicyEntry 7 }

    csOrionIKEPolicySaLifetimeHardKbytes OBJECT-TYPE
	SYNTAX	Integer32 (0 | 256..2147483647)
	MAX-ACCESS  read-create
	STATUS	current
	DESCRIPTION
                "The number of kilobytes transferred before the SA is
                completely deleted.

                0 is a special value and indicates that this particular
                Lifetime parameter is not to be conveyed to the remote side
                in any proposal that might be sent."
	DEFVAL { 4096 }
	::= { csOrionIKEPolicyEntry 8 }

    csOrionIKEPolicyAuthentication OBJECT-TYPE
	SYNTAX	INTEGER {
		preShare	(1),
		dssSig		(2),  
		rsaSig		(3),  
		methRsaEnc	(4),  -- not supported
		methRsaEncRev	(5),  -- not supported
		xauthInitPreShared (65001),
		xauthInitRsa	(65005)
	}
	MAX-ACCESS  read-create
	STATUS  current
	DESCRIPTION
		"The Authentication algorithm employed by this Policy entry."
	DEFVAL { rsaSig }
	::= { csOrionIKEPolicyEntry 9 }

    csOrionIKEPolicyPfsGroup OBJECT-TYPE
	SYNTAX	INTEGER
	{
			group1 (1),
			group2 (2),
			-- group3 (3),	group 3 & 4 not yet implemented
			-- group4 (4),
			group5 (5)
	}
	MAX-ACCESS  read-create
	STATUS	current
	DESCRIPTION
		"If one of the pfs features is enabled in 
		csOrionIKECryptoMapFlags, this object is used to identify
		the Diffie-Helman group used for this IKE Crypto Map."
	DEFVAL { group1 }
	::= { csOrionIKEPolicyEntry 10 }

    csOrionIKEPolicyStatus OBJECT-TYPE
	SYNTAX	RowStatus
	MAX-ACCESS  read-create
	STATUS	current
	DESCRIPTION
		"A row status type for the IKE Policy Entry."
	::= { csOrionIKEPolicyEntry 11 }

--
-- IKE Cert Table
--

    csOrionIKECertTable OBJECT-TYPE
	SYNTAX	SEQUENCE OF CsOrionIKECertEntry
	MAX-ACCESS  not-accessible
	STATUS	current
	DESCRIPTION
		"A table of Certificates."
	::= { csOrionEncryptInfo 6 }

    csOrionIKECertEntry OBJECT-TYPE
	SYNTAX 	 CsOrionIKECertEntry
	MAX-ACCESS  not-accessible
	STATUS	current
	DESCRIPTION
		"Each entry contains a specific certificate."
	INDEX   { csOrionGlobalVPNIndex, csOrionVPNVRouterIndex, 
			csOrionIKECertName, csOrionIKECertMapName }
	::= { csOrionIKECertTable 1 }

    CsOrionIKECertEntry ::=
	SEQUENCE {
	csOrionIKECertName
 		DisplayString,
	csOrionIKECertMapName
 		DisplayString,
	csOrionIKECertFlag
		Integer32,
	csOrionIKECertCertificate
		OCTET STRING,
	csOrionIKECertPrivateKey
		OCTET STRING,
	csOrionIKECertStatus
		RowStatus
	}

    csOrionIKECertName OBJECT-TYPE
	SYNTAX  DisplayString (SIZE(0..80))
	MAX-ACCESS  not-accessible
	STATUS  current
	DESCRIPTION
		"The name assigned to this set of IKE Certificates."
	::= { csOrionIKECertEntry 1 }

    csOrionIKECertMapName OBJECT-TYPE
	SYNTAX  DisplayString (SIZE(0..80))
	MAX-ACCESS  not-accessible
	STATUS  current
	DESCRIPTION
		"The IKE Crypto Map referred to by this Cert entry."
	::= { csOrionIKECertEntry 2 }

    csOrionIKECertFlag OBJECT-TYPE
	SYNTAX  Integer32 
	MAX-ACCESS  read-create
	STATUS  current
	DESCRIPTION
		"Each bit within this object enables a specific feature
		within the Cert Table.  Below is a list of the features
		and their corresponding bits identifiers.

			feature			bit
		------------------------------------------------------
			no-crl			0
		
		(more descriptions will follow)."
	DEFVAL { 1 }
	::= { csOrionIKECertEntry 3 }

    csOrionIKECertCertificate OBJECT-TYPE
	SYNTAX  OCTET STRING (SIZE(0..1500))
	MAX-ACCESS  read-create
	STATUS  current
	DESCRIPTION
		""
	DEFVAL { "" }
	::= { csOrionIKECertEntry 4 }

    csOrionIKECertPrivateKey OBJECT-TYPE
	SYNTAX  OCTET STRING (SIZE(0..1500))
	MAX-ACCESS  read-create
	STATUS  current
	DESCRIPTION
		""
	DEFVAL { "" }
	::= { csOrionIKECertEntry 5 }

    csOrionIKECertStatus OBJECT-TYPE
	SYNTAX	RowStatus
	MAX-ACCESS  read-create
	STATUS	current
	DESCRIPTION
		"A row status type for the IKE Cert Entry."
	::= { csOrionIKECertEntry 6 }


--
-- IKE Server Parameter Table in every VR
--

    csOrionIKESvrParamTable OBJECT-TYPE
	SYNTAX	SEQUENCE OF CsOrionIKESvrParamEntry
	MAX-ACCESS  not-accessible
	STATUS	current
	DESCRIPTION
		"A table of IKE Server Parameters in every VR."
	::= { csOrionEncryptInfo 7 }

    csOrionIKESvrParamEntry OBJECT-TYPE
	SYNTAX 	 CsOrionIKESvrParamEntry
	MAX-ACCESS  not-accessible
	STATUS	current
	DESCRIPTION
		"Each entry contains parameter settings of an IKE server."
	INDEX   { csOrionGlobalVPNIndex, csOrionVPNVRouterIndex, 
			csOrionIKESvrParamMapName }
	::= { csOrionIKESvrParamTable 1 }

    CsOrionIKESvrParamEntry ::=
	SEQUENCE {
	csOrionIKESvrParamMapName
 		DisplayString,
	csOrionIKESvrParamFlag
		Unsigned32,
	csOrionIKESvrParamIpAddress
		IpAddress,
	csOrionIKESvrParamPort
		Integer32,
	csOrionIKESvrParamRetryLimit
		Integer32,
	csOrionIKESvrParamRetryTimer
		Integer32,
	csOrionIKESvrParamRetryTimerMicroSec
		Integer32,
	csOrionIKESvrParamRetryTimerMaximum
		Integer32,
	csOrionIKESvrParamExpireTimer
		Integer32,
	csOrionIKESvrParamSecretRecreate
		Integer32,
	csOrionIKESvrParamSPISize
		Integer32,
	csOrionIKESvrParamMaxKeyLength
		Integer32,
	csOrionIKESvrParamMaxSACount
		Integer32,
	csOrionIKESvrParamLocalSecretSize
		Integer32,
	csOrionIKESvrParamTokenHashType
		INTEGER,
	csOrionIKESvrParamRowStatus
		RowStatus
	}

    csOrionIKESvrParamMapName OBJECT-TYPE
	SYNTAX  DisplayString (SIZE(0..80))
	MAX-ACCESS  not-accessible
	STATUS  current
	DESCRIPTION
		"The map name for this server."
	::= { csOrionIKESvrParamEntry 1 }

    csOrionIKESvrParamFlag OBJECT-TYPE
	SYNTAX  Unsigned32 
	MAX-ACCESS  read-create
	STATUS  current
	DESCRIPTION
		"Each bit within this object specifies the compatibility
		options that the server uses by default. Below is a list 
		of the features and their corresponding bits identifiers.

			options							bit
		------------------------------------------------------
			old-pk-encryption-prf-key		0
			old-payload-padding				1
			old-message-padding				2
			old-da-padding					3
			old-id-in-hash					4
			ignore-cert-request-payload		5
			old-cr-format					6
			use-zero-spi					7
		
		End of description."
	DEFVAL { 0 }  -- no option
	::= { csOrionIKESvrParamEntry 2 }

    csOrionIKESvrParamIpAddress OBJECT-TYPE
	SYNTAX  IpAddress
	MAX-ACCESS  read-create
	STATUS  current
	DESCRIPTION
		"The address of the IKE server."
	::= { csOrionIKESvrParamEntry 3 }

    csOrionIKESvrParamPort OBJECT-TYPE
	SYNTAX  Integer32
	MAX-ACCESS  read-create
	STATUS  current
	DESCRIPTION
		"The UDP port that the server is listening to."
	DEFVAL { 500 }
	::= { csOrionIKESvrParamEntry 4 }

	csOrionIKESvrParamRetryLimit OBJECT-TYPE
	SYNTAX  Integer32
	MAX-ACCESS  read-create
	STATUS  current
	DESCRIPTION
		"Limits the number of ISAKMP packet transmission retries.
		The server retries the transmission if it does not receive
		a response in csOrionIKESvrParamRetryTimer seconds."
	DEFVAL { 10 }
	::= { csOrionIKESvrParamEntry 5 }

	csOrionIKESvrParamRetryTimer OBJECT-TYPE
	SYNTAX  Integer32
	MAX-ACCESS  read-create
	STATUS  current
	DESCRIPTION
		"The amount of time, in seconds, that the server gives the
		remote end to reply to the sent request, before it will send
		the packet again. Fraction of a second must be specified in
		csOrionIKESvrParamRetryTimerMicroSec."
	DEFVAL { 1 }
	::= { csOrionIKESvrParamEntry 6 }

	csOrionIKESvrParamRetryTimerMicroSec OBJECT-TYPE
	SYNTAX  Integer32
	MAX-ACCESS  read-create
	STATUS  current
	DESCRIPTION
		"The microseconds part of csOrionIKESvrParamRetryTimer."
	DEFVAL { 200 }
	::= { csOrionIKESvrParamEntry 7 }

	csOrionIKESvrParamRetryTimerMaximum OBJECT-TYPE
	SYNTAX  Integer32
	MAX-ACCESS  read-create
	STATUS  current
	DESCRIPTION
		"Specifies the maximum value, in seconds, for the retry timer."
	DEFVAL { 30 }
	::= { csOrionIKESvrParamEntry 8 }

	csOrionIKESvrParamExpireTimer OBJECT-TYPE
	SYNTAX  Integer32
	MAX-ACCESS  read-create
	STATUS  current
	DESCRIPTION
		"Specifies the maximum time, in seconds, that the IKE server 
		allows a negotiation to continue."
	DEFVAL { 300 }
	::= { csOrionIKESvrParamEntry 9 }

	csOrionIKESvrParamSecretRecreate OBJECT-TYPE
	SYNTAX  Integer32
	MAX-ACCESS  read-create
	STATUS  current
	DESCRIPTION
		"A local secret recreation timer expressed in seconds."
	DEFVAL { 14400 }    -- 4 hours
	::= { csOrionIKESvrParamEntry 10 }

	csOrionIKESvrParamSPISize OBJECT-TYPE
	SYNTAX  Integer32
	MAX-ACCESS  read-create
	STATUS  current
	DESCRIPTION
		"A compatibility flag that specifies the number of bytes
		of zero that can be used when the security parameter index
		(SPI) of an ISAKMP security association is sent to the
		remote end."
	DEFVAL { 8 }
	::= { csOrionIKESvrParamEntry 11 }

	csOrionIKESvrParamMaxKeyLength OBJECT-TYPE
	SYNTAX  Integer32
	MAX-ACCESS  read-create
	STATUS  current
	DESCRIPTION
		"The maximum length of an encryption key, specified in bytes,
		that is accepted by the local end."
	DEFVAL { 64 }
	::= { csOrionIKESvrParamEntry 12 }

	csOrionIKESvrParamMaxSACount OBJECT-TYPE
	SYNTAX  Integer32
	MAX-ACCESS  read-create
	STATUS  current
	DESCRIPTION
		"Limits the maximum number of ISAKMP SA entries."
	DEFVAL { 512 }
	::= { csOrionIKESvrParamEntry 13 }

	csOrionIKESvrParamLocalSecretSize OBJECT-TYPE
	SYNTAX  Integer32
	MAX-ACCESS  read-create
	STATUS  current
	DESCRIPTION
		"The length of the local secrets, specified in bits."
	DEFVAL { 32 }
	::= { csOrionIKESvrParamEntry 14 }

	csOrionIKESvrParamTokenHashType OBJECT-TYPE
	SYNTAX  INTEGER {
		md5		(1),
		sha		(2)
	}
	MAX-ACCESS  read-create
	STATUS  current
	DESCRIPTION
		"A reference to an algorithm configuration block that
		defines the anti-clogging token hash algorithm."
	DEFVAL { md5 }
	::= { csOrionIKESvrParamEntry 15 }

    csOrionIKESvrParamRowStatus OBJECT-TYPE
	SYNTAX	RowStatus
	MAX-ACCESS  read-create
	STATUS	current
	DESCRIPTION
		"A row status type for the IKE Server."
	::= { csOrionIKESvrParamEntry 16 }


--
-- Event Logging Control Table for IPSEC/IKE
--

    csOrionIpSecEvLogTable OBJECT-TYPE
	SYNTAX	SEQUENCE OF CsOrionIpSecEvLogEntry
	MAX-ACCESS  not-accessible
	STATUS	obsolete
	DESCRIPTION
		"A table for Event Logging Control for IPSEC/IKE.
		NOTE: this table has been moved to {csOrionEncryptInfo 13} since it should be under VI level instead of VR level."
	::= { csOrionEncryptInfo 8 }

    csOrionIpSecEvLogEntry OBJECT-TYPE
	SYNTAX 	 CsOrionIpSecEvLogEntry
	MAX-ACCESS  not-accessible
	STATUS	obsolete
	DESCRIPTION
		"Each entry contains the event logging level
		and area for the IPSEC/IKE module on a
		virtual router."
	INDEX   { csOrionGlobalVPNIndex, csOrionVPNVRouterIndex }
	::= { csOrionIpSecEvLogTable 1 }

    CsOrionIpSecEvLogEntry ::=
	SEQUENCE {
	csOrionIpSecEvLogLevel
		EvLogLevel,
	csOrionIpSecEvLogArea
 		EvLogArea
	}

    csOrionIpSecEvLogLevel OBJECT-TYPE
        SYNTAX EvLogLevel
        MAX-ACCESS read-write
        STATUS     obsolete
        DESCRIPTION
               "This object is used to set the level of details for
                event logs for IPSEC/IKE. 
	       "
        DEFVAL { major }  -- only critical and major events will be logged
        ::= { csOrionIpSecEvLogEntry 1 }

    csOrionIpSecEvLogArea OBJECT-TYPE
        SYNTAX EvLogArea
        MAX-ACCESS read-write
        STATUS     obsolete
        DESCRIPTION
               "This object is used to set the area of event logs
                for IPSEC/IKE."
        DEFVAL { '00000040'h  }  -- bit 6, ipsec/ike area
        ::= { csOrionIpSecEvLogEntry 2 }


------------------------------------------------------------------------------
--
--	       IPSEC Statistics table 
--
------------------------------------------------------------------------------

    csOrionIpSecStatsTable OBJECT-TYPE
        SYNTAX  SEQUENCE OF CsOrionIpSecStatsEntry
        MAX-ACCESS  not-accessible
        STATUS  current
        DESCRIPTION
            "The IPSEC Statistics table."
        ::= {csOrionEncryptInfo 9 }

    csOrionIpSecStatsEntry OBJECT-TYPE
        SYNTAX   CsOrionIpSecStatsEntry
        MAX-ACCESS  not-accessible
        STATUS  current
        DESCRIPTION
           "An entry containing IPSEC statistics information for this 
			Virtual Interface."
        INDEX { csOrionGlobalVPNIndex, csOrionVPNVRouterIndex, csOrionVIfIndex }
        ::= { csOrionIpSecStatsTable 1 }

    CsOrionIpSecStatsEntry ::=
		SEQUENCE {
		csOrionIpSecStatsRcvAhPktsDropped
			Counter32,
		csOrionIpSecStatsRcvAhPktsBadAh
			Counter32,
		csOrionIpSecStatsRcvAhPktsBadSpi
			Counter32,
		csOrionIpSecStatsRcvEspPktsDropped
			Counter32,
		csOrionIpSecStatsRcvEspPktsBadEsp
			Counter32,
		csOrionIpSecStatsRcvPktsOk
			Counter32,
		csOrionIpSecStatsTxPktsDenied
			Counter32,
		csOrionIpSecStatsEspTotalInboundSAs
			Counter32,
		csOrionIpSecStatsEspTotalInboundSAsFailed
			Counter32,
		csOrionIpSecStatsEspCurrentInboundSAs
			Counter32,
		csOrionIpSecStatsEspTotalOutboundSAs
			Counter32,
		csOrionIpSecStatsEspTotalOutboundSAsFailed
			Counter32,
		csOrionIpSecStatsEspCurrentOutboundSAs
			Counter32,
		csOrionIpSecStatsAhTotalInboundSAs
			Counter32,
		csOrionIpSecStatsAhTotalInboundSAsFailed
			Counter32,
		csOrionIpSecStatsAhCurrentInboundSAs
			Counter32,
		csOrionIpSecStatsAhTotalOutboundSAs
			Counter32,
		csOrionIpSecStatsAhTotalOutboundSAsFailed
			Counter32,
		csOrionIpSecStatsAhCurrentOutboundSAs
			Counter32,
		csOrionIpSecStatsEspCryptoCepEstablishOk
			Counter32,
		csOrionIpSecStatsEspCryptoCepEstablishFailed
			Counter32,
		csOrionIpSecStatsAhCryptoCepEstablishOk
			Counter32,
		csOrionIpSecStatsAhCryptoCepEstablishFailed
			Counter32,
		csOrionIpSecStatsEspEncryptPktsOk
			Counter32,
		csOrionIpSecStatsEspDecryptPktsOk
			Counter32,
		csOrionIpSecStatsAhEncryptPktsOk
			Counter32,
		csOrionIpSecStatsAhDecryptPktsOk
			Counter32,
		csOrionIpSecStatsEspEncryptPktsBad
			Counter32,
		csOrionIpSecStatsEspDecryptPktsBad
			Counter32,
		csOrionIpSecStatsAhEncryptPktsBad
			Counter32,
		csOrionIpSecStatsAhDecryptPktsBad
			Counter32
	}

    csOrionIpSecStatsRcvAhPktsDropped OBJECT-TYPE
        SYNTAX  Counter32
        MAX-ACCESS  read-only
        STATUS  current
        DESCRIPTION
			"The number of dropped packets that were AH encrypted and 
 			 were received in this Virtual Interface."
        ::= { csOrionIpSecStatsEntry 1 }

    csOrionIpSecStatsRcvAhPktsBadAh OBJECT-TYPE
        SYNTAX  Counter32
        MAX-ACCESS  read-only
        STATUS  current
        DESCRIPTION
			"The number of bad AH packets that are AH encrypted and 
 			 are received in this Virtual Interface."
        ::= { csOrionIpSecStatsEntry 2 }

    csOrionIpSecStatsRcvAhPktsBadSpi OBJECT-TYPE
        SYNTAX  Counter32
        MAX-ACCESS  read-only
        STATUS  current
        DESCRIPTION
			"The number of bad SPI packets that are AH encrypted and 
 			 are received in this Virtual Interface."
        ::= { csOrionIpSecStatsEntry 3 }

    csOrionIpSecStatsRcvEspPktsDropped OBJECT-TYPE
        SYNTAX  Counter32
        MAX-ACCESS  read-only
        STATUS  current
        DESCRIPTION
			"The number of dropped packets that were ESP encrypted and 
 			 were received in this Virtual Interface."
        ::= { csOrionIpSecStatsEntry 4 }

    csOrionIpSecStatsRcvEspPktsBadEsp OBJECT-TYPE
        SYNTAX  Counter32
        MAX-ACCESS  read-only
        STATUS  current
        DESCRIPTION
			"The number of bad ESP packets that are ESP encrypted and 
 			 were received in this Virtual Interface."
        ::= { csOrionIpSecStatsEntry 5 }

    csOrionIpSecStatsRcvPktsOk OBJECT-TYPE
        SYNTAX  Counter32
        MAX-ACCESS  read-only
        STATUS  current
        DESCRIPTION
			"The number of good packets received in this Virtual 
			 Interface."
        ::= { csOrionIpSecStatsEntry 6 }

    csOrionIpSecStatsTxPktsDenied OBJECT-TYPE
        SYNTAX  Counter32
        MAX-ACCESS  read-only
        STATUS  current
        DESCRIPTION
			"The number of denied packets transmitted by this Virtual
			 Interface."
        ::= { csOrionIpSecStatsEntry 7 }

    csOrionIpSecStatsEspTotalInboundSAs OBJECT-TYPE
        SYNTAX  Counter32
        MAX-ACCESS  read-only
        STATUS  current
        DESCRIPTION
			"The total number of ESP encrypted inbound SAs for this 
			 Virtual Interface."
        ::= { csOrionIpSecStatsEntry 8 }

    csOrionIpSecStatsEspTotalInboundSAsFailed OBJECT-TYPE
        SYNTAX  Counter32
        MAX-ACCESS  read-only
        STATUS  current
        DESCRIPTION
			"The total number of failed ESP encrypted inbound SAs 
			 for this Virtual Interface."
        ::= { csOrionIpSecStatsEntry 9 }

    csOrionIpSecStatsEspCurrentInboundSAs OBJECT-TYPE
        SYNTAX  Counter32
        MAX-ACCESS  read-only
        STATUS  current
        DESCRIPTION
			"The current number of ESP encrypted inbound SAs for this 
			 Virtual Interface."
        ::= { csOrionIpSecStatsEntry 10 }

    csOrionIpSecStatsEspTotalOutboundSAs OBJECT-TYPE
        SYNTAX  Counter32
        MAX-ACCESS  read-only
        STATUS  current
        DESCRIPTION
			"The total number of ESP encrypted outbound SAs for this 
			 Virtual Interface."
        ::= { csOrionIpSecStatsEntry 11 }

    csOrionIpSecStatsEspTotalOutboundSAsFailed OBJECT-TYPE
        SYNTAX  Counter32
        MAX-ACCESS  read-only
        STATUS  current
        DESCRIPTION
			"The total number of failed ESP encrypted outbound SAs 
			 for this Virtual Interface."
        ::= { csOrionIpSecStatsEntry 12 }

    csOrionIpSecStatsEspCurrentOutboundSAs OBJECT-TYPE
        SYNTAX  Counter32
        MAX-ACCESS  read-only
        STATUS  current
        DESCRIPTION
 			"The current number of ESP encrypted outbound SAs for this 
			 Virtual Interface."
        ::= { csOrionIpSecStatsEntry 13 }

    csOrionIpSecStatsAhTotalInboundSAs OBJECT-TYPE
        SYNTAX  Counter32
        MAX-ACCESS  read-only
        STATUS  current
        DESCRIPTION
			"The total number of AH encrypted inbound SAs for this 
			 Virtual Interface."
        ::= { csOrionIpSecStatsEntry 14 }

    csOrionIpSecStatsAhTotalInboundSAsFailed OBJECT-TYPE
        SYNTAX  Counter32
        MAX-ACCESS  read-only
        STATUS  current
        DESCRIPTION
 			"The total number of failed AH encrypted inbound SAs 
			 for this Virtual Interface."
        ::= { csOrionIpSecStatsEntry 15 }

    csOrionIpSecStatsAhCurrentInboundSAs OBJECT-TYPE
        SYNTAX  Counter32
        MAX-ACCESS  read-only
        STATUS  current
        DESCRIPTION
			"The current number of AH encrypted inbound SAs for this 
			 Virtual Interface."
        ::= { csOrionIpSecStatsEntry 16 }

    csOrionIpSecStatsAhTotalOutboundSAs OBJECT-TYPE
        SYNTAX  Counter32
        MAX-ACCESS  read-only
        STATUS  current
        DESCRIPTION
			"The total number of AH encrypted outbound SAs for this 
			 Virtual Interface."
        ::= { csOrionIpSecStatsEntry 17 }

    csOrionIpSecStatsAhTotalOutboundSAsFailed OBJECT-TYPE
        SYNTAX  Counter32
        MAX-ACCESS  read-only
        STATUS  current
        DESCRIPTION
 			"The total number of failed AH encrypted outbound SAs 
			 for this Virtual Interface."
        ::= { csOrionIpSecStatsEntry 18 }

    csOrionIpSecStatsAhCurrentOutboundSAs OBJECT-TYPE
        SYNTAX  Counter32
        MAX-ACCESS  read-only
        STATUS  current
        DESCRIPTION
 			"The current number of AH encrypted outbound SAs for this 
			 Virtual Interface."
        ::= { csOrionIpSecStatsEntry 19 }

    csOrionIpSecStatsEspCryptoCepEstablishOk OBJECT-TYPE
        SYNTAX  Counter32
        MAX-ACCESS  read-only
        STATUS  current
        DESCRIPTION
			"The number of crypto ceps that are ESP encrypted 
 			 sucessfully established in this Virtual Interface."
        ::= { csOrionIpSecStatsEntry 20 }

    csOrionIpSecStatsEspCryptoCepEstablishFailed OBJECT-TYPE
        SYNTAX  Counter32
        MAX-ACCESS  read-only
        STATUS  current
        DESCRIPTION
			"The number of crypto ceps that are ESP encrypted 
 			 failed to establish in this Virtual Interface."
        ::= { csOrionIpSecStatsEntry 21 }

    csOrionIpSecStatsAhCryptoCepEstablishOk OBJECT-TYPE
        SYNTAX  Counter32
        MAX-ACCESS  read-only
        STATUS  current
        DESCRIPTION
			"The number of crypto ceps that are AH encrypted 
 			 sucessfully established in this Virtual Interface."
        ::= { csOrionIpSecStatsEntry 22 }

    csOrionIpSecStatsAhCryptoCepEstablishFailed OBJECT-TYPE
        SYNTAX  Counter32
        MAX-ACCESS  read-only
        STATUS  current
        DESCRIPTION
			"The number of crypto ceps that are AH encrypted 
 			 failed to establish in this Virtual Interface."
        ::= { csOrionIpSecStatsEntry 23 }

    csOrionIpSecStatsEspEncryptPktsOk OBJECT-TYPE
        SYNTAX  Counter32
        MAX-ACCESS  read-only
        STATUS  current
        DESCRIPTION
			"The number of good ESP encrypted packets in this
			 Virtual Interface."
        ::= { csOrionIpSecStatsEntry 24 }

    csOrionIpSecStatsEspDecryptPktsOk OBJECT-TYPE
        SYNTAX  Counter32
        MAX-ACCESS  read-only
        STATUS  current
        DESCRIPTION
 			"The number of good ESP decrypted packets in this
			 Virtual Interface."
        ::= { csOrionIpSecStatsEntry 25 }

    csOrionIpSecStatsAhEncryptPktsOk OBJECT-TYPE
        SYNTAX  Counter32
        MAX-ACCESS  read-only
        STATUS  current
        DESCRIPTION
 			"The number of good AH encrypted packets in this 
			 Virtual Interface."
        ::= { csOrionIpSecStatsEntry 26 }

    csOrionIpSecStatsAhDecryptPktsOk OBJECT-TYPE
        SYNTAX  Counter32
        MAX-ACCESS  read-only
        STATUS  current
        DESCRIPTION
 			"The number of good AH decrypted packets in this 
			 Virtual Interface."
        ::= { csOrionIpSecStatsEntry 27 }

    csOrionIpSecStatsEspEncryptPktsBad OBJECT-TYPE
        SYNTAX  Counter32
        MAX-ACCESS  read-only
        STATUS  current
        DESCRIPTION
			"The number of bad ESP encrypted packets in this 
			 Virtual Interface."
        ::= { csOrionIpSecStatsEntry 28 }

    csOrionIpSecStatsEspDecryptPktsBad OBJECT-TYPE
        SYNTAX  Counter32
        MAX-ACCESS  read-only
        STATUS  current
        DESCRIPTION
 			"The number of bad ESP decrypted packets in this 
			 Virtual Interface."
        ::= { csOrionIpSecStatsEntry 29 }

    csOrionIpSecStatsAhEncryptPktsBad OBJECT-TYPE
        SYNTAX  Counter32
        MAX-ACCESS  read-only
        STATUS  current
        DESCRIPTION
			"The number of bad AH encrypted packets in this 
			 Virtual Interface."
        ::= { csOrionIpSecStatsEntry 30 }

    csOrionIpSecStatsAhDecryptPktsBad OBJECT-TYPE
        SYNTAX  Counter32
        MAX-ACCESS  read-only
        STATUS  current
        DESCRIPTION
			"The number of bad AH decrypted packets in this 
			 Virtual Interface."
        ::= { csOrionIpSecStatsEntry 31 }

------------------------------------------------------------------------------
--
--	       		IKE Statistics table 
--
------------------------------------------------------------------------------
    csOrionIKEStatsTable OBJECT-TYPE
        SYNTAX  SEQUENCE OF CsOrionIKEStatsEntry
        MAX-ACCESS  not-accessible
        STATUS  current
        DESCRIPTION
            "The IKE Statistics table."
        ::= {csOrionEncryptInfo 10 }

    csOrionIKEStatsEntry OBJECT-TYPE
        SYNTAX   CsOrionIKEStatsEntry
        MAX-ACCESS  not-accessible
        STATUS  current
        DESCRIPTION
           "An entry containing IKE statistics information for this 
			Virtual Interface."
        INDEX { csOrionGlobalVPNIndex, csOrionVPNVRouterIndex, csOrionVIfIndex }
        ::= { csOrionIKEStatsTable 1 }

    CsOrionIKEStatsEntry ::=
		SEQUENCE {
		csOrionIKEStatsPhase1Negotiations
			Counter32,
		csOrionIKEStatsPhase1NegotiationsFailed
			Counter32,
		csOrionIKEStatsPhase1InPkts
			Counter32,
		csOrionIKEStatsPhase1InPktsRejected
			Counter32,
		csOrionIKEStatsPhase1OutPkts
			Counter32,
		csOrionIKEStatsPhase2Negotiations
			Counter32,
		csOrionIKEStatsPhase2NegotiationsFailed
			Counter32,
		csOrionIKEStatsPhase2InPkts
			Counter32,
		csOrionIKEStatsPhase2InPktsRejected
			Counter32,
		csOrionIKEStatsPhase2OutPkts
			Counter32
	}

    csOrionIKEStatsPhase1Negotiations OBJECT-TYPE
        SYNTAX  Counter32
        MAX-ACCESS  read-only
        STATUS  current
        DESCRIPTION
			"The number of IKE phase 1 negotiations in this 
			 Virtual Interface."
        ::= { csOrionIKEStatsEntry 1 }

    csOrionIKEStatsPhase1NegotiationsFailed OBJECT-TYPE
        SYNTAX  Counter32
        MAX-ACCESS  read-only
        STATUS  current
        DESCRIPTION
			"The number of Failed IKE phase 1 negotiations in this 
			 Virtual Interface."
        ::= { csOrionIKEStatsEntry 2 }

    csOrionIKEStatsPhase1InPkts OBJECT-TYPE
        SYNTAX  Counter32
        MAX-ACCESS  read-only
        STATUS  current
        DESCRIPTION
			"The number of IKE phase 1 packets received in this 
			 Virtual Interface."
        ::= { csOrionIKEStatsEntry 3 }

    csOrionIKEStatsPhase1InPktsRejected OBJECT-TYPE
        SYNTAX  Counter32
        MAX-ACCESS  read-only
        STATUS  current
        DESCRIPTION
			"The number of rejected IKE phase 1 packets received in this 
			 Virtual Interface."
        ::= { csOrionIKEStatsEntry 4 }

    csOrionIKEStatsPhase1OutPkts OBJECT-TYPE
        SYNTAX  Counter32
        MAX-ACCESS  read-only
        STATUS  current
        DESCRIPTION
			"The number of IKE phase 1 packets transmitted this 
			 Virtual Interface."
        ::= { csOrionIKEStatsEntry 5 }

    csOrionIKEStatsPhase2Negotiations OBJECT-TYPE
        SYNTAX  Counter32
        MAX-ACCESS  read-only
        STATUS  current
        DESCRIPTION
			"The number of IKE phase 2 negotiations in this 
			 Virtual Interface."
        ::= { csOrionIKEStatsEntry 6 }

    csOrionIKEStatsPhase2NegotiationsFailed OBJECT-TYPE
        SYNTAX  Counter32
        MAX-ACCESS  read-only
        STATUS  current
        DESCRIPTION
			"The number of Failed IKE phase 2 negotiations in this 
			 Virtual Interface."
        ::= { csOrionIKEStatsEntry 7 }

    csOrionIKEStatsPhase2InPkts OBJECT-TYPE
        SYNTAX  Counter32
        MAX-ACCESS  read-only
        STATUS  current
        DESCRIPTION
			"The number of IKE phase 2 packets received in this 
			 Virtual Interface."
        ::= { csOrionIKEStatsEntry 8 }

    csOrionIKEStatsPhase2InPktsRejected OBJECT-TYPE
        SYNTAX  Counter32
        MAX-ACCESS  read-only
        STATUS  current
        DESCRIPTION
			"The number of rejected IKE phase 2 packets received in this 
			 Virtual Interface."
        ::= { csOrionIKEStatsEntry 9 }

    csOrionIKEStatsPhase2OutPkts OBJECT-TYPE
        SYNTAX  Counter32
        MAX-ACCESS  read-only
        STATUS  current
        DESCRIPTION
			"The number of IKE phase 2 packets transmitted this 
			 Virtual Interface."
        ::= { csOrionIKEStatsEntry 10 }

------------------------------------------------------------------------------
--
--	       		IKE State table 
--
------------------------------------------------------------------------------
    csOrionIKEStateTable OBJECT-TYPE
        SYNTAX  SEQUENCE OF CsOrionIKEStateEntry
        MAX-ACCESS  not-accessible
        STATUS  current
        DESCRIPTION
            "The IKE State table."
        ::= {csOrionEncryptInfo 11 }

    csOrionIKEStateEntry OBJECT-TYPE
        SYNTAX   CsOrionIKEStateEntry
        MAX-ACCESS  not-accessible
        STATUS  current
        DESCRIPTION
           "An entry containing IKE state information for this 
			Virtual Interface."
        INDEX { csOrionGlobalVPNIndex, csOrionVPNVRouterIndex, csOrionVIfIndex,csOrionIKEStateSAIndex }
        ::= { csOrionIKEStateTable 1 }

    CsOrionIKEStateEntry ::=
		SEQUENCE {
		csOrionIKEStateSAIndex
			Integer32,	
		csOrionIKEStateLocalAddress
			IpAddress,
		csOrionIKEStateRemoteAddress
			IpAddress,
		csOrionIKEStateInitRespondFlag
			INTEGER,
		csOrionIKEStateAuthenticationType
			INTEGER,
		csOrionIKEStateCreationTime
			TimeStamp,
		csOrionIKEStateExpirationTime
			TimeStamp,
		csOrionIKEStateNegotiations
			Counter32,
		csOrionIKEStateLastUsed
			TimeStamp,
		csOrionIKEStateBytesTransferred
			Counter32,
		csOrionIKEStateCryptoAlgorithm
			DisplayString,
		csOrionIKEStateHashAlgorithm
			DisplayString,
		csOrionIKEStatePrfAlgorithm
			DisplayString,
		csOrionIKEStateRetryLimit
			Integer32,
		csOrionIKEStateRetryTimer
			Integer32,
		csOrionIKEStateRetryTimerMicroSec
			Integer32,
		csOrionIKEStateMaxRetryDuration
			Integer32,
		csOrionIKEStateMaxRetryDurationMicroSec
			Integer32
	}

    csOrionIKEStateSAIndex OBJECT-TYPE
	SYNTAX		Integer32 (1..16960)
	MAX-ACCESS	not-accessible
	STATUS		current
	DESCRIPTION
		"A unique value, greater than zero, for each SA. "
	DEFVAL { 512 }
	::= { csOrionIKEStateEntry 1 }

    csOrionIKEStateLocalAddress OBJECT-TYPE
 	SYNTAX	IpAddress 
 	MAX-ACCESS  read-only
	STATUS	current
	DESCRIPTION
		" The local IP address of this SA."
	::= { csOrionIKEStateEntry 2 }

    csOrionIKEStateRemoteAddress OBJECT-TYPE
 	SYNTAX	IpAddress 
 	MAX-ACCESS  read-only
	STATUS	current
	DESCRIPTION
		" The remote IP address of this SA."
	::= { csOrionIKEStateEntry 3 }

    csOrionIKEStateInitRespondFlag OBJECT-TYPE
 	SYNTAX	INTEGER { 
		initiator	(1),
		responder	(2)
	}
 	MAX-ACCESS  read-only
	STATUS	current
	DESCRIPTION
		" Indicates if this SA is an initiator or a responder."
	::= { csOrionIKEStateEntry 4 }

    csOrionIKEStateAuthenticationType OBJECT-TYPE
 	SYNTAX	INTEGER {
		pre-shared-key	(1),
		dss-signatures	(2),
		rsa-signatures	(3),	
		rsa-encryption  (4),
		rsa-encryption-revised (5),
		gss-api		(6),
		xauth-init-pre-shared (65001),
		xauth-resp-pre-shared (65002),
		xauth-init-dss (65003),
		xauth-resp-dss (65004),
		xauth-init-rsa (65005),
		xauth-resp-rsa (65006),
		xauth-init-rsa-encryption (65007),
		xauth-resp-rsa-encryption (65008),
		xauth-init-rsa-revised-encryption (65009),
		xauth-resp-rsa-revised-encryption (65010)
	}
 	MAX-ACCESS  read-only
	STATUS	current
	DESCRIPTION
		" The authentication type of this SA. It could be a certificate or
		  a pre-shared key."	
	::= { csOrionIKEStateEntry 5 }

    csOrionIKEStateCreationTime OBJECT-TYPE
 	SYNTAX	TimeStamp 
 	MAX-ACCESS  read-only
	STATUS	current
	DESCRIPTION
		" The creation time of this SA."
	::= { csOrionIKEStateEntry 6 }

    csOrionIKEStateExpirationTime OBJECT-TYPE
 	SYNTAX	TimeStamp 
 	MAX-ACCESS  read-only
	STATUS	current
	DESCRIPTION
		" The expiration time of this SA."
	::= { csOrionIKEStateEntry 7 }

    csOrionIKEStateNegotiations OBJECT-TYPE
 	SYNTAX	Counter32 
 	MAX-ACCESS  read-only
	STATUS	current
	DESCRIPTION
		" The number of phase 1 ISAKMP/IKE negotiations for this SA."
	::= { csOrionIKEStateEntry 8 }

    csOrionIKEStateLastUsed OBJECT-TYPE
 	SYNTAX	TimeStamp 
 	MAX-ACCESS  read-only
	STATUS	current
	DESCRIPTION
		" The last time this SA was used. "
	::= { csOrionIKEStateEntry 9 }

    csOrionIKEStateBytesTransferred OBJECT-TYPE
 	SYNTAX	Counter32 
 	MAX-ACCESS  read-only
	STATUS	current
	DESCRIPTION
		" The number of bytes transferred by this SA."
	::= { csOrionIKEStateEntry 10 }

    csOrionIKEStateCryptoAlgorithm OBJECT-TYPE
 	SYNTAX	DisplayString (SIZE(0..80)) 
 	MAX-ACCESS  read-only
	STATUS	current
	DESCRIPTION
		" The name of the crypto algorithm for this SA."
	::= { csOrionIKEStateEntry 11 }

    csOrionIKEStateHashAlgorithm OBJECT-TYPE
 	SYNTAX	DisplayString (SIZE(0..80)) 
 	MAX-ACCESS  read-only
	STATUS	current
	DESCRIPTION
		" The name of the hash algorithm for this SA."
	::= { csOrionIKEStateEntry 12 }

    csOrionIKEStatePrfAlgorithm OBJECT-TYPE
 	SYNTAX	DisplayString (SIZE(0..80)) 
 	MAX-ACCESS  read-only
	STATUS	current
	DESCRIPTION
		" The name of the PRF algorithm for this SA."
	::= { csOrionIKEStateEntry 13 }

    csOrionIKEStateRetryLimit OBJECT-TYPE
 	SYNTAX	Integer32 
 	MAX-ACCESS  read-only
	STATUS	current
	DESCRIPTION
		" The limit of retry counts for this SA."
	::= { csOrionIKEStateEntry 14 }

    csOrionIKEStateRetryTimer OBJECT-TYPE
 	SYNTAX	Integer32 
 	MAX-ACCESS  read-only
	STATUS	current
	DESCRIPTION
		" The retry interval in seconds. It indicates the duration 
		  from one retry to next retry for this SA. 
		  Fraction of a second must be specified in  
		  csOrionIKEStateRetryTimerMicroSec."
	::= { csOrionIKEStateEntry 15 }

    csOrionIKEStateRetryTimerMicroSec OBJECT-TYPE
 	SYNTAX	Integer32 
 	MAX-ACCESS  read-only
	STATUS	current
	DESCRIPTION
		" The micro-second part of csOrionIKEStateRetryTimer."
	::= { csOrionIKEStateEntry 16 }

    csOrionIKEStateMaxRetryDuration OBJECT-TYPE
 	SYNTAX	Integer32 
 	MAX-ACCESS  read-only
	STATUS	current
	DESCRIPTION
		" The maximum total retry duration for this SA.
                  Fraction of a second must be specified in
                  csOrionIKEStateMaxRetryDurationMicroSec."
	::= { csOrionIKEStateEntry 17 }

    csOrionIKEStateMaxRetryDurationMicroSec OBJECT-TYPE
 	SYNTAX	Integer32 
 	MAX-ACCESS  read-only
	STATUS	current
	DESCRIPTION
		" The micro-second part of  csOrionIKEStateMaxRetryDuration."
	::= { csOrionIKEStateEntry 18 }

--
-- IKE Dialup Connection Table
--

    csOrionIKEDialupConnTable OBJECT-TYPE
	SYNTAX	SEQUENCE OF CsOrionIKEDialupConnEntry
	MAX-ACCESS  not-accessible
	STATUS	current
	DESCRIPTION
		"A table of IKE dialup connection table."
	::= { csOrionEncryptInfo 12 }

    csOrionIKEDialupConnEntry OBJECT-TYPE
	SYNTAX 	 CsOrionIKEDialupConnEntry
	MAX-ACCESS  not-accessible
	STATUS	current
	DESCRIPTION
		"Each entry contains a specific IKE dialup connection."
	INDEX   { csOrionGlobalVPNIndex, csOrionVPNVRouterIndex, 
			csOrionVIfIndex, csOrionIKEDialupConnIndex }
	::= { csOrionIKEDialupConnTable 1 }

    CsOrionIKEDialupConnEntry ::=
	SEQUENCE {
	csOrionIKEDialupConnIndex
 		Integer32,
	csOrionIKEDialupConnRemIpAddress
 		IpAddress,
	csOrionIKEDialupConnUserId
		DisplayString,
	csOrionIKEDialupConnDistinguishName
		DisplayString,
	csOrionIKEDialupConnRowStatus
		INTEGER
	}

    csOrionIKEDialupConnIndex OBJECT-TYPE
	SYNTAX  Integer32 (1..4000)
	MAX-ACCESS  not-accessible
	STATUS  current
	DESCRIPTION
		"An index that uniquely identifies an entry in the IKE
		dialup connection table."
	::= { csOrionIKEDialupConnEntry 1 }

    csOrionIKEDialupConnRemIpAddress OBJECT-TYPE
	SYNTAX  IpAddress
	MAX-ACCESS  read-only
	STATUS  current
	DESCRIPTION
		"IP address of the remote IpSec tunnel."
	::= { csOrionIKEDialupConnEntry 2 }

    csOrionIKEDialupConnUserId OBJECT-TYPE
	SYNTAX  DisplayString (SIZE(0..64))
	MAX-ACCESS  read-only
	STATUS  current
	DESCRIPTION
		"Login ID of the dialup user, if the user uses Xauth. 
		If Xauth is skipped, this will be an empty string."
	::= { csOrionIKEDialupConnEntry 3 }

    csOrionIKEDialupConnDistinguishName OBJECT-TYPE
	SYNTAX  DisplayString
	MAX-ACCESS  read-only
	STATUS  current
	DESCRIPTION
		"X.509 Distinguish Name of the dialup user, if the user 
		uses certificates.
		For connection that does not use certificate, this
		will be an empty string."
	::= { csOrionIKEDialupConnEntry 4 }

    csOrionIKEDialupConnRowStatus OBJECT-TYPE
	SYNTAX  INTEGER {
		active (1),
		destroy (6)
	}
	MAX-ACCESS  read-write
	STATUS  current
	DESCRIPTION
		"This object allows for deletion of a connection if
		it is set to 'destroy'. 'active' is not a valid
		value to set.

		Get on this object will always yield 'active'."
	::= { csOrionIKEDialupConnEntry 5 }


--------------------------------------------------------------------------
--
--	       		IPSEC State table 
--
--------------------------------------------------------------------------
    csOrionIpSecStateTable OBJECT-TYPE
        SYNTAX  SEQUENCE OF CsOrionIpSecStateEntry
        MAX-ACCESS  not-accessible
        STATUS  current
        DESCRIPTION
            "The IPSEC State table."
        ::= {csOrionEncryptInfo 13 }

    csOrionIpSecStateEntry OBJECT-TYPE
        SYNTAX   CsOrionIpSecStateEntry
        MAX-ACCESS  not-accessible
        STATUS  current
        DESCRIPTION
           "An entry containing IPSEC state information for this 
			Virtual Interface."
        INDEX { csOrionGlobalVPNIndex, csOrionVPNVRouterIndex, csOrionVIfIndex, csOrionIpSecStateSAIndex }
        ::= { csOrionIpSecStateTable 1 }

    CsOrionIpSecStateEntry ::=
		SEQUENCE {
		csOrionIpSecStateSAIndex
			Integer32,	
		csOrionIpSecStateSpi
			Unsigned32,	
		csOrionIpSecStateSAFlag
			Integer32,
		csOrionIpSecStateProtocol
			INTEGER,
		csOrionIpSecStatePort
			Integer32,
		csOrionIpSecStateCreatorType
			INTEGER,
		csOrionIpSecStateRemoteGateway
			IpAddress,
		csOrionIpSecStateLocalGateway
			IpAddress,
		csOrionIpSecStateRemoteEndPoint
			IpAddress,
		csOrionIpSecStateLocalEndPoint
			IpAddress,
		csOrionIpSecStateAlgorithmType
			INTEGER,
		csOrionIpSecStateSAType
			INTEGER,
		csOrionIpSecStateExpire
			TimeStamp,
		csOrionIpSecStateLastUsed
			TimeStamp,
		csOrionIpSecStateDirection
			INTEGER,
		csOrionIpSecStateEncryptionAlgorithm
			DisplayString,
		csOrionIpSecStateHashAlgorithm
			DisplayString
	}

    csOrionIpSecStateSAIndex OBJECT-TYPE
	SYNTAX		Integer32 (1..16960)
	MAX-ACCESS	not-accessible
	STATUS		current
	DESCRIPTION
		"A unique value, greater than zero, for each SA. "
	DEFVAL { 512 }
	::= { csOrionIpSecStateEntry 1 }

    csOrionIpSecStateSpi OBJECT-TYPE
	SYNTAX		Unsigned32
	MAX-ACCESS	read-only
	STATUS		current
	DESCRIPTION
		"The SPI is an arbitray 32-bit value that, in combintation with the
		 destination IP address and security protocol(AH), uniquely 
		 identified the Security Association for this datagram. "
	::= { csOrionIpSecStateEntry 2 }

    csOrionIpSecStateSAFlag OBJECT-TYPE
 	SYNTAX	Integer32 
 	MAX-ACCESS  read-only
	STATUS	current
	DESCRIPTION
		" A flag Containing info regarding this SA. The value of
		  the flag is the combination of the following values:
			tunnel-only		(1),
			transport-only	(2),
			esp-rfc1827		(8),
			ah-rfc1826		(16),
			esp-rfc2045		(32),
			ah-rfc1828		(64),
			ah-rfc2202		(128)
	      Giving an example: the value 33 represents tunnel + esp-rfc2045"
	::= { csOrionIpSecStateEntry 3 }

    csOrionIpSecStateProtocol OBJECT-TYPE
 	SYNTAX	INTEGER  {
		none	(1),
		any		(255)
	}
 	MAX-ACCESS  read-only
	STATUS	current
	DESCRIPTION
		" The protocol being used by this SA. This value is 
		  connected to General Access list protocol. "
	::= { csOrionIpSecStateEntry 4 }

    csOrionIpSecStatePort OBJECT-TYPE
 	SYNTAX	Integer32 
 	MAX-ACCESS  read-only
	STATUS	current
	DESCRIPTION
		" The port number of the protocol; this value is connected
		  to General Access list port number. "
	::= { csOrionIpSecStateEntry 5 }

    csOrionIpSecStateCreatorType OBJECT-TYPE
 	SYNTAX	INTEGER {
		manual		(1),
		ike			(2),
		dial-in		(3)
	}
 	MAX-ACCESS  read-only
	STATUS	current
	DESCRIPTION
		" The creator type of this SA."
	::= { csOrionIpSecStateEntry 6 }

    csOrionIpSecStateRemoteGateway OBJECT-TYPE
 	SYNTAX	IpAddress 
 	MAX-ACCESS  read-only
	STATUS	current
	DESCRIPTION
		" The IP address of remote gateway."
	::= { csOrionIpSecStateEntry 7 }

    csOrionIpSecStateLocalGateway OBJECT-TYPE
 	SYNTAX	IpAddress 
 	MAX-ACCESS  read-only
	STATUS	current
	DESCRIPTION
		" The IP address of local gateway."
	::= { csOrionIpSecStateEntry 8 }

    csOrionIpSecStateRemoteEndPoint OBJECT-TYPE
 	SYNTAX	IpAddress 
 	MAX-ACCESS  read-only
	STATUS	current
	DESCRIPTION
		" The IP address of remote end point."
	::= { csOrionIpSecStateEntry 9 }

    csOrionIpSecStateLocalEndPoint OBJECT-TYPE
 	SYNTAX	IpAddress 
 	MAX-ACCESS  read-only
	STATUS	current
	DESCRIPTION
		" The IP address of local end point."
	::= { csOrionIpSecStateEntry 10 }

    csOrionIpSecStateAlgorithmType OBJECT-TYPE
 	SYNTAX	INTEGER {
		ah-rfc1828			(1),
		ah-hmac-rfc1828		(2),
		ah-md5-hmac			(3),
		ah-sha-hmac			(4),
		esp-des-rfc1829		(5),
		esp-3des-rfc1829	(6),	
		esp-des				(7),
		esp-3des			(8),
		esp-md5-hmac		(10),
		esp-sha-hmac		(11),
		esp3-md5-hmac		(12),
		esp3-sha-hmac		(13),
		other				(14)
	}
 	MAX-ACCESS  read-only
	STATUS	current
	DESCRIPTION
		" The algorithm type of this SA. " 
	::= { csOrionIpSecStateEntry 11 }

    csOrionIpSecStateSAType OBJECT-TYPE
 	SYNTAX	INTEGER {
		esp			(1),
		ah			(2),
		other		(3)
	}
 	MAX-ACCESS  read-only
	STATUS	current
	DESCRIPTION
		" The type of this SA. " 
	::= { csOrionIpSecStateEntry 12 }

    csOrionIpSecStateExpire OBJECT-TYPE
 	SYNTAX	TimeStamp 
 	MAX-ACCESS  read-only
	STATUS	current
	DESCRIPTION
		" Indicate when this SA will be dropped."
	::= { csOrionIpSecStateEntry 13 }

    csOrionIpSecStateLastUsed OBJECT-TYPE
 	SYNTAX	TimeStamp 
 	MAX-ACCESS  read-only
	STATUS	current
	DESCRIPTION
		" The last time this SA was used. "
	::= { csOrionIpSecStateEntry 14 }

    csOrionIpSecStateDirection OBJECT-TYPE
 	SYNTAX	INTEGER {
		ipsec-sa-send	(1),
		ipsec-sa-rcv	(2)
	}
 	MAX-ACCESS  read-only
	STATUS	current
	DESCRIPTION
		" The sending and receiving direction of this SA. " 
	::= { csOrionIpSecStateEntry 15 }

    csOrionIpSecStateEncryptionAlgorithm OBJECT-TYPE
 	SYNTAX	DisplayString (SIZE(0..80)) 
 	MAX-ACCESS  read-only
	STATUS	current
	DESCRIPTION
		" The name of the encryption algorithm for this SA."
	::= { csOrionIpSecStateEntry 16 }

    csOrionIpSecStateHashAlgorithm OBJECT-TYPE
 	SYNTAX	DisplayString (SIZE(0..80)) 
 	MAX-ACCESS  read-only
	STATUS	current
	DESCRIPTION
		" The name of the hash algorithm for this SA."
	::= { csOrionIpSecStateEntry 17 }

----------------------------------------------------------------
-- Event Logging Control Table for IPSEC/IKE
----------------------------------------------------------------

    csOrionIpSecEventLogTable OBJECT-TYPE
	SYNTAX	SEQUENCE OF CsOrionIpSecEventLogEntry
	MAX-ACCESS  not-accessible
	STATUS	current
	DESCRIPTION
		"A table for Event Logging Control for IPSEC/IKE."
	::= { csOrionEncryptInfo 14 }

    csOrionIpSecEventLogEntry OBJECT-TYPE
	SYNTAX 	 CsOrionIpSecEventLogEntry
	MAX-ACCESS  not-accessible
	STATUS	current
	DESCRIPTION
		"Each entry contains the event logging level
		and area for the IPSEC/IKE module on a
		virtual router."
	INDEX   { csOrionGlobalVPNIndex, csOrionVPNVRouterIndex, csOrionVIfIndex }
	::= { csOrionIpSecEventLogTable 1 }

    CsOrionIpSecEventLogEntry ::=
	SEQUENCE {
	csOrionIpSecEventLogLevel
		EvLogLevel,
	csOrionIpSecEventLogArea
 		EvLogArea
	}

    csOrionIpSecEventLogLevel OBJECT-TYPE
        SYNTAX EvLogLevel
        MAX-ACCESS read-write
        STATUS     current
        DESCRIPTION
               "This object is used to set the level of details for
                event logs for IPSEC/IKE. 
	       "
        DEFVAL { major }  -- only critical and major events will be logged
        ::= { csOrionIpSecEventLogEntry 1 }

    csOrionIpSecEventLogArea OBJECT-TYPE
        SYNTAX EvLogArea
        MAX-ACCESS read-write
        STATUS     current
        DESCRIPTION
               "This object is used to set the area of event logs
                for IPSEC/IKE."
        DEFVAL { '00000040'h  }  -- bit 6, ipsec/ike area
        ::= { csOrionIpSecEventLogEntry 2 }


------------------------------------------------------------------------------
--
--	       VPN Virtual Router NBNS Configuration
--
------------------------------------------------------------------------------

    csOrionVrNbnsConfigTable OBJECT-TYPE
	SYNTAX  SEQUENCE OF CsOrionVrNbnsConfigEntry
	MAX-ACCESS  not-accessible
	STATUS  current
	DESCRIPTION
		"This table contains NBNS configuration parameters."
    ::= { csOrionNBNSInfo 1 }

    csOrionVrNbnsConfigEntry OBJECT-TYPE
	SYNTAX CsOrionVrNbnsConfigEntry
	MAX-ACCESS not-accessible
	STATUS  current
	DESCRIPTION
		"Each entry represents the NBNS configuration parameters 
		for a single VR."
	INDEX   { csOrionGlobalVPNIndex, csOrionVPNVRouterIndex }
	::= { csOrionVrNbnsConfigTable 1 }

    CsOrionVrNbnsConfigEntry ::=
	SEQUENCE {
		csOrionVrPrimaryNbnsServer
			IpAddress,
		csOrionVrSecondaryNbnsServer
			IpAddress
	}

    csOrionVrPrimaryNbnsServer OBJECT-TYPE
	SYNTAX  IpAddress
	MAX-ACCESS  read-write
	STATUS  current
	DESCRIPTION
		"The primary NBNS server for this VR."
	::= { csOrionVrNbnsConfigEntry 1 }

    csOrionVrSecondaryNbnsServer OBJECT-TYPE
	SYNTAX  IpAddress
	MAX-ACCESS  read-write
	STATUS  current
	DESCRIPTION
		"The secondary NBNS server for this VR."
	::= { csOrionVrNbnsConfigEntry 2 }

------------------------------------------------------------------------------
--
--	       Queue Info
--
------------------------------------------------------------------------------

--
-- This table is used to define separate virtual network connection (vnc)
-- queues, each of which is allocated a specified amount of bandwidth.  
-- The packets which are placed in any particular vnc queue is determined 
-- by the access list Id's associated with the queue entry.
--

    csOrionVncQueueTable OBJECT-TYPE
	SYNTAX	SEQUENCE OF CsOrionVncQueueEntry
	MAX-ACCESS  not-accessible
	STATUS	current
	DESCRIPTION
	    "A list of VNC Queues for each Virtual Interfaces.  Each queue
	    is assigned a minimum and maximum bandwidth."
	::= { csOrionQueueInfo 1 }

    csOrionVncQueueEntry OBJECT-TYPE
	SYNTAX 	 CsOrionVncQueueEntry
	MAX-ACCESS  not-accessible
	STATUS	current
	DESCRIPTION
	    "An entry containing management information applicable
	    to a particular virtual interface's vnc queue."
	INDEX { csOrionGlobalVPNIndex, csOrionVPNVRouterIndex, csOrionVIfIndex,
		csOrionVncQueueId, csOrionVncQueueAclId }
	::= { csOrionVncQueueTable 1 }

    CsOrionVncQueueEntry ::=
	SEQUENCE {
	csOrionVncQueueId
		Integer32,
	csOrionVncQueueAclId
		Integer32,
	csOrionVncQueueMinBw
		Integer32,
	csOrionVncQueueMaxBw
		Integer32,
	csOrionVncQueueRowStatus
		RowStatus
	}

    csOrionVncQueueId OBJECT-TYPE
	SYNTAX		Integer32
	MAX-ACCESS	not-accessible
	STATUS		current
	DESCRIPTION
	    "The Id of this particular queue."
	::= { csOrionVncQueueEntry 1 }

    csOrionVncQueueAclId OBJECT-TYPE
	SYNTAX		Integer32
	MAX-ACCESS	not-accessible
	STATUS		current
	DESCRIPTION
	    "The Id of an access list entry (from csOrionGenAclTable).
	    All packets transmitted on this virtual that satisfy that 
	    access list entry are placed in this queue."
	::= { csOrionVncQueueEntry 2 }

    csOrionVncQueueMinBw OBJECT-TYPE
	SYNTAX		Integer32 
	MAX-ACCESS	read-create
	STATUS		current
	DESCRIPTION
	    "The minimum bandwidth allocated to this queue."
	::= { csOrionVncQueueEntry 3 }

    csOrionVncQueueMaxBw OBJECT-TYPE
	SYNTAX		Integer32 
	MAX-ACCESS	read-create
	STATUS		current
	DESCRIPTION
	    "The maximum bandwidth allocated to this queue."
	::= { csOrionVncQueueEntry 4 }
	
    csOrionVncQueueRowStatus OBJECT-TYPE
	SYNTAX		RowStatus
	MAX-ACCESS	read-create
	STATUS		current
	DESCRIPTION
	    "A row status type for this Rate Allocation Queue."
	::= { csOrionVncQueueEntry 5 }

------------------------------------------------------------------------------
--
--	       VPN Virtual Router PPP General Configuration Table
--
------------------------------------------------------------------------------

    csOrionPppConfigTable OBJECT-TYPE
	SYNTAX  SEQUENCE OF CsOrionPppConfigEntry
	MAX-ACCESS  not-accessible
	STATUS  current
	DESCRIPTION
		"This table contains general PPP configuration parameters."
    ::= { csOrionPppInfo 1 }

    csOrionPppConfigEntry OBJECT-TYPE
	SYNTAX CsOrionPppConfigEntry
	MAX-ACCESS not-accessible
	STATUS  current
	DESCRIPTION
		"Each entry represents the PPP configuration parameters
		for a single Virtual Router."
	INDEX   { csOrionGlobalVPNIndex, csOrionVPNVRouterIndex }
	::= { csOrionPppConfigTable 1 }

    CsOrionPppConfigEntry ::=
	SEQUENCE {
	       csOrionPppConfigHostname
			DisplayString
	}

    csOrionPppConfigHostname OBJECT-TYPE
	SYNTAX  DisplayString (SIZE(0..80))
	MAX-ACCESS  read-create
	STATUS  current
	DESCRIPTION
		"The name of this Virtual Router used during pap/chap
		authentication."
	::= { csOrionPppConfigEntry 1 }

------------------------------------------------------------------------------
--
--	       VPN Virtual Router PPP Interface Configuration Table
--
------------------------------------------------------------------------------

    csOrionPppIfConfigTable OBJECT-TYPE
	SYNTAX  SEQUENCE OF CsOrionPppIfConfigEntry
	MAX-ACCESS  not-accessible
	STATUS  current
	DESCRIPTION
		"This table contains interface-specific PPP configuration 
		parameters."
    ::= { csOrionPppInfo 2 }

    csOrionPppIfConfigEntry OBJECT-TYPE
	SYNTAX CsOrionPppIfConfigEntry
	MAX-ACCESS not-accessible
	STATUS  current
	DESCRIPTION
		"Each entry represents the PPP interface-specific 
		configuration parameters for a single Logical Interface."
	INDEX   { csOrionPppIfSlotIndex, csOrionPppIfPortIndex,
		  csOrionPppIfChIndex, csOrionPppIfSubIfIndex }
	::= { csOrionPppIfConfigTable 1 }

    CsOrionPppIfConfigEntry ::=
	SEQUENCE {
		csOrionPppIfSlotIndex
			Integer32,
		csOrionPppIfPortIndex
			Integer32,
		csOrionPppIfChIndex
			Integer32,
		csOrionPppIfSubIfIndex
			Integer32,
		csOrionPppIfConfigAuth
			INTEGER,
		csOrionPppIfEncryption
			INTEGER,
		csOrionPppIfEncryptionMode
			INTEGER,
		csOrionPppIfRetransmit
			Integer32,
		csOrionPppIfConfigReqRtx
			Integer32,
		csOrionPppIfTerminateReqRtx
			Integer32,
		csOrionPppIfTimeout
			Integer32,
		csOrionPppIfReauth
			Integer32,
		csOrionPppIfAdminStatus
			INTEGER,
		csOrionPppIfOperStatus
			OperStatus,
		csOrionPppIfEvLogLevel
			EvLogLevel,
		csOrionPppIfEvLogArea
			EvLogArea,
		csOrionPppIfEchoTimeout
			Integer32

	}

    csOrionPppIfSlotIndex OBJECT-TYPE
	SYNTAX  Integer32 (1..64)
	MAX-ACCESS  not-accessible
	STATUS  current
	DESCRIPTION
		"The Slot Id of this Logical Interface."
	::= { csOrionPppIfConfigEntry 1 }


    csOrionPppIfPortIndex OBJECT-TYPE
	SYNTAX  Integer32 (1..64)
	MAX-ACCESS  not-accessible
	STATUS  current
	DESCRIPTION
		"The Port Id of this Logical Interface."
	::= { csOrionPppIfConfigEntry 2 }


    csOrionPppIfChIndex OBJECT-TYPE
	SYNTAX  Integer32 (0..64)
	MAX-ACCESS  not-accessible
	STATUS  current
	DESCRIPTION
		"The Channel Id of this Logical Interface.
		Channel is 0 if this object is in the Unchannelized DS3/E3
		or ATM PVC."
	::= { csOrionPppIfConfigEntry 3 }

	csOrionPppIfSubIfIndex OBJECT-TYPE
	SYNTAX  Integer32 (0..2147483647)
	MAX-ACCESS  not-accessible
	STATUS  current
	DESCRIPTION
		"The identifier for this logical interface.  This
	     corresponds to the 'subinterface' entered via the CLI.
		 A sub-if 0 will be used for PPP objects other than in
		 PPP over ATM."
	::= { csOrionPppIfConfigEntry 4 }

    csOrionPppIfConfigAuth OBJECT-TYPE
	SYNTAX  INTEGER {
		none			(1),
		pap				(2),
		chapmd5			(3),
		mschapv1Server	(4)
	}
	MAX-ACCESS  read-write
	STATUS  current
	DESCRIPTION
		"The type of authentication used by PPP over this Logical
		Interface."
	DEFVAL { none }
	::= { csOrionPppIfConfigEntry 5 }

    csOrionPppIfEncryption OBJECT-TYPE
	SYNTAX  INTEGER {
		none	(1),
		weak	(2),
		strong	(3)
	}
	MAX-ACCESS  read-write
	STATUS  obsolete
	DESCRIPTION
		"NOTE: This object has been obsoleted."
	DEFVAL { none }
	::= { csOrionPppIfConfigEntry 6 }

    csOrionPppIfEncryptionMode OBJECT-TYPE
	SYNTAX  INTEGER {
		stateful	(1),
		stateless	(2)
	}
	MAX-ACCESS  read-write
	STATUS  obsolete
	DESCRIPTION
		"NOTE: This object has been obsoleted."
	DEFVAL { stateful }
	::= { csOrionPppIfConfigEntry 7 }

    csOrionPppIfRetransmit OBJECT-TYPE
	SYNTAX  Integer32 (1..64)
	MAX-ACCESS  read-write
	STATUS  obsolete
	DESCRIPTION
		"The maximum number of PPP retransmissions attempted on this
		Logical Interface."
	DEFVAL { 6 }
	::= { csOrionPppIfConfigEntry 8 }

    csOrionPppIfConfigReqRtx OBJECT-TYPE
	SYNTAX  Integer32 (0..64)
	MAX-ACCESS  read-write
	STATUS  current
	DESCRIPTION
		"The maximum number of PPP  configuration request 
		retransmissions attempted on this Logical Interface."
	DEFVAL { 10 }
	::= { csOrionPppIfConfigEntry 9 }

    csOrionPppIfTerminateReqRtx OBJECT-TYPE
	SYNTAX  Integer32 (0..64)
	MAX-ACCESS  read-write
	STATUS  current
	DESCRIPTION
		"The maximum number of PPP  terminate request 
		retransmissions attempted on this Logical Interface."
	DEFVAL { 2 }
	::= { csOrionPppIfConfigEntry 10 }

    csOrionPppIfTimeout OBJECT-TYPE
	SYNTAX  Integer32 (1..64)
	MAX-ACCESS  read-write
	STATUS  current
	DESCRIPTION
		"The amount of time (in seconds) between retransmit attempts
		on this Logical Interface."
	DEFVAL { 3 }
	::= { csOrionPppIfConfigEntry 11 }

    csOrionPppIfReauth OBJECT-TYPE
	SYNTAX  Integer32 (0..65535)
	MAX-ACCESS  read-write
	STATUS  current
	DESCRIPTION
		"The amount of time (in seconds) between re-authentication 
		requests on an established PPP connection on this Logical 
		Interface.  The value 0 disabled re-authentication."
	DEFVAL { 0 }
	::= { csOrionPppIfConfigEntry 12 }

    csOrionPppIfAdminStatus OBJECT-TYPE
	SYNTAX  INTEGER {
		enable  (1),
		disable (2)
	}
	MAX-ACCESS  read-write
	STATUS	current
	DESCRIPTION
	       "This object is used to enable/disable the PPP."
	DEFVAL { disable }
	::= { csOrionPppIfConfigEntry 13 }

	csOrionPppIfOperStatus OBJECT-TYPE
	SYNTAX  OperStatus
	MAX-ACCESS  read-only
	STATUS	current
	DESCRIPTION
	       "The operational status for this interface."
	::= { csOrionPppIfConfigEntry 14 }

	csOrionPppIfEvLogLevel OBJECT-TYPE
	SYNTAX  EvLogLevel
	MAX-ACCESS  read-write
	STATUS	current
	DESCRIPTION
               "This object is used to set the level of details for
                event logs for PPP. 

		Events with level higher than this object will not be
		logged.
	       "
        DEFVAL { major }  -- only critical and major events will be logged
	::= { csOrionPppIfConfigEntry 15 }

    csOrionPppIfEvLogArea OBJECT-TYPE
	SYNTAX  EvLogArea
	MAX-ACCESS  read-write
	STATUS	current
	DESCRIPTION
               "This object is used to set the area of event logs
                for PPP.

		Events which area is not specified in this object will
		not be logged."
        DEFVAL { '00000080'h  }  -- bit 7, link area
	::= { csOrionPppIfConfigEntry 16 }

	csOrionPppIfEchoTimeout OBJECT-TYPE
	SYNTAX	 Integer32(0..65535)
	MAX-ACCESS  read-write
	STATUS	current
	DESCRIPTION
		"The echo timeout (keepalive) in seconds."
	DEFVAL {10}
	::= { csOrionPppIfConfigEntry 17 }

------------------------------------------------------------------------------
--
--	       VPN Virtual Router PPP Remote Username/Password Table
--
------------------------------------------------------------------------------


    csOrionPppRemoteUserTable OBJECT-TYPE
	SYNTAX  SEQUENCE OF CsOrionPppRemoteUserEntry
	MAX-ACCESS  not-accessible
	STATUS  current
	DESCRIPTION
		"This table contains remote username/password pairs.  This
		database is used to authenticate remote users via PAP
		or CHAP."
    ::= { csOrionPppInfo 3 }

    csOrionPppRemoteUserEntry OBJECT-TYPE
	SYNTAX CsOrionPppRemoteUserEntry
	MAX-ACCESS not-accessible
	STATUS  current
	DESCRIPTION
		"Each entry represents a single username, password pair."
	INDEX   { csOrionGlobalVPNIndex, csOrionVPNVRouterIndex,
 		    csOrionPppRemoteUserName }
	::= { csOrionPppRemoteUserTable 1 }

    CsOrionPppRemoteUserEntry ::=
	SEQUENCE {
	       csOrionPppRemoteUserName
 			DisplayString,
	       csOrionPppRemoteUserPassword
			DisplayString,
	       csOrionPppRemoteUserRowStatus
 			RowStatus,
		   csOrionPppRemoteUserConnProfile
			DisplayString
	}

    csOrionPppRemoteUserName OBJECT-TYPE
	SYNTAX  DisplayString (SIZE(0..80))
	MAX-ACCESS  not-accessible
	STATUS  current
	DESCRIPTION
		"The name of a remote user."
	::= { csOrionPppRemoteUserEntry 1 }

    csOrionPppRemoteUserPassword OBJECT-TYPE
	SYNTAX  DisplayString (SIZE(0..80))
	MAX-ACCESS  read-create
	STATUS  current
	DESCRIPTION
		"The password of a remote user."
	DEFVAL { "" }
	::= { csOrionPppRemoteUserEntry 2 }

    csOrionPppRemoteUserRowStatus OBJECT-TYPE
	SYNTAX  RowStatus
	MAX-ACCESS  read-create
	STATUS  current
	DESCRIPTION
		"The RowStatus object for this table."
	::= { csOrionPppRemoteUserEntry 3 }

    csOrionPppRemoteUserConnProfile OBJECT-TYPE
	SYNTAX  DisplayString (SIZE(0..80))
	MAX-ACCESS  read-create
	STATUS  current
	DESCRIPTION
		"The connection profile for this user. 
		 Refer to csOrionConnectionProfileName object."
	DEFVAL { "" }
	::= { csOrionPppRemoteUserEntry 4 }

------------------------------------------------------------------------------
--
--	       VPN Virtual Router PPTP Configuration
--
------------------------------------------------------------------------------

    csOrionPptpConfTable OBJECT-TYPE
	SYNTAX  SEQUENCE OF CsOrionPptpConfEntry
	MAX-ACCESS  not-accessible
	STATUS  current
	DESCRIPTION
		"This table contains general Pptp Configuration parameters."
    ::= { csOrionPptpInfo 1 }

    csOrionPptpConfEntry OBJECT-TYPE
	SYNTAX CsOrionPptpConfEntry
	MAX-ACCESS not-accessible
	STATUS  current
	DESCRIPTION
		"Each entry represents a set of Pptp configuration for
		a single Virtual Router."
	INDEX   { csOrionGlobalVPNIndex, csOrionVPNVRouterIndex }
	::= { csOrionPptpConfTable 1 }

    CsOrionPptpConfEntry ::=
	SEQUENCE {
		csOrionPptpConfStatus
 			INTEGER,
		csOrionPptpConfMaxConn
			Integer32,
		csOrionPptpConfIdleTimeout
			Integer32,
		csOrionPptpConfEncryption
			INTEGER,
		csOrionPptpConfAuthentication
			INTEGER,
		csOrionPptpConfIpPool
			DisplayString
	}

    csOrionPptpConfStatus OBJECT-TYPE
	SYNTAX  INTEGER {
		enabled		(1),
		disabled	(2)
	}
	MAX-ACCESS  read-write
	STATUS  current
	DESCRIPTION
		"This object enables or disables the PPTP Server on this
		Virtual Router."
	DEFVAL { disabled }
	::= { csOrionPptpConfEntry 1 }

    csOrionPptpConfMaxConn OBJECT-TYPE
	SYNTAX  Integer32 (1..65535)
	MAX-ACCESS  read-write
	STATUS  current
	DESCRIPTION
		"The maximum number of simultaneous Pptp connections
		supported by this Virtual Router."
	::= { csOrionPptpConfEntry 2 }

    csOrionPptpConfIdleTimeout OBJECT-TYPE
	SYNTAX  Integer32 (0..65535)
	MAX-ACCESS  read-write
	STATUS  current
	DESCRIPTION
		"The amount of time the Pptp server allows a connection
		to remain idle. A value 0 would mean no timeout."
	DEFVAL { 300 }
	::= { csOrionPptpConfEntry 3 }

    csOrionPptpConfEncryption OBJECT-TYPE
	SYNTAX  INTEGER {
		none	(1),
		weak	(2),
		strong	(3)
	}
	MAX-ACCESS  read-write
	STATUS  current
	DESCRIPTION
		"The type of encryption used by PPTP Server on 
		this Virtual Router."
	DEFVAL { none }
	::= { csOrionPptpConfEntry 4 }

    csOrionPptpConfAuthentication OBJECT-TYPE
	SYNTAX  INTEGER {
		none			(1),
		pap				(2),
		chapmd5			(3),
		mschapv1Server	(4)
	}
	MAX-ACCESS  read-write
	STATUS  current
	DESCRIPTION
		"The type of authentication used by PPTP Server on 
		this Virtual Router."
	DEFVAL { none }
	::= { csOrionPptpConfEntry 5 }

    csOrionPptpConfIpPool OBJECT-TYPE
	SYNTAX  DisplayString (SIZE(0..80))
	MAX-ACCESS  read-write
	STATUS  current
	DESCRIPTION
		"This object identifies the Ip Local Address Pool that
		should be used by this PPTP Server to assign addresses
		to dynamic PPTP connections."
	DEFVAL { "" }
	::= { csOrionPptpConfEntry 6 }

------------------------------------------------------------------------------
--
--	       VPN Virtual Router PPTP Connection Table
--
------------------------------------------------------------------------------

    csOrionPptpConnTable OBJECT-TYPE
	SYNTAX  SEQUENCE OF CsOrionPptpConnEntry
	MAX-ACCESS  not-accessible
	STATUS  current
	DESCRIPTION
		"This table identifies all the current Pptp connections
		on this Virtual Router."
	::= { csOrionPptpInfo 2 }

    csOrionPptpConnEntry OBJECT-TYPE
	SYNTAX CsOrionPptpConnEntry
	MAX-ACCESS not-accessible
	STATUS  current
	DESCRIPTION
		"Each entry represents a single Pptp connection."
	INDEX   { csOrionGlobalVPNIndex, csOrionVPNVRouterIndex,
		  csOrionPptpConnFarIpAddr, csOrionPptpConnLocalIpAddr }
	::= { csOrionPptpConnTable 1 }

    CsOrionPptpConnEntry ::=
	SEQUENCE {
		csOrionPptpConnFarIpAddr
			IpAddress,
		csOrionPptpConnLocalIpAddr
			IpAddress,
		csOrionPptpConnAge
			Integer32,
		csOrionPptpConnStatus
			INTEGER,
		csOrionPptpConnFarUsername
			DisplayString
	}

    csOrionPptpConnFarIpAddr OBJECT-TYPE
	SYNTAX  IpAddress
	MAX-ACCESS  not-accessible
	STATUS  current
	DESCRIPTION
		"This object identifies the far end of a Pptp connection."
	::= { csOrionPptpConnEntry 1 }

    csOrionPptpConnLocalIpAddr OBJECT-TYPE
	SYNTAX  IpAddress
	MAX-ACCESS  not-accessible
	STATUS  current
	DESCRIPTION
		"This object identifies the local end of a Pptp connection."
	::= { csOrionPptpConnEntry 2 }

    csOrionPptpConnAge OBJECT-TYPE
	SYNTAX  Integer32 (1..65535)
	MAX-ACCESS  read-only
	STATUS  current
	DESCRIPTION
		"The age (in seconds) of this Pptp connection."
	::= { csOrionPptpConnEntry 3 }

    csOrionPptpConnStatus OBJECT-TYPE
	SYNTAX  INTEGER {
		enabled		(1),
		disabled	(2)
	}
	MAX-ACCESS  read-write
	STATUS  current
	DESCRIPTION
		"This object can be used to remove a Pptp connection by
		setting the value to disabled."
	::= { csOrionPptpConnEntry 4 }

    csOrionPptpConnFarUsername OBJECT-TYPE
	SYNTAX  DisplayString (SIZE(1..80))
	MAX-ACCESS  read-only
	STATUS  current
	DESCRIPTION
		"This is the username on the other end of the connection."
	::= { csOrionPptpConnEntry 5 }


------------------------------------------------------------------------------
--
--	       VPN Virtual Router Radius Configuration
--
------------------------------------------------------------------------------

    csOrionVrRadiusConfigTable OBJECT-TYPE
	SYNTAX  SEQUENCE OF CsOrionVrRadiusConfigEntry
	MAX-ACCESS  not-accessible
	STATUS  current
	DESCRIPTION
		"This table contains Radius configuration parameters."
    ::= { csOrionRadiusInfo 1 }

    csOrionVrRadiusConfigEntry OBJECT-TYPE
	SYNTAX CsOrionVrRadiusConfigEntry
	MAX-ACCESS not-accessible
	STATUS  current
	DESCRIPTION
		"Each entry represents the Radius configuration parameters 
		for a single VR."
	INDEX   { csOrionGlobalVPNIndex, csOrionVPNVRouterIndex }
	::= { csOrionVrRadiusConfigTable 1 }

    CsOrionVrRadiusConfigEntry ::=
	SEQUENCE {
		csOrionVrRadiusRetransmit
			Integer32,
		csOrionVrRadiusTimeout
			Integer32
	}

    csOrionVrRadiusRetransmit OBJECT-TYPE
	SYNTAX  Integer32 (0..64)
	MAX-ACCESS  read-write
	STATUS  current
	DESCRIPTION
		"The number of times a Radius Server will be queried before
		moving to the next Radius Server in the list identified by
		csOrionVrRadiusList."
	DEFVAL { 3 }
	::= { csOrionVrRadiusConfigEntry 1 }

    csOrionVrRadiusTimeout OBJECT-TYPE
	SYNTAX  Integer32 (1..128)
	MAX-ACCESS  read-write
	STATUS  current
	DESCRIPTION
		"The amount of time (in seconds) this Virtual Router will
		wait for a Radius Server before timing out."
	DEFVAL { 5 }
	::= { csOrionVrRadiusConfigEntry 2 }


------------------------------------------------------------------------------
--
--	       VPN Virtual Router RADIUS Authentication Server Table
--
------------------------------------------------------------------------------

    csOrionVrRadiusSvrTable OBJECT-TYPE
	SYNTAX	SEQUENCE OF CsOrionVrRadiusSvrEntry
	MAX-ACCESS  not-accessible
	STATUS	current
	DESCRIPTION
		"A list of RADIUS authentication servers."
	::= { csOrionRadiusInfo 2 }

    csOrionVrRadiusSvrEntry OBJECT-TYPE
	SYNTAX 	 CsOrionVrRadiusSvrEntry
	MAX-ACCESS  not-accessible
	STATUS	current
	DESCRIPTION
		"An entry containing management information applicable
		to a particular RADIUS Server."
	INDEX   { csOrionGlobalVPNIndex, csOrionVPNVRouterIndex,
			  csOrionVrRadiusSvrPriority }
	::= { csOrionVrRadiusSvrTable 1 }

    CsOrionVrRadiusSvrEntry ::=
	SEQUENCE {
		csOrionVrRadiusSvrPriority
			Integer32,
		csOrionVrRadiusSvrAddress
			IpAddress,
		csOrionVrRadiusSvrKey
			OCTET STRING,
		csOrionVrRadiusSvrRowStatus
			RowStatus,
		csOrionVrRadiusSvrOperStatus
			OperStatus,
		csOrionVrRadiusSvrPort
			Integer32
	}

    csOrionVrRadiusSvrPriority OBJECT-TYPE
	SYNTAX	Integer32 (1..100)
	MAX-ACCESS  not-accessible
	STATUS	current
	DESCRIPTION
		"The relative priority of this RADIUS server in this list."
	::= { csOrionVrRadiusSvrEntry 1 }

    csOrionVrRadiusSvrAddress OBJECT-TYPE
	SYNTAX	IpAddress
	MAX-ACCESS  read-create
	STATUS	current
	DESCRIPTION
		"The IP address of this RADIUS server in this list."
	::= { csOrionVrRadiusSvrEntry 2 }

    csOrionVrRadiusSvrKey OBJECT-TYPE
	SYNTAX		OCTET STRING (SIZE(0..255))
	MAX-ACCESS  read-create
	STATUS  current
	DESCRIPTION
		"The authentication and encryption key used for all Radius
		communication between the Virtual Router and this Radius
		Server."
	::= { csOrionVrRadiusSvrEntry 3 }

    csOrionVrRadiusSvrRowStatus OBJECT-TYPE
	SYNTAX		RowStatus 
	MAX-ACCESS	read-create
	STATUS		current
	DESCRIPTION
		"The Admin Status type for this entry in the Radius Server
		Table."
	::= {csOrionVrRadiusSvrEntry 4 }

    csOrionVrRadiusSvrOperStatus OBJECT-TYPE
	SYNTAX		OperStatus
	MAX-ACCESS	read-only
	STATUS		current
	DESCRIPTION
		"The operational status for this entry in the Radius Server
		Table."
	::= { csOrionVrRadiusSvrEntry 5 }

    csOrionVrRadiusSvrPort OBJECT-TYPE
	SYNTAX		Integer32 (0..65535)
	MAX-ACCESS	read-create
	STATUS		current
	DESCRIPTION
		"Radius client uses the default port 1812 for AA requests.
		This will not work with the old radius servers which uses
		1645 for AA requests. To support the old port, we throw in
		this extra parameter."
	DEFVAL		{ 1812 }
	::= { csOrionVrRadiusSvrEntry 6 }


------------------------------------------------------------------------------
--
--	       VPN Virtual Router RADIUS Accounting Server Table
--
------------------------------------------------------------------------------

    csOrionVrRadiusAcctSvrTable OBJECT-TYPE
	SYNTAX	SEQUENCE OF CsOrionVrRadiusAcctSvrEntry
	MAX-ACCESS  not-accessible
	STATUS	current
	DESCRIPTION
		"A list of RADIUS accounting servers."
	::= { csOrionRadiusInfo 3 }

    csOrionVrRadiusAcctSvrEntry OBJECT-TYPE
	SYNTAX 	 CsOrionVrRadiusAcctSvrEntry
	MAX-ACCESS  not-accessible
	STATUS	current
	DESCRIPTION
		"An entry containing management information applicable
		to a particular RADIUS Accounting Server."
	INDEX   { csOrionGlobalVPNIndex, csOrionVPNVRouterIndex,
			  csOrionVrRadiusAcctSvrPriority }
	::= { csOrionVrRadiusAcctSvrTable 1 }

    CsOrionVrRadiusAcctSvrEntry ::=
	SEQUENCE {
		csOrionVrRadiusAcctSvrPriority
			Integer32,
		csOrionVrRadiusAcctSvrAddress
			IpAddress,
		csOrionVrRadiusAcctSvrKey
			OCTET STRING,
		csOrionVrRadiusAcctSvrRowStatus
			RowStatus,
		csOrionVrRadiusAcctSvrOperStatus
			OperStatus,
		csOrionVrRadiusAcctSvrPort
			Integer32
	}

    csOrionVrRadiusAcctSvrPriority OBJECT-TYPE
	SYNTAX	Integer32 (1..100)
	MAX-ACCESS  not-accessible
	STATUS	current
	DESCRIPTION
		"The relative priority of this RADIUS accounting server in this list."
	::= { csOrionVrRadiusAcctSvrEntry 1 }

    csOrionVrRadiusAcctSvrAddress OBJECT-TYPE
	SYNTAX	IpAddress
	MAX-ACCESS  read-create
	STATUS	current
	DESCRIPTION
		"The IP address of this RADIUS accounting server in this list."
	::= { csOrionVrRadiusAcctSvrEntry 2 }

    csOrionVrRadiusAcctSvrKey OBJECT-TYPE
	SYNTAX		OCTET STRING (SIZE(0..255))
	MAX-ACCESS  read-create
	STATUS  current
	DESCRIPTION
		"The authentication and encryption key used for all Radius
		communication between the Virtual Router and this Radius
		Accounting Server."
	::= { csOrionVrRadiusAcctSvrEntry 3 }

    csOrionVrRadiusAcctSvrRowStatus OBJECT-TYPE
	SYNTAX		RowStatus 
	MAX-ACCESS	read-create
	STATUS		current
	DESCRIPTION
		"The Admin Status type for this entry in the Radius Accounting Server
		Table."
	::= {csOrionVrRadiusAcctSvrEntry 4 }

    csOrionVrRadiusAcctSvrOperStatus OBJECT-TYPE
	SYNTAX		OperStatus
	MAX-ACCESS	read-only
	STATUS		current
	DESCRIPTION
		"The operational status for this entry in the Radius Accounting Server
		Table."
	::= { csOrionVrRadiusAcctSvrEntry 5 }

    csOrionVrRadiusAcctSvrPort OBJECT-TYPE
        SYNTAX          Integer32 (0..65535)
        MAX-ACCESS      read-create
        STATUS          current
        DESCRIPTION
                "Radius client uses the default port 1813 for ACCT requests.
                This will not work with the old radius servers which uses
                1646 for ACCT requests. To support the old port, we throw in
                this extra parameter."
        DEFVAL          { 1813 }
        ::= { csOrionVrRadiusAcctSvrEntry 6 }


------------------------------------------------------------------------------
--
--        VPN Virtual Router's DHCP Relay Configuration
--
------------------------------------------------------------------------------

    csOrionVrDhcpRelayConfigTable OBJECT-TYPE
   SYNTAX  SEQUENCE OF CsOrionVrDhcpRelayConfigEntry
   MAX-ACCESS  not-accessible
   STATUS  current
   DESCRIPTION
      "This table contains DHCP Relay Agent configuration
       parameters."
    ::= { csOrionDHCPRelayInfo 1}

    csOrionVrDhcpRelayConfigEntry OBJECT-TYPE
   SYNTAX CsOrionVrDhcpRelayConfigEntry
   MAX-ACCESS not-accessible
   STATUS  current
   DESCRIPTION
      "Each entry represents the DHCP Relay configuration
       for a single VR."
   INDEX   { csOrionGlobalVPNIndex,csOrionVPNVRouterIndex }
   ::= { csOrionVrDhcpRelayConfigTable 1 }

    CsOrionVrDhcpRelayConfigEntry ::=
   SEQUENCE {
      csOrionVrDhcpRelayMaxHops
         Integer32,
      csOrionVrDhcpRelaySecsThreshold
         Integer32,
      csOrionVrDhcpRelayOperStatus
         OperStatus,
      csOrionVrDhcpRelayAdminStatus
         INTEGER
   }

    csOrionVrDhcpRelayMaxHops  OBJECT-TYPE
   SYNTAX  Integer32 (1..16)
	MAX-ACCESS read-create
   STATUS current
   DESCRIPTION
      "The upper limit for the 'hops' field of DHCP requests.
       Any request with a value exceeding this limit will be
       dropped by the relay agent."
   DEFVAL { 4 }
   ::= { csOrionVrDhcpRelayConfigEntry 1 }

	 csOrionVrDhcpRelaySecsThreshold OBJECT-TYPE
   SYNTAX  Integer32 (0..360)
   MAX-ACCESS read-create
   STATUS current
   DESCRIPTION
      "The threshold, in seconds, for the 'time elapsed' field
       of DHCP requests. This value is used to prioritize clients
       across the relay agent. The agent forwards only those
       requests that have a 'time elapsed' field value equal to or
       greater than the value set for this paramter."
   DEFVAL { 4 }
   ::= { csOrionVrDhcpRelayConfigEntry 2 }

	 csOrionVrDhcpRelayOperStatus OBJECT-TYPE
	SYNTAX  OperStatus
	MAX-ACCESS  read-only
	STATUS	current
	DESCRIPTION
	       "This object indicates the current operational status of
           the relay agent."
	::= { csOrionVrDhcpRelayConfigEntry 3 }

	 csOrionVrDhcpRelayAdminStatus OBJECT-TYPE
	SYNTAX  INTEGER {
      enabled  (1), -- enable DHCP packet forwarding.
      disabled (2)  -- stop the forwarding function.
   }
	MAX-ACCESS  read-create
	STATUS	current
	DESCRIPTION
	       "This object indicates the desired state of the DHCP
           relay agent. A relay agent, once enabled, requires
           at least one DHCP server address to forward packets
           to.
           
           If a list of servers has been configured, then
           all requests are forwarded to all servers -- no
           priority or precedence is applied."
   DEFVAL { disabled }
	::= { csOrionVrDhcpRelayConfigEntry 4 }

------------------------------------------------------------------------------
--
--	       DHCP Relay Server table 
--
------------------------------------------------------------------------------

    csOrionVrDhcpRelayServerTable  OBJECT-TYPE
   SYNTAX  SEQUENCE OF CsOrionVrDhcpRelayServerEntry
   MAX-ACCESS  not-accessible
   STATUS  current
   DESCRIPTION
      "This table contains the IP addresses of a list of DHCP
       servers to which the relay can forward the requests."
    ::= { csOrionDHCPRelayInfo 2}

    csOrionVrDhcpRelayServerEntry OBJECT-TYPE
   SYNTAX  CsOrionVrDhcpRelayServerEntry
	MAX-ACCESS not-accessible
   STATUS  current
   DESCRIPTION
      "Each entry contains a information about a single DHCP
       server -- an IP address, and, optionally, a name."
   INDEX { csOrionGlobalVPNIndex, csOrionVPNVRouterIndex,
           csOrionVrDhcpRelayServerAddress }
    ::= { csOrionVrDhcpRelayServerTable 1 }

	 CsOrionVrDhcpRelayServerEntry ::=
   SEQUENCE {
      csOrionVrDhcpRelayServerAddress
         IpAddress,
      csOrionVrDhcpRelayServerName
         DisplayString,
	   csOrionVrDhcpRelayServerRowStatus
         RowStatus
   }


    csOrionVrDhcpRelayServerAddress OBJECT-TYPE
   SYNTAX     IpAddress
   MAX-ACCESS read-create
   STATUS     current
   DESCRIPTION
      "The IP address of the DHCP server this entry corresponds to."
   ::= { csOrionVrDhcpRelayServerEntry 1 }

    csOrionVrDhcpRelayServerName   OBJECT-TYPE
   SYNTAX     DisplayString (SIZE(0..20))
   MAX-ACCESS read-create
   STATUS     current
   DESCRIPTION
      "The name of the the DHCP server this entry
       corresponds to."
   DEFVAL  {"" }
   ::= { csOrionVrDhcpRelayServerEntry 2 }

	 csOrionVrDhcpRelayServerRowStatus OBJECT-TYPE
   SYNTAX     RowStatus
   MAX-ACCESS read-create
   STATUS     current
   DESCRIPTION
      "The RowStatus object for this table entry."
   ::= { csOrionVrDhcpRelayServerEntry 3 }

------------------------------------------------------------------------------
--
--	       DHCP Relay Stats table 
--
------------------------------------------------------------------------------

    csOrionDhcpRelayStatsTable OBJECT-TYPE
	SYNTAX	SEQUENCE OF CsOrionDhcpRelayStatsEntry
	MAX-ACCESS  not-accessible
	STATUS	current
	DESCRIPTION
		"This table contains various statistics pertaining to the DHCP Relay
       Agent."
	::= { csOrionDHCPRelayInfo 3 }

    csOrionDhcpRelayStatsEntry OBJECT-TYPE
	SYNTAX 	 CsOrionDhcpRelayStatsEntry
	MAX-ACCESS  not-accessible
	STATUS	current
	DESCRIPTION
		"A Set of statistics for a single DHCP Relay Agent."
	INDEX { csOrionGlobalVPNIndex, csOrionVPNVRouterIndex}
	::= { csOrionDhcpRelayStatsTable 1 }

    CsOrionDhcpRelayStatsEntry ::=
	SEQUENCE {
	csOrionDhcpRelayInReqs
		Counter32,
	csOrionDhcpRelayInDiscs
		Counter32,
	csOrionDhcpRelayInRels
		Counter32,
	csOrionDhcpRelayInDecs
		Counter32,
	csOrionDhcpRelayInAcks
		Counter32,
	csOrionDhcpRelayInNaks
		Counter32,
	csOrionDhcpRelayInOffers
		Counter32,
	csOrionDhcpRelayOutReqs
	   Counter32,
	csOrionDhcpRelayOutDiscs
		Counter32,
	csOrionDhcpRelayOutRels
		Counter32,
	csOrionDhcpRelayOutDecs
		Counter32,
	csOrionDhcpRelayOutAcks
		Counter32,
	csOrionDhcpRelayOutNaks
		Counter32,
	csOrionDhcpRelayOutOffers
		Counter32
	}

    csOrionDhcpRelayInReqs OBJECT-TYPE
	SYNTAX  Counter32
	MAX-ACCESS  read-only
	STATUS  current
	DESCRIPTION
		"The total number of DHCP Request packets received."
	::= { csOrionDhcpRelayStatsEntry 1 }

    csOrionDhcpRelayInDiscs OBJECT-TYPE
	SYNTAX  Counter32
	MAX-ACCESS  read-only
	STATUS  current
	DESCRIPTION
		"The total number of DHCP Discover packets received."
	::= { csOrionDhcpRelayStatsEntry 2 }

    csOrionDhcpRelayInRels OBJECT-TYPE
	SYNTAX	Counter32
	MAX-ACCESS  read-only
	STATUS	current
	DESCRIPTION
		"The total number of DHCP Release packets received."
	::= { csOrionDhcpRelayStatsEntry 3 }

    csOrionDhcpRelayInDecs OBJECT-TYPE
	SYNTAX  Counter32
	MAX-ACCESS  read-only
	STATUS  current
	DESCRIPTION
		"The total number of DHCP Decline packets received."
	::= { csOrionDhcpRelayStatsEntry 4 }

    csOrionDhcpRelayInAcks OBJECT-TYPE
	SYNTAX  Counter32
	MAX-ACCESS  read-only
	STATUS  current
	DESCRIPTION
		"The tatal number of DHCP Ack packets received."
	::= { csOrionDhcpRelayStatsEntry 5 }

    csOrionDhcpRelayInNaks OBJECT-TYPE
	SYNTAX  Counter32
	MAX-ACCESS  read-only
	STATUS  current
	DESCRIPTION
		"The total number of DHCP Nak packets received."
	::= { csOrionDhcpRelayStatsEntry 6 }

    csOrionDhcpRelayInOffers OBJECT-TYPE
	SYNTAX  Counter32
	MAX-ACCESS  read-only
	STATUS  current
	DESCRIPTION
		"The total number of DHCP Offer packets received."
	::= { csOrionDhcpRelayStatsEntry 7 }

    csOrionDhcpRelayOutReqs OBJECT-TYPE
	SYNTAX  Counter32
	MAX-ACCESS  read-only
	STATUS  current
	DESCRIPTION
		"The total number of DHCP Request packets forwarded."
	::= { csOrionDhcpRelayStatsEntry 8 }

    csOrionDhcpRelayOutDiscs OBJECT-TYPE
	SYNTAX  Counter32
	MAX-ACCESS  read-only
	STATUS  current
	DESCRIPTION
		"The total number of DHCP Discover packets forwarded."
	::= { csOrionDhcpRelayStatsEntry 9 }

    csOrionDhcpRelayOutRels OBJECT-TYPE
	SYNTAX	Counter32
	MAX-ACCESS  read-only
	STATUS	current
	DESCRIPTION
		"The total number of DHCP Release packets forwarded."
	::= { csOrionDhcpRelayStatsEntry 10 }

    csOrionDhcpRelayOutDecs OBJECT-TYPE
	SYNTAX  Counter32
	MAX-ACCESS  read-only
	STATUS  current
	DESCRIPTION
		"The total number of DHCP Decline packets forwarded."
	::= { csOrionDhcpRelayStatsEntry 11 }

    csOrionDhcpRelayOutAcks OBJECT-TYPE
	SYNTAX  Counter32
	MAX-ACCESS  read-only
	STATUS  current
	DESCRIPTION
		"The tatal number of DHCP Ack packets forwarded."
	::= { csOrionDhcpRelayStatsEntry 12 }

    csOrionDhcpRelayOutNaks OBJECT-TYPE
	SYNTAX  Counter32
	MAX-ACCESS  read-only
	STATUS  current
	DESCRIPTION
		"The total number of DHCP Nak packets forwarded."
	::= { csOrionDhcpRelayStatsEntry 13 }

    csOrionDhcpRelayOutOffers OBJECT-TYPE
	SYNTAX  Counter32
	MAX-ACCESS  read-only
	STATUS  current
	DESCRIPTION
		"The total number of DHCP Offer packets forwarded."
	::= { csOrionDhcpRelayStatsEntry 14 }

------------------------------------------------------------------------------
--
--	       VPN Virtual Router DNS Configuration
--
------------------------------------------------------------------------------

    csOrionVrDnsConfigTable OBJECT-TYPE
	SYNTAX  SEQUENCE OF CsOrionVrDnsConfigEntry
	MAX-ACCESS  not-accessible
	STATUS  current
	DESCRIPTION
		"This table contains DNS configuration parameters."
    ::= { csOrionDNSInfo 1 }

    csOrionVrDnsConfigEntry OBJECT-TYPE
	SYNTAX CsOrionVrDnsConfigEntry
	MAX-ACCESS not-accessible
	STATUS  current
	DESCRIPTION
		"Each entry represents the DNS configuration parameters 
		for a single VR."
	INDEX   { csOrionGlobalVPNIndex, csOrionVPNVRouterIndex }
	::= { csOrionVrDnsConfigTable 1 }

    CsOrionVrDnsConfigEntry ::=
	SEQUENCE {
		csOrionVrPrimaryDnsServer
			IpAddress,
		csOrionVrSecondaryDnsServer
			IpAddress
	}

    csOrionVrPrimaryDnsServer OBJECT-TYPE
	SYNTAX  IpAddress
	MAX-ACCESS  read-write
	STATUS  current
	DESCRIPTION
		"The primary DNS server for this VR."
	::= { csOrionVrDnsConfigEntry 1 }

    csOrionVrSecondaryDnsServer OBJECT-TYPE
	SYNTAX  IpAddress
	MAX-ACCESS  read-write
	STATUS  current
	DESCRIPTION
		"The secondary DNS server for this VR."
	::= { csOrionVrDnsConfigEntry 2 }


------------------------------------------------------------------------------
--
--        VR's Interface Manager Table
--
------------------------------------------------------------------------------

   csOrionVrIfManagerTable OBJECT-TYPE
   SYNTAX  SEQUENCE OF CsOrionVrIfManagerEntry
   MAX-ACCESS  not-accessible
   STATUS  current
   DESCRIPTION
      ""
    ::= { csOrionServiceSelectionInfo 1}

   csOrionVrIfManagerEntry OBJECT-TYPE
   SYNTAX CsOrionVrIfManagerEntry
   MAX-ACCESS not-accessible
   STATUS  current
   DESCRIPTION
      ""
   INDEX   { csOrionGlobalVPNIndex,csOrionVPNVRouterIndex,
			 csOrionVrIfManagerSlotIndex, csOrionVrIfManagerPortIndex,
			 csOrionVrIfManagerChannelIndex, csOrionVrIfManagerSubifIndex }
   ::= { csOrionVrIfManagerTable 1 }

   CsOrionVrIfManagerEntry ::=
   SEQUENCE {
      csOrionVrIfManagerSlotIndex
         Integer32,
      csOrionVrIfManagerPortIndex
         Integer32,
      csOrionVrIfManagerChannelIndex
         Integer32,
      csOrionVrIfManagerSubifIndex
         Integer32,
	  csOrionVrIfManagerRowStatus
		 RowStatus
   }

   csOrionVrIfManagerSlotIndex  OBJECT-TYPE
   SYNTAX  Integer32 (1..'7fffffff'h)
   MAX-ACCESS not-accessible
   STATUS current
   DESCRIPTION
      "This object identifies the slot ID."
   ::= { csOrionVrIfManagerEntry 1 }

   csOrionVrIfManagerPortIndex OBJECT-TYPE
   SYNTAX  Integer32 (1..'7fffffff'h)
   MAX-ACCESS not-accessible
   STATUS current
   DESCRIPTION
      "This object identifies the port ID."
   ::= { csOrionVrIfManagerEntry 2 }

   csOrionVrIfManagerChannelIndex OBJECT-TYPE
   SYNTAX  Integer32 (0..'7fffffff'h)
   MAX-ACCESS  not-accessible
   STATUS	current
   DESCRIPTION
	  "This object identifies the channel ID."
   ::= { csOrionVrIfManagerEntry 3 }

   csOrionVrIfManagerSubifIndex OBJECT-TYPE
   SYNTAX  Integer32 (0..'7fffffff'h)
   MAX-ACCESS  not-accessible
   STATUS	current
   DESCRIPTION
	  "This object identifies the subif ID."
   ::= { csOrionVrIfManagerEntry 4 }

   csOrionVrIfManagerRowStatus OBJECT-TYPE
   SYNTAX   RowStatus
   MAX-ACCESS   read-create
   STATUS   current
   DESCRIPTION
      "The row status for this table."
   ::= { csOrionVrIfManagerEntry 5 }



--------------------------------------------------------------------------
--
-- 		Connection Profile Table 
--
--------------------------------------------------------------------------


	csOrionConnectionProfileTable OBJECT-TYPE
	SYNTAX	SEQUENCE OF CsOrionConnectionProfileEntry 
	MAX-ACCESS  not-accessible
	STATUS	current
	DESCRIPTION
		"This table contains a list of connection profiles."
	::= { csOrionServiceSelectionInfo 2 }

    csOrionConnectionProfileEntry OBJECT-TYPE
	SYNTAX 	 CsOrionConnectionProfileEntry
	MAX-ACCESS  not-accessible
	STATUS	current
	DESCRIPTION
		"This entry represents a single connection profile."
	INDEX   { csOrionGlobalVPNIndex, csOrionVPNVRouterIndex,
			  csOrionConnectionProfileName}
	::= { csOrionConnectionProfileTable 1 }

    CsOrionConnectionProfileEntry::=
	SEQUENCE {
 		csOrionConnectionProfileName	
			LongDisplayString,
		csOrionConnectionProfileVpnId	 
			Integer32,
		csOrionConnectionProfileVrId
			IpAddress,
		csOrionConnectionProfileAddrPoolname
			LongDisplayString,
		csOrionConnectionProfileLnsAddress
			IpAddress,
		csOrionConnectionProfileRowStatus
			RowStatus
	}

    csOrionConnectionProfileName OBJECT-TYPE
	SYNTAX	LongDisplayString  (SIZE (0..256))
	MAX-ACCESS  not-accessible
	STATUS	current
	DESCRIPTION
		"The name of this connection profile."
	::= { csOrionConnectionProfileEntry 1 }

    csOrionConnectionProfileVpnId OBJECT-TYPE
	SYNTAX 	 Integer32 (0.. 2147483647)
	MAX-ACCESS  read-create
	STATUS	current
	DESCRIPTION
		"The VPN Id this profile applies to."
	DEFVAL  { 0 }  -- this value is a wild card. 
				   -- Means any VPN.
	::= { csOrionConnectionProfileEntry 2 }

    csOrionConnectionProfileVrId OBJECT-TYPE
	SYNTAX IpAddress
	MAX-ACCESS  read-create
	STATUS	current
	DESCRIPTION
		"The VR Id this profile applies to."
	DEFVAL  { '00000000'H }  -- 0.0.0.0 This value is a wild card. 
							 -- Means any VR.
	::= { csOrionConnectionProfileEntry 3 }

    csOrionConnectionProfileAddrPoolname OBJECT-TYPE
 	SYNTAX	LongDisplayString (SIZE(0..256))
	MAX-ACCESS  read-create
	STATUS	current
	DESCRIPTION
		"The local IP address poolname in the VR."
	DEFVAL  { "" }  -- this value is a wild card.
					-- Means and address poolname.
	::= { csOrionConnectionProfileEntry 4 }

	csOrionConnectionProfileLnsAddress OBJECT-TYPE
	SYNTAX IpAddress
	MAX-ACCESS  read-create
	STATUS	current
	DESCRIPTION
		"The LNS IP address this profile applies to."
	DEFVAL  { '00000000'H }  -- 0.0.0.0 This value is a wild card. 
							 -- Means any LNS IP address.
	::= { csOrionConnectionProfileEntry 5 }

	csOrionConnectionProfileRowStatus OBJECT-TYPE
 	SYNTAX	RowStatus
	MAX-ACCESS  read-create
	STATUS	current
	DESCRIPTION
		"The row status for this table."
	::= { csOrionConnectionProfileEntry 6 }


--------------------------------------------------------------------------
--
-- 		Service Name Table (template) 
--
--------------------------------------------------------------------------


	csOrionServiceTemplateTable OBJECT-TYPE
	SYNTAX	SEQUENCE OF CsOrionServiceTemplateEntry
	MAX-ACCESS  not-accessible
	STATUS	current
	DESCRIPTION
		"This table contains a list of names of service selections.
		 Each of this entry will hold a list of connection profiles.
		 Refer to expansion table csOrionServiceTemplateConnProfileTable."
	::= { csOrionServiceSelectionInfo 3 }

	csOrionServiceTemplateEntry OBJECT-TYPE
	SYNTAX 	 CsOrionServiceTemplateEntry
	MAX-ACCESS  not-accessible
	STATUS	current
	DESCRIPTION
		"This entry represents a single service selection."
	INDEX   { csOrionGlobalVPNIndex, csOrionVPNVRouterIndex,
			  csOrionServiceTemplateName}
	::= { csOrionServiceTemplateTable 2 }

    CsOrionServiceTemplateEntry::=
	SEQUENCE {
 	csOrionServiceTemplateName	
		LongDisplayString,
	csOrionServiceTemplateRowStatus
		RowStatus
	}

    csOrionServiceTemplateName OBJECT-TYPE
	SYNTAX	LongDisplayString  (SIZE (0..256))
	MAX-ACCESS  not-accessible
	STATUS	current
	DESCRIPTION
		"The service selection template name."
	::= { csOrionServiceTemplateEntry 1 }

	csOrionServiceTemplateRowStatus OBJECT-TYPE
	SYNTAX	RowStatus
	MAX-ACCESS  read-create
	STATUS	current
	DESCRIPTION
		"The row status for this table."
	::= { csOrionServiceTemplateEntry 2 }


--
-- 		Service Name Connection Profile Table (expansion table ofcsOrionServiceTemplateTable) 
--

	csOrionServiceTemplateConnProfileTable OBJECT-TYPE
	SYNTAX	SEQUENCE OF CsOrionServiceTemplateConnProfileEntry
	MAX-ACCESS  not-accessible
	STATUS	current
	DESCRIPTION
		"This table contains a list of connection profiles contained
		 in a single service selection template."
	::= { csOrionServiceSelectionInfo 4 }

	csOrionServiceTemplateConnProfileEntry OBJECT-TYPE
	SYNTAX 	 CsOrionServiceTemplateConnProfileEntry
	MAX-ACCESS  not-accessible
	STATUS	current
	DESCRIPTION
		"This entry represents a single connection profile on a
		 service selection."
	INDEX   { csOrionGlobalVPNIndex, csOrionVPNVRouterIndex,
			  csOrionServiceTemplateName, 
			  csOrionServiceTemplateConnProfileName}
	::= { csOrionServiceTemplateConnProfileTable 2 }

    CsOrionServiceTemplateConnProfileEntry::=
	SEQUENCE {
 	csOrionServiceTemplateConnProfileName	
		LongDisplayString,
	csOrionServiceTemplateConnProfileRowStatus
		RowStatus
	}

    csOrionServiceTemplateConnProfileName OBJECT-TYPE
	SYNTAX	LongDisplayString  (SIZE (0..256))
	MAX-ACCESS  not-accessible
	STATUS	current
	DESCRIPTION
		"The name of the connection profile to be added in the table.
		 NOTE: Must be an existing csOrionConnectionProfileName."
	::= { csOrionServiceTemplateConnProfileEntry 1 }

	csOrionServiceTemplateConnProfileRowStatus OBJECT-TYPE
	SYNTAX	RowStatus
	MAX-ACCESS  read-create
	STATUS	current
	DESCRIPTION
		"The row status for this table."
	::= { csOrionServiceTemplateConnProfileEntry 2 }

------------------------------------------------------------------------------
--
--	       VPN Virtual Router Cisco HDLC Interface Configuration Table
--
------------------------------------------------------------------------------
	csOrionCiscoHdlcConfigTable OBJECT-TYPE
	SYNTAX  SEQUENCE OF CsOrionCiscoHdlcConfigEntry
	MAX-ACCESS  not-accessible
	STATUS  current
	DESCRIPTION
		"This table contains configuration parameters for 
		Cisco HDLC."
    ::= { csOrionCiscoHdlcInfo 1 }

    csOrionCiscoHdlcConfigEntry OBJECT-TYPE
	SYNTAX CsOrionCiscoHdlcConfigEntry
	MAX-ACCESS not-accessible
	STATUS  current
	DESCRIPTION
		"Each entry represents the Cisco HDLC interface-specific 
		configuration parameters for a single interface."
	INDEX   { csOrionCiscoHdlcSlotIndex, csOrionCiscoHdlcPortIndex,
		  csOrionCiscoHdlcChIndex }
	::= { csOrionCiscoHdlcConfigTable 1 }

    CsOrionCiscoHdlcConfigEntry ::=
	SEQUENCE {
		csOrionCiscoHdlcSlotIndex
			Integer32,
		csOrionCiscoHdlcPortIndex
			Integer32,
		csOrionCiscoHdlcChIndex
			Integer32,
		csOrionCiscoHdlcSlarpKeepAlive
			Integer32,
		csOrionCiscoHdlcOperStatus
			OperStatus,
		csOrionCiscoHdlcAdminStatus
			INTEGER

	}

    csOrionCiscoHdlcSlotIndex OBJECT-TYPE
	SYNTAX  Integer32 (1..64)
	MAX-ACCESS  not-accessible
	STATUS  current
	DESCRIPTION
		"The Slot Id of this interface."
	::= { csOrionCiscoHdlcConfigEntry 1 }


    csOrionCiscoHdlcPortIndex OBJECT-TYPE
	SYNTAX  Integer32 (1..64)
	MAX-ACCESS  not-accessible
	STATUS  current
	DESCRIPTION
		"The Port Id of this interface."
	::= { csOrionCiscoHdlcConfigEntry 2 }


    csOrionCiscoHdlcChIndex OBJECT-TYPE
	SYNTAX  Integer32 (0..64)
	MAX-ACCESS  not-accessible
	STATUS  current
	DESCRIPTION
		"The Channel Id of this interface.
		Channel is 0 if this object is in the Unchannelized DS3."
	::= { csOrionCiscoHdlcConfigEntry 3 }


    csOrionCiscoHdlcSlarpKeepAlive OBJECT-TYPE
	SYNTAX  Integer32 (1..2147483647)
	MAX-ACCESS  read-write
	STATUS  current
	DESCRIPTION
		"The interval, in second, between keep alive packets."
	DEFVAL { 10 }
	::= { csOrionCiscoHdlcConfigEntry 4 }


    csOrionCiscoHdlcOperStatus OBJECT-TYPE
	SYNTAX  OperStatus
	MAX-ACCESS  read-only
	STATUS	current
	DESCRIPTION
	       "The operational status of this table."
	::= { csOrionCiscoHdlcConfigEntry 5 }


    csOrionCiscoHdlcAdminStatus OBJECT-TYPE
	SYNTAX  INTEGER {
		enable  (1),
		disable (2)
	}
	MAX-ACCESS  read-write
	STATUS	current
	DESCRIPTION
	       "This object is used to enable/disable the Cisco HDLC."
	DEFVAL { disable }
	::= { csOrionCiscoHdlcConfigEntry 6 }

------------------------------------------------------------------------------
--
--	       FRoIP
--
------------------------------------------------------------------------------

	csOrionFRoIPConfTable OBJECT-TYPE
	SYNTAX  SEQUENCE OF CsOrionFRoIPConfEntry
	MAX-ACCESS  not-accessible
	STATUS  current
	DESCRIPTION
		"This table contains general FRoIP Configuration parameters."
    ::= { csOrionFRoIPInfo 1 }

    csOrionFRoIPConfEntry OBJECT-TYPE
	SYNTAX CsOrionFRoIPConfEntry
	MAX-ACCESS not-accessible
	STATUS  current
	DESCRIPTION
		"Each entry represents a set of FRoIPconfiguration for
		a Virtual Router. There is only one instance of FRoIP  on
		a Virtual Router. An entry is created with IP address and 
		default values for all the other objects when a VR is created.
		Creation of row by Network Management Stations is not allowed."
	INDEX   { csOrionGlobalVPNIndex, csOrionVPNVRouterIndex }
	::= { csOrionFRoIPConfTable 1 }

    CsOrionFRoIPConfEntry ::=
	SEQUENCE {
		csOrionFRoIPVIfaceId
			Integer32,
		csOrionFRoIPConfMaxPeer
			Integer32,
		csOrionFRoIPConfDefaultWindowSize
			Integer32,
		csOrionFRoIPConfDefaultWindowTimeout
			Integer32,
                csOrionFRoIPConfDefaultServiceSlot
                        Integer32,
		csOrionFRoIPConfNumActiveTransports
			Integer32,
		csOrionFRoIPAdminStatus
 			INTEGER,
		csOrionFRoIPOperStatus
			OperStatus
	}

   csOrionFRoIPVIfaceId OBJECT-TYPE
	SYNTAX	Integer32
	MAX-ACCESS  read-write
	STATUS	current
	DESCRIPTION
		" "
	::= { csOrionFRoIPConfEntry 1 }

    csOrionFRoIPConfMaxPeer OBJECT-TYPE
	SYNTAX	 Integer32(1..1024) 
	MAX-ACCESS  read-write
	STATUS	current
	DESCRIPTION
		" "
	DEFVAL {24} 
	::= { csOrionFRoIPConfEntry 2 }

    csOrionFRoIPConfDefaultWindowSize OBJECT-TYPE
	SYNTAX	 Integer32(0..256) 
	MAX-ACCESS  read-write
	STATUS	current
	DESCRIPTION
		" "
	DEFVAL {24}
	::= { csOrionFRoIPConfEntry 3 }

    csOrionFRoIPConfDefaultWindowTimeout OBJECT-TYPE
	SYNTAX	 Integer32(10..25000)
	MAX-ACCESS  read-write
	STATUS	current
	DESCRIPTION
		" "
	DEFVAL {1000}
	::= { csOrionFRoIPConfEntry 4 }

    csOrionFRoIPConfDefaultServiceSlot OBJECT-TYPE
        SYNTAX  Integer32 (1..26)
        MAX-ACCESS  read-write
        STATUS  current
        DESCRIPTION
               "This object identifies the slot that all new
                transports created off this base inherit."
        ::= { csOrionFRoIPConfEntry 5 }
  
    csOrionFRoIPConfNumActiveTransports OBJECT-TYPE
	SYNTAX	 Integer32
	MAX-ACCESS  read-only
	STATUS	current
	DESCRIPTION
		" "
	::= { csOrionFRoIPConfEntry 6 }

    csOrionFRoIPAdminStatus OBJECT-TYPE
	SYNTAX	 INTEGER {
		enable (1),
		disable (2)
		}
	MAX-ACCESS  read-write
	STATUS	current
	DESCRIPTION
		" "
	DEFVAL {disable}
	::= { csOrionFRoIPConfEntry 7 }

    csOrionFRoIPOperStatus OBJECT-TYPE
	SYNTAX	 OperStatus 
	MAX-ACCESS  read-only
	STATUS	current
	DESCRIPTION
		" "
	::= { csOrionFRoIPConfEntry 8 }


    csOrionFRoIPTransportTable OBJECT-TYPE
	SYNTAX  SEQUENCE OF CsOrionFRoIPTransportEntry
	MAX-ACCESS  not-accessible
	STATUS  current
	DESCRIPTION
		"This table contains transport related objects of FRoIP."
    ::= { csOrionFRoIPInfo 2 }

    csOrionFRoIPTransportEntry OBJECT-TYPE
	SYNTAX CsOrionFRoIPTransportEntry
	MAX-ACCESS not-accessible
	STATUS  current
	DESCRIPTION
		"Each entry represents a set of  transport related objects of FRoIP
		on a Virtual Router."
	INDEX   { csOrionGlobalVPNIndex, csOrionVPNVRouterIndex, csOrionFRoIPTransportPeer }
	::= { csOrionFRoIPTransportTable 1 }

    CsOrionFRoIPTransportEntry ::=
	SEQUENCE {
		csOrionFRoIPTransportPeer
 			IpAddress,
		csOrionFRoIPTransportMode
			INTEGER,
		csOrionFRoIPTransportWindowSize
 			Integer32,
		csOrionFRoIPTransportWindowTimeout
			Integer32,
		csOrionFRoIPTransportKeepAlive
			Integer32,
		csOrionFRoIPTransportEventWindowSize
			Integer32,
		csOrionFRoIPTransportPermittedBadEvents
			Integer32,
                csOrionFRoIPTransportDefaultSlot
                        Integer32,
		csOrionFRoIPTransportOutPkts
			Counter32,
		csOrionFRoIPTransportInPkts
			Counter32,
		csOrionFRoIPTransportOutBytes
			Counter32,
		csOrionFRoIPTransportInBytes
			Counter32,
		csOrionFRoIPTransportRowStatus
			RowStatus,
        csOrionFRoIPTransportAdminStatus
			INTEGER,
		csOrionFRoIPTransportOperStatus
			OperStatus
	}

   csOrionFRoIPTransportPeer OBJECT-TYPE
	SYNTAX	IpAddress
	MAX-ACCESS  not-accessible
	STATUS	current
	DESCRIPTION
		" "
	::= { csOrionFRoIPTransportEntry 1 }

    csOrionFRoIPTransportMode OBJECT-TYPE
	SYNTAX	 INTEGER {
		active(1),
		passive(2)
		} 
	MAX-ACCESS  read-only
	STATUS	current
	DESCRIPTION
		" "
	::= { csOrionFRoIPTransportEntry 2 }

    csOrionFRoIPTransportWindowSize OBJECT-TYPE
	SYNTAX	 Integer32(0..256)
	MAX-ACCESS  read-create
	STATUS	current
	DESCRIPTION
		" "
	DEFVAL {24}
	::= { csOrionFRoIPTransportEntry 3 }

    csOrionFRoIPTransportWindowTimeout OBJECT-TYPE
	SYNTAX	 Integer32 (10..25000)
	MAX-ACCESS  read-create
	STATUS	current
	DESCRIPTION
		" In milliseconds"
	DEFVAL {1000}
	::= { csOrionFRoIPTransportEntry 4 }

    csOrionFRoIPTransportKeepAlive OBJECT-TYPE
	SYNTAX	 Integer32(3..30)
	MAX-ACCESS  read-create
	STATUS	current
	DESCRIPTION
		" "
	DEFVAL {15}
	::= { csOrionFRoIPTransportEntry 5 }

    csOrionFRoIPTransportEventWindowSize OBJECT-TYPE
	SYNTAX	 Integer32 (1..10)
	MAX-ACCESS  read-create
	STATUS	current
	DESCRIPTION
		" "
	DEFVAL {4}
	::= { csOrionFRoIPTransportEntry 6 }

    csOrionFRoIPTransportPermittedBadEvents OBJECT-TYPE
	SYNTAX	 Integer32 (1..10)
	MAX-ACCESS  read-create
	STATUS	current
	DESCRIPTION
		" "
	DEFVAL {3}
	::= { csOrionFRoIPTransportEntry 7 }


    csOrionFRoIPTransportDefaultSlot OBJECT-TYPE
        SYNTAX  Integer32 (1..26)
        MAX-ACCESS  read-only
        STATUS  current
        DESCRIPTION
                " "
        ::= { csOrionFRoIPTransportEntry 8 }

    csOrionFRoIPTransportOutPkts OBJECT-TYPE
	SYNTAX	 Counter32
	MAX-ACCESS  read-only
	STATUS	current
	DESCRIPTION
		" "
	::= { csOrionFRoIPTransportEntry 9 }

    csOrionFRoIPTransportInPkts OBJECT-TYPE
	SYNTAX	 Counter32
	MAX-ACCESS  read-only
	STATUS	current
	DESCRIPTION
		" "
	::= { csOrionFRoIPTransportEntry 10 }

    csOrionFRoIPTransportOutBytes OBJECT-TYPE
	SYNTAX	 Counter32
	MAX-ACCESS  read-only
	STATUS	current
	DESCRIPTION
		" "
	::= { csOrionFRoIPTransportEntry 11 }

    csOrionFRoIPTransportInBytes OBJECT-TYPE
	SYNTAX	 Counter32
	MAX-ACCESS  read-only
	STATUS	current
	DESCRIPTION
		" "
	::= { csOrionFRoIPTransportEntry 12 }

    csOrionFRoIPTransportRowStatus OBJECT-TYPE
	SYNTAX	 RowStatus
	MAX-ACCESS  read-create
	STATUS	current
	DESCRIPTION
		" "
	::= { csOrionFRoIPTransportEntry 13 }
    csOrionFRoIPTransportAdminStatus OBJECT-TYPE
	SYNTAX	 INTEGER {
		enable (1),
		disable (2)
		}
	MAX-ACCESS  read-create
	STATUS	current
	DESCRIPTION
		" "
	DEFVAL {disable}
	::= { csOrionFRoIPTransportEntry 14 }

    csOrionFRoIPTransportOperStatus OBJECT-TYPE  
	SYNTAX	 OperStatus 
	MAX-ACCESS  read-only
	STATUS	current
	DESCRIPTION
		" "
	::= { csOrionFRoIPTransportEntry 15 }

     csFRoIPCircuitTable OBJECT-TYPE
         SYNTAX   SEQUENCE OF CsFRoIPCircuitEntry
         MAX-ACCESS   not-accessible
         STATUS   current
         DESCRIPTION
            "A table containing information about 
             virtual circuits corresponding to FRoIP Transports.."
         ::= { csOrionFRoIPInfo 3 }


     csFRoIPCircuitEntry OBJECT-TYPE
         SYNTAX   CsFRoIPCircuitEntry
         MAX-ACCESS   not-accessible
         STATUS   current
         DESCRIPTION
            "The information regarding a single Data Link
            Connection.  Discontinuities in the counters contained
            in this table are indicated by the value in
            csFrCircuitCreationTime."
         INDEX {  csOrionGlobalVPNIndex, csOrionVPNVRouterIndex, csOrionFRoIPTransportPeer, csFRoIPCircuitDlci}
         ::= { csFRoIPCircuitTable 1 }


     CsFRoIPCircuitEntry ::=
         SEQUENCE {
             csFRoIPCircuitDlci                   DLCI,
             csFRoIPCircuitState                  INTEGER,
             csFRoIPCircuitReceivedFECNs          Counter32,
             csFRoIPCircuitReceivedBECNs          Counter32,
             csFRoIPCircuitSentFrames             Counter32,
             csFRoIPCircuitSentOctets             Counter32,
             csFRoIPCircuitReceivedFrames         Counter32,
             csFRoIPCircuitReceivedOctets         Counter32,
             csFRoIPCircuitCreationTime           TimeStamp,
             csFRoIPCircuitLastTimeChange         TimeStamp,
             csFRoIPCircuitCommittedBurst         Integer32,
             csFRoIPCircuitExcessBurst            Integer32,
             csFRoIPCircuitThroughput             Integer32,
             csFRoIPCircuitMulticast              INTEGER,
             csFRoIPCircuitType                   INTEGER,
             csFRoIPCircuitDiscards               Counter32,
             csFRoIPCircuitReceivedDEs            Counter32,
             csFRoIPCircuitSentDEs                Counter32,
             csFRoIPCircuitRowStatus              RowStatus,
			 csFRoIPCircuitOperStatus             OperStatus,
			 csFRoIPCircuitFwdLink				   OCTET STRING

     }

     csFRoIPCircuitDlci OBJECT-TYPE
         SYNTAX   DLCI
         MAX-ACCESS   not-accessible
         STATUS   current
         DESCRIPTION
            "The Data Link Connection Identifier for this virtual
            circuit.  Note, this impelemtation supports only values between 
	    16 and 1023 (inclusive)."
         REFERENCE
            "American National Standard T1.618-1991, Section 3.3.6"
         ::= { csFRoIPCircuitEntry 1 }


     csFRoIPCircuitState OBJECT-TYPE
         SYNTAX   INTEGER    {

                     invalid (1),
                     active (2),
                     inactive (3)
                  }
         MAX-ACCESS   read-create
         STATUS   current
         DESCRIPTION
            "Indicates whether the particular virtual circuit is
            operational.  In the absence of a Data Link Connection
            Management Interface, virtual circuit entries (rows)
            may be created by setting virtual circuit state to
            'active', or deleted by changing Circuit state to
            'invalid'.

            Whether or not the row actually disappears is left to
            the implementation, so this object may actually read as
            'invalid' for some arbitrary length of time.  It is
            also legal to set the state of a virtual circuit to
            'inactive' to temporarily disable a given circuit.

            The use of 'invalid' is deprecated in this SNMP Version
            2 MIB, in favor of csFRoIPCircuitRowStatus."
         DEFVAL { active }
         ::= { csFRoIPCircuitEntry 2 }


     csFRoIPCircuitReceivedFECNs OBJECT-TYPE
         SYNTAX   Counter32
         MAX-ACCESS   read-only
         STATUS   current
         DESCRIPTION
            "Number of frames received from the network indicating
            forward congestion since the virtual circuit was
            created.  This occurs when the remote DTE sets the FECN
            flag, or when a switch in the network enqueues the
            frame to a trunk whose transmission queue is
            congested."
         REFERENCE
            "American National Standard T1.618-1991, Section 3.3.3"
         ::= { csFRoIPCircuitEntry 3 }


     csFRoIPCircuitReceivedBECNs OBJECT-TYPE
         SYNTAX   Counter32
         MAX-ACCESS   read-only


         STATUS   current
         DESCRIPTION
            "Number of frames received from the network indicating
            backward congestion since the virtual circuit was
            created.  This occurs when the remote DTE sets the BECN
            flag, or when a switch in the network receives the
            frame from a trunk whose transmission queue is
            congested."
         REFERENCE
            "American National Standard T1.618-1991, Section 3.3.4"
         ::= { csFRoIPCircuitEntry 4 }


     csFRoIPCircuitSentFrames OBJECT-TYPE
         SYNTAX   Counter32
         MAX-ACCESS   read-only
         STATUS   current
         DESCRIPTION
            "The number of frames sent from this virtual circuit
            since it was created."
         ::= { csFRoIPCircuitEntry 5}


     csFRoIPCircuitSentOctets OBJECT-TYPE
         SYNTAX   Counter32
         MAX-ACCESS   read-only
         STATUS   current
         DESCRIPTION
            "The number of octets sent from this virtual circuit
            since it was created.  Octets counted are the full
            frame relay header and the payload, but do not include
            the flag characters or CRC."
         ::= { csFRoIPCircuitEntry 6 }


     csFRoIPCircuitReceivedFrames OBJECT-TYPE
         SYNTAX   Counter32
         MAX-ACCESS   read-only
         STATUS   current
         DESCRIPTION
            "Number of frames received over this virtual circuit
            since it was created."
         ::= { csFRoIPCircuitEntry 7 }


     csFRoIPCircuitReceivedOctets OBJECT-TYPE
         SYNTAX   Counter32
         MAX-ACCESS   read-only
         STATUS   current
         DESCRIPTION
            "Number of octets received over this virtual circuit
            since it was created.  Octets counted include the full
            frame relay header, but do not include the flag
            characters or the CRC."
         ::= { csFRoIPCircuitEntry 8 }


     csFRoIPCircuitCreationTime OBJECT-TYPE
         SYNTAX   TimeStamp
         MAX-ACCESS   read-only
         STATUS   current
         DESCRIPTION
            "The value of sysUpTime when the virtual circuit was
            created, whether by the Data Link Connection Management
            Interface or by a SetRequest."
         ::= { csFRoIPCircuitEntry 9 }


     csFRoIPCircuitLastTimeChange OBJECT-TYPE
         SYNTAX   TimeStamp
         MAX-ACCESS   read-only
         STATUS   current
         DESCRIPTION
            "The value of sysUpTime when last there was a change in
            the virtual circuit state"
         ::= { csFRoIPCircuitEntry 10 }


     csFRoIPCircuitCommittedBurst OBJECT-TYPE
         SYNTAX   Integer32(0..2147483647)
         MAX-ACCESS   read-create
         STATUS   current
         DESCRIPTION
            "This variable indicates the maximum amount of data, in
            bits, that the network agrees to transfer under normal
            conditions, during the measurement interval."
         REFERENCE
            "American National Standard T1.617-1991, Section
            6.5.19"
         DEFVAL   { 0 }  -- the default indicates no commitment
         ::= { csFRoIPCircuitEntry 11 }


     csFRoIPCircuitExcessBurst OBJECT-TYPE
         SYNTAX   Integer32(0..2147483647)
         MAX-ACCESS   read-create
         STATUS   current
         DESCRIPTION
            "This variable indicates the maximum amount of
            uncommitted data bits that the network will attempt to
            deliver over the measurement interval.

            By default, if not configured when creating the entry,
            the Excess Information Burst Size is set to the value
            of ifSpeed."
         REFERENCE
            "American National Standard T1.617-1991, Section
            6.5.19"
         ::= { csFRoIPCircuitEntry 12 }


     csFRoIPCircuitThroughput OBJECT-TYPE
         SYNTAX   Integer32(0..2147483647)
         MAX-ACCESS   read-create
         STATUS   current
         DESCRIPTION
            "Throughput is the average number of 'Frame Relay
            Information Field' bits transferred per second across a
            user network interface in one direction, measured over
            the measurement interval.

            If the configured committed burst rate and throughput
            are both non-zero, the measurement interval, T, is
                T=csFRoIPCircuitCommittedBurst/csFRoIPCircuitThroughput.

            If the configured committed burst rate and throughput
            are both zero, the measurement interval, T, is
                       T=csFRoIPCircuitExcessBurst/ifSpeed."
         REFERENCE
            "American National Standard T1.617-1991, Section
            6.5.19"
         DEFVAL {0}  -- the default value of Throughput is
                     -- "no commitment".
         ::= { csFRoIPCircuitEntry 13 }


     csFRoIPCircuitMulticast OBJECT-TYPE
         SYNTAX   INTEGER    {
                     unicast   (1),
                     oneWay    (2),
                     twoWay    (3),
                     nWay      (4)
                     }
         MAX-ACCESS   read-only
         STATUS   current
         DESCRIPTION
            "This indicates whether this VC is used as a unicast VC
            (i.e. not multicast) or the type of multicast service
            subscribed to"
         REFERENCE
            "Frame Relay PVC Multicast Service and Protocol
            Description Implementation: FRF.7 Frame Relay Forum
            Technical Committe October 21, 1994"
              ::= { csFRoIPCircuitEntry 14 }


     csFRoIPCircuitType OBJECT-TYPE
         SYNTAX   INTEGER    {
                     static  (1),
                     dynamic (2)
                  }
         MAX-ACCESS   read-only
         STATUS   current
         DESCRIPTION
            "Indication of whether the VC was manually created
            (static), or dynamically created (dynamic) via the data
            link control management interface."
         ::= { csFRoIPCircuitEntry 15 }


     csFRoIPCircuitDiscards OBJECT-TYPE
         SYNTAX   Counter32
         MAX-ACCESS   read-only
         STATUS   current
         DESCRIPTION
            "The number of inbound frames dropped because of format
            errors, or because the VC is inactive."
         ::= { csFRoIPCircuitEntry 16 }


     csFRoIPCircuitReceivedDEs OBJECT-TYPE
         SYNTAX   Counter32
         MAX-ACCESS   read-only
         STATUS   current
         DESCRIPTION
            "Number of frames received from the network indicating
            that they were eligible for discard since the virtual
            circuit was created.  This occurs when the remote DTE
            sets the DE flag, or when in remote DTE's switch
            detects that the frame was received as Excess Burst
            data."
         REFERENCE
            "American National Standard T1.618-1991, Section 3.3.4"
         ::= { csFRoIPCircuitEntry 17 }


     csFRoIPCircuitSentDEs OBJECT-TYPE
         SYNTAX   Counter32
         MAX-ACCESS   read-only
         STATUS   current
         DESCRIPTION
            "Number of frames sent to the network indicating that
            they were eligible for discard since the virtual
            circuit was created.   This occurs when the local DTE
            sets the DE flag, indicating that during Network
            congestion situations those frames should be discarded
            in preference of other frames sent without the DE bit
            set."
         REFERENCE
            "American National  Standard  T1.618-1991, Section
            3.3.4"
        ::= { csFRoIPCircuitEntry 18 }


     csFRoIPCircuitRowStatus OBJECT-TYPE
         SYNTAX   RowStatus
         MAX-ACCESS   read-create
         STATUS   current
         DESCRIPTION
            "This object is used to create a new row or modify or
            destroy an existing row in the manner described in the
            definition of the RowStatus textual convention.
            Writable objects in the table may be written in any
            RowStatus state."
         ::= { csFRoIPCircuitEntry 19 }


     csFRoIPCircuitOperStatus OBJECT-TYPE
         SYNTAX   OperStatus
         MAX-ACCESS   read-only
         STATUS   current
         DESCRIPTION
            "The operational status of this circuit."
         ::= { csFRoIPCircuitEntry 20 }

	csFRoIPCircuitFwdLink OBJECT-TYPE
         SYNTAX   OCTET STRING (SIZE(16))
         MAX-ACCESS   read-create
         STATUS   current
         DESCRIPTION
            "The forwarding link of this DLCI. This is a switching 
			 parameters for intra blade and inter-blade switching.
			 It takes the following format:
			   byte #0 to #3  : Slot number (csFRoIPDlcmiSlot)
			   byte #4 to #7  : Port number (csFRoIPDlcmiPort)
			   byte #8 to #11 : Channel number (csFRoIPDlcmiChannel, 
										zero for unchannelized blade)
			   byte #12 to #15: DLCI number (csFRoIPCircuitDlci)
			   NOTE: all zero indicates that this DLCI is not connected
			         to any link."
		 DEFVAL { '00000000000000000000000000000000'H }
         ::= { csFRoIPCircuitEntry 21 }


------------------------------------------------------------------------------
--
--	       L2TP
--
------------------------------------------------------------------------------


	--
	-- L2TP Configuration
	--

	csOrionL2tpConfigTable OBJECT-TYPE
	SYNTAX  SEQUENCE OF CsOrionL2tpConfigEntry
	MAX-ACCESS  not-accessible
	STATUS  current
	DESCRIPTION
		"This table contains general L2TP configuration parameters.
		 IMPORTANT : Tunnels and session parameters are established using 
					 the parameters in this table. That means, changing 
					 the value of an object in this table will not
					 affect existing tunnels and session. It will be applied
					 for the tunnels and session that are to be established."
    ::= { csOrionL2tpInfo 1 }

    csOrionL2tpConfigEntry OBJECT-TYPE
	SYNTAX CsOrionL2tpConfigEntry
	MAX-ACCESS not-accessible
	STATUS  current
	DESCRIPTION
		"Each entry represents a single L2TP object for a Virtual Router. 
		 Only a single instance of this object is created upon creation
		 of a VR."
	INDEX   { csOrionGlobalVPNIndex, csOrionVPNVRouterIndex }
	::= { csOrionL2tpConfigTable 1 }

    CsOrionL2tpConfigEntry ::=
	SEQUENCE {
		csOrionL2tpConfigServiceIf
			Integer32,
		csOrionL2tpConfigMaxTunnels
			Integer32,
		csOrionL2tpConfigMaxSessionsPerTunnel
			Integer32,
		csOrionL2tpConfigTunnelAuthentication
			INTEGER,
		csOrionL2tpConfigTunnelHelloInterval
			Integer32,
		csOrionL2tpConfigTunnelMaxRetransmissions
			Integer32,
		csOrionL2tpConfigTunnelMaxRetransmissionTimeout
			Integer32,
		csOrionL2tpConfigTunnelRWS
			Integer32,
		csOrionL2tpConfigTunnelEmptyTunnelTimeout
			Integer32,
		csOrionL2tpConfigSessionFlowControl
			INTEGER,
		csOrionL2tpConfigSessionRWS
			Integer32,
		csOrionL2tpConfigSessionTxQueueSize
			Integer32,
		csOrionL2tpConfigSessionPacketSequencing
			INTEGER,
		csOrionL2tpConfigPppConfigReqRetransmission
			Integer32,
		csOrionL2tpConfigPppRestartTimeout
			Integer32,
		csOrionL2tpConfigPppTermReqRetransmission
			Integer32,
		csOrionL2tpConfigPppAuthProtocol
 			INTEGER,
		csOrionL2tpConfigPppReauthPeriod
			Integer32,
		csOrionL2tpConfigPppEchoTimeout
			Integer32,
		csOrionL2tpConfigPppIpPoolName
			DisplayString
	}

	csOrionL2tpConfigServiceIf OBJECT-TYPE
	SYNTAX	Integer32(1..64000) 
	MAX-ACCESS  read-write
	STATUS	current
	DESCRIPTION
		"This object defines the VI over which communication will 
		 occur with peers. This object can be set only when there 
		 is no tunnel."
	DEFVAL { 1 }
	::= { csOrionL2tpConfigEntry 1 }

    csOrionL2tpConfigMaxTunnels OBJECT-TYPE
	SYNTAX	Integer32(1..65535) 
	MAX-ACCESS  read-write
	STATUS	current
	DESCRIPTION
		"This object defines the maximum number of L2TP tunnels that  
		 can be established."
	DEFVAL { 256 }
	::= { csOrionL2tpConfigEntry 2 }

    csOrionL2tpConfigMaxSessionsPerTunnel OBJECT-TYPE
	SYNTAX	 Integer32(1..65535)  
	MAX-ACCESS  read-write
	STATUS	current
	DESCRIPTION
		"This object defines the maximum sessions that can be 
		 established per tunnel."
	DEFVAL { 256 } 
	::= { csOrionL2tpConfigEntry 3 }

    csOrionL2tpConfigTunnelAuthentication OBJECT-TYPE
	SYNTAX	 INTEGER{
		enable  (1),
		disable (2)
		}
	MAX-ACCESS  read-write
	STATUS	current
	DESCRIPTION
		"This object controls the tunnel authentication.
		 If set to Enable, a challenge will be sent to the peer 
		 during tunnel creation. The tunnel will be torn down 
		 if the peer does not send a valid response. 
		 Regardless of the setting, if the peer sends a challenge 
		 during tunnel creation, a response will be sent."
	DEFVAL { disable }
	::= { csOrionL2tpConfigEntry 4 }

    csOrionL2tpConfigTunnelHelloInterval OBJECT-TYPE
	SYNTAX	 Integer32(0..3600)
	MAX-ACCESS  read-write
	STATUS	current
	DESCRIPTION
		"This object defines the interval (in seconds) in
         which HELLO (or keep-alive) packets are to be sent
         to the tunnel peer. Setting this to 0 disables sending of
         HELLO packets"
	DEFVAL { 60 }
	::= { csOrionL2tpConfigEntry 5 }

	csOrionL2tpConfigTunnelMaxRetransmissions OBJECT-TYPE
	SYNTAX	 Integer32(5..10)
	MAX-ACCESS  read-write
	STATUS	current
	DESCRIPTION
		"This object defines the number of retransmissions which
         the tunnel will attempt before assuming that the peer
         is no longer responding."
	DEFVAL { 5 }
	::= { csOrionL2tpConfigEntry 6 }

	csOrionL2tpConfigTunnelMaxRetransmissionTimeout OBJECT-TYPE
	SYNTAX	 Integer32(10..30)
	MAX-ACCESS  read-write
	STATUS	current
	DESCRIPTION
		"This object defines the maximum retransmission timeout
         interval in seconds which the tunnel will wait before 
		 retransmitting a control packet that has not been 
		 acknowledged."
	DEFVAL { 16 }
	::= { csOrionL2tpConfigEntry 7 }

	csOrionL2tpConfigTunnelRWS OBJECT-TYPE
	SYNTAX	 Integer32(1..16)
	MAX-ACCESS  read-write
	STATUS	current
	DESCRIPTION
		"This object defines the control channel receive window size.
         It specifies the maximum number of packets the tunnel peer 
         can send without waiting for an acknowledgement from this peer."
	DEFVAL { 10 }
	::= { csOrionL2tpConfigEntry 8 }

	csOrionL2tpConfigTunnelEmptyTunnelTimeout OBJECT-TYPE
	SYNTAX	 Integer32(0..3600)
	MAX-ACCESS  read-write
	STATUS	current
	DESCRIPTION
		"This object controls the time interval in seconds after which
		 an alive but empty tunnel (i.e. a tunnel without sessions) will
		 be torn down. Setting this to 0 will allow the empty tunnel to
		 continue to exist until either the peer stops responding or the
		 the tunnel is torn down by peer or the administrator."
	DEFVAL { 120 }
	::= { csOrionL2tpConfigEntry 9 }

	csOrionL2tpConfigSessionFlowControl OBJECT-TYPE
	SYNTAX	 INTEGER{
		enable  (1),
		disable (2)
		}
	MAX-ACCESS  read-write
	STATUS	current
	DESCRIPTION
		"This object will be used to control whether the peer will be 
		 requested to flow control its transmissions. Note that regardless 
		 of the setting, if the peer requests that this peer flow control its
		 transmissions, that request will be honored. Session Flow Control 
		 was part of draft specifications but not part of the RFC. 
		 This object should be set to Enable only if all the peers are using
		 draft implementations."
	DEFVAL { disable }
	::= { csOrionL2tpConfigEntry 10 }

	csOrionL2tpConfigSessionRWS OBJECT-TYPE
	SYNTAX	 Integer32(0..16)
	MAX-ACCESS  read-write
	STATUS	current
	DESCRIPTION
		"This object controls the size of the session receive window. 
		 It will be advertised to the peer during session setup if 
		 csOrionL2tpConfigSessionFlowControl is set to Enable.

		 The value 0 has special significance. It indicates that
		 the peer must include sequence numbers in payload packets
		 but the peer need not flow control its transmissions. This
		 can be used to force a peer that is non-RFC compliant to
		 include sequence numbers in payload packets."
	DEFVAL { 10 }
	::= { csOrionL2tpConfigEntry 11 }

	csOrionL2tpConfigSessionTxQueueSize OBJECT-TYPE
	SYNTAX	 Integer32(1..16)
	MAX-ACCESS  read-write
	STATUS	current
	DESCRIPTION
		"This object controls the size of the session-specific 
		 transmit queue. If the peer has requested flow control
		 and the peer's session receive window is full, packets 
		 to be sent to that peer will be held in a queue waiting 
		 for the peer's receive window to open."
	DEFVAL { 5 }
	::= { csOrionL2tpConfigEntry 12 }

	csOrionL2tpConfigSessionPacketSequencing OBJECT-TYPE
	SYNTAX	 INTEGER{
		enable  (1),
		disable (2)
		}
	MAX-ACCESS  read-write
	STATUS	current
	DESCRIPTION
		"This object determines whether or not session payload
         packets will be requested to be sent with sequence
         numbers from the tunnel peer."
	DEFVAL { disable }
	::= { csOrionL2tpConfigEntry 13 }

	csOrionL2tpConfigPppConfigReqRetransmission OBJECT-TYPE
	SYNTAX	 Integer32(0..64)
	MAX-ACCESS  read-write
	STATUS	current
	DESCRIPTION
		"This object is identical to csOrionPppIfConfigReqRtx."
	DEFVAL { 10 }
	::= { csOrionL2tpConfigEntry 14 }

	csOrionL2tpConfigPppRestartTimeout OBJECT-TYPE
	SYNTAX	 Integer32(1..64)
	MAX-ACCESS  read-write
	STATUS	current
	DESCRIPTION
		"This object is identical to csOrionPppIfTimeout."
	DEFVAL { 3 }
	::= { csOrionL2tpConfigEntry 15 }

	csOrionL2tpConfigPppTermReqRetransmission OBJECT-TYPE
	SYNTAX	 Integer32(0..64)
	MAX-ACCESS  read-write
	STATUS	current
	DESCRIPTION
		"This object is identical to csOrionPppIfTerminateReqRtx."
	DEFVAL { 2 }
	::= { csOrionL2tpConfigEntry 16 }

	csOrionL2tpConfigPppAuthProtocol OBJECT-TYPE
	SYNTAX	 INTEGER{
		none			(1),
		pap				(2),
		chapmd5			(3),
		mschapv1Server	(4)
		}
	MAX-ACCESS  read-write
	STATUS	current
	DESCRIPTION
		"This object is identical to csOrionPppIfConfigAuth."
	DEFVAL {none}
	::= { csOrionL2tpConfigEntry 17 }

	csOrionL2tpConfigPppReauthPeriod OBJECT-TYPE
	SYNTAX	 Integer32(0..65535)
	MAX-ACCESS  read-write
	STATUS	current
	DESCRIPTION
		"This object is identical to csOrionPppIfReauth."
	DEFVAL { 0 }
	::= { csOrionL2tpConfigEntry 18 }

	csOrionL2tpConfigPppEchoTimeout OBJECT-TYPE
	SYNTAX	 Integer32(0..65535)
	MAX-ACCESS  read-write
	STATUS	current
	DESCRIPTION
		"The echo timeout in seconds."
	DEFVAL {10}
	::= { csOrionL2tpConfigEntry 19 }

	csOrionL2tpConfigPppIpPoolName OBJECT-TYPE
	SYNTAX		DisplayString (SIZE(0..80))
	MAX-ACCESS	read-write
	STATUS		current
	DESCRIPTION
	    "The name of this address pool.  This is used
		 to identify a specific address pool."
	DEFVAL {""}
	::= { csOrionL2tpConfigEntry 20 }

	--
	-- L2TP Tunnels 
	--

	csOrionL2tpTunnelTable OBJECT-TYPE
	SYNTAX  SEQUENCE OF CsOrionL2tpTunnelEntry
	MAX-ACCESS  not-accessible
	STATUS  current
	DESCRIPTION
		"The entries in this table are the L2TP tunnels that 
		have been established with various peers."
    ::= { csOrionL2tpInfo 2 }

    csOrionL2tpTunnelEntry OBJECT-TYPE
	SYNTAX CsOrionL2tpTunnelEntry
	MAX-ACCESS not-accessible
	STATUS  current
	DESCRIPTION
		"Each entry represents a single L2TP tunnel established 
		 with a peer."
	INDEX   { csOrionGlobalVPNIndex, csOrionVPNVRouterIndex, 
			  csOrionL2tpTunnelLocalId }
	::= { csOrionL2tpTunnelTable 1 }

	CsOrionL2tpTunnelEntry ::=
	SEQUENCE {
		csOrionL2tpTunnelLocalId
			Integer32,
		csOrionL2tpTunnelMaxSessions
			Integer32,
		csOrionL2tpTunnelAuthentication
			INTEGER,
		csOrionL2tpTunnelHelloInterval
			Integer32,
		csOrionL2tpTunnelMaxRetransmissions
			Integer32,
		csOrionL2tpTunnelMaxRetransmissionTimeout
			Integer32,
		csOrionL2tpTunnelRWS
			Integer32,
		csOrionL2tpTunnelEmptyTunnelTimeout
			Integer32,
		csOrionL2tpTunnelUpTime
			Integer32,
		csOrionL2tpTunnelRemoteIpAddress
			IpAddress,
		csOrionL2tpTunnelRemoteTunnelId
			Integer32,
		csOrionL2tpTunnelRemoteUdpPort
			Integer32,
		csOrionL2tpTunnelRemoteRWS
			Integer32,
		csOrionL2tpTunnelRemoteHostname
			DisplayString,
		csOrionL2tpTunnelActiveSessionsCount
			Integer32,
		csOrionL2tpTunnelStatus
			RowStatus
	}


	csOrionL2tpTunnelLocalId OBJECT-TYPE
	SYNTAX	Integer32 (1..65535)
	MAX-ACCESS  not-accessible
	STATUS	current
	DESCRIPTION
		"Each tunnel is assigned a random locally unique 
		 identifier when the tunnel is created. The tunnel 
		 identifier can be used as an index for the tunnel table."
	::= { csOrionL2tpTunnelEntry 1 }

	csOrionL2tpTunnelMaxSessions OBJECT-TYPE
	SYNTAX	 Integer32 
	MAX-ACCESS  read-only
	STATUS	current
	DESCRIPTION
		"This object defines the maximum sessions that can be 
		 established in this tunnel.
		 NOTE : Not used at this time."
	::= { csOrionL2tpTunnelEntry 2 }

	csOrionL2tpTunnelAuthentication OBJECT-TYPE
	SYNTAX	 INTEGER{
		enable  (1),
		disable (2)
		}
	MAX-ACCESS  read-only
	STATUS	current
	DESCRIPTION
		"This object controls the tunnel authentication.
		 If set to Enable, a challenge will be sent to the peer 
		 during tunnel creation. The tunnel will be torn down 
		 if the peer does not send a valid response. 
		 Regardless of the setting, if the peer sends a challenge 
		 during tunnel creation, a response will be sent."
	::= { csOrionL2tpTunnelEntry 3 }

	csOrionL2tpTunnelHelloInterval OBJECT-TYPE
	SYNTAX	 Integer32
	MAX-ACCESS  read-only
	STATUS	current
	DESCRIPTION
		"This object defines the interval (in seconds) in
         which HELLO (or keep-alive) packets are to be sent
         to the tunnel peer. The value 0 indicates that sending of
         HELLO packets is disabled"
	::= { csOrionL2tpTunnelEntry 4 }

	csOrionL2tpTunnelMaxRetransmissions OBJECT-TYPE
	SYNTAX	 Integer32
	MAX-ACCESS  read-only
	STATUS	current
	DESCRIPTION
		"This object defines the number of retransmission's which
         the tunnel will attempt before assuming that the peer
         is no longer responding."
	::= { csOrionL2tpTunnelEntry 5 }

	csOrionL2tpTunnelMaxRetransmissionTimeout OBJECT-TYPE
	SYNTAX	 Integer32
	MAX-ACCESS  read-only
	STATUS	current
	DESCRIPTION
		"This object defines the maximum retransmission timeout
         interval in seconds which the tunnel will wait before 
		 retransmitting a control packet that has not been 
		 acknowledged."
	::= { csOrionL2tpTunnelEntry 6 }

	csOrionL2tpTunnelRWS OBJECT-TYPE
	SYNTAX	 Integer32
	MAX-ACCESS  read-only
	STATUS	current
	DESCRIPTION
		"This object defines the control channel receive window size.
         It specifies the maximum number of packets the tunnel peer 
         can send without waiting for an acknowledgement from this peer."
	::= { csOrionL2tpTunnelEntry 7 }

	csOrionL2tpTunnelEmptyTunnelTimeout OBJECT-TYPE
	SYNTAX	 Integer32
	MAX-ACCESS  read-only
	STATUS	current
	DESCRIPTION
		"This object controls the time interval in seconds after which
		 an alive but empty tunnel (i.e. a tunnel without sessions) will
		 be torn down. The value 0 indicates that the empty tunnel will
		 continue to exist until either the peer stops responding or the
		 the tunnel is torn down by peer or the administrator."
	::= { csOrionL2tpTunnelEntry 8 }

	csOrionL2tpTunnelUpTime OBJECT-TYPE
	SYNTAX	 Integer32
	MAX-ACCESS  read-only
	STATUS	current
	DESCRIPTION
		"This object indicates the number of seconds this tunnel
		 has been up since it was established."
	::= { csOrionL2tpTunnelEntry 9 }

	csOrionL2tpTunnelRemoteIpAddress OBJECT-TYPE
	SYNTAX	IpAddress
	MAX-ACCESS  read-only
	STATUS	current
	DESCRIPTION
		"This index identifies the IP Address of the peer."
	::= { csOrionL2tpTunnelEntry 10 }

	csOrionL2tpTunnelRemoteTunnelId OBJECT-TYPE
	SYNTAX	Integer32
	MAX-ACCESS  read-only
	STATUS	current
	DESCRIPTION
		"This object is the identifier assigned to the tunnel by 
		 the peer. This identifier is unique only for a given peer."
	::= { csOrionL2tpTunnelEntry 11 }

	csOrionL2tpTunnelRemoteUdpPort OBJECT-TYPE
	SYNTAX	Integer32
	MAX-ACCESS  read-only
	STATUS	current
	DESCRIPTION
		"This object identifies the UDP port that the peer is using
		 for communication."
	::= { csOrionL2tpTunnelEntry 12 }

	csOrionL2tpTunnelRemoteRWS OBJECT-TYPE
	SYNTAX	Integer32
	MAX-ACCESS  read-only
	STATUS	current
	DESCRIPTION
		"This is the control receive window size advertised by the 
		 peer during tunnel creation. It specifies the number of 
		 control packets that can be sent to the peer without waiting
		 for an acknowledgement."
	::= { csOrionL2tpTunnelEntry 13 }

	csOrionL2tpTunnelRemoteHostname OBJECT-TYPE
	SYNTAX	DisplayString
	MAX-ACCESS  read-only
	STATUS	current
	DESCRIPTION
		"This is the name that the peer used to identify itself during
		 tunnel creation"
	::= { csOrionL2tpTunnelEntry 14 }

	csOrionL2tpTunnelActiveSessionsCount OBJECT-TYPE
	SYNTAX	Integer32
	MAX-ACCESS  read-only
	STATUS	current
	DESCRIPTION
		"This is the number of sessions that are currently present within
		 this tunnel"
	::= { csOrionL2tpTunnelEntry 15 }

	csOrionL2tpTunnelStatus OBJECT-TYPE
	SYNTAX	RowStatus
	MAX-ACCESS  read-write
	STATUS	current
	DESCRIPTION
		"The row status for this table. Used only for deleting this tunnel.
		 IMPORTANT: (1) entries on this table are created when a tunnel is
					established by the peer. Therefore, creation of entry 
					thru SNMP SET request is not allowed. 
					(2) tunnel is usually torn down by the peer."
	::= { csOrionL2tpTunnelEntry 16 }

	--
	-- L2TP Sessions 
	--

	csOrionL2tpSessionTable OBJECT-TYPE
	SYNTAX  SEQUENCE OF CsOrionL2tpSessionEntry
	MAX-ACCESS  not-accessible
	STATUS  current
	DESCRIPTION
		"The entries in this table are the L2TP sessions established in a
		 specific tunnel."
    ::= { csOrionL2tpInfo 3 }

    csOrionL2tpSessionEntry OBJECT-TYPE
	SYNTAX CsOrionL2tpSessionEntry
	MAX-ACCESS not-accessible
	STATUS  current
	DESCRIPTION
		"Each entry represents a single session object in a specific tunnel."
	INDEX   { csOrionGlobalVPNIndex, csOrionVPNVRouterIndex, 
			  csOrionL2tpTunnelLocalId, csOrionL2tpSessionLocalId }
	::= { csOrionL2tpSessionTable 1 }

	CsOrionL2tpSessionEntry ::=
	SEQUENCE {
		csOrionL2tpSessionLocalId
			Integer32,
		csOrionL2tpSessionFlowControl
			INTEGER,
		csOrionL2tpSessionRWS
			Integer32,
		csOrionL2tpSessionTxQueueSize
			Integer32,
		csOrionL2tpSessionPacketSequencing
			INTEGER,
		csOrionL2tpSessionUpTime
			Integer32,
		csOrionL2tpSessionRemoteCallId
			Integer32,
		csOrionL2tpSessionRemoteFlowControl
			INTEGER,
		csOrionL2tpSessionRemoteRWS
			Integer32,
		csOrionL2tpSessionUsername
			DisplayString,
		csOrionL2tpSessionRowStatus
			RowStatus,
		csOrionL2tpSessionLocalIpAddress
			IpAddress,
		csOrionL2tpSessionRemoteIpAddress
			IpAddress,
		csOrionL2tpSessionCallType
			INTEGER,
		csOrionL2tpSessionState
			INTEGER
	}

	csOrionL2tpSessionLocalId OBJECT-TYPE
	SYNTAX	Integer32 (1..65535)
	MAX-ACCESS  not-accessible
	STATUS	current
	DESCRIPTION
		"Each session is assigned a random locally unique tunnel-specific
		 identifier when it is created. The session identifier can be used
		 as an index to identify a particular session in a tunnel."
	::= { csOrionL2tpSessionEntry 1 }

	csOrionL2tpSessionFlowControl OBJECT-TYPE
	SYNTAX	 INTEGER{
		enable  (1),
		disable (2)
		}
	MAX-ACCESS  read-only
	STATUS	current
	DESCRIPTION
		"This object will be used to control whether the peer 
		 will be requested to flow control its transmissions. 
		 Note that regardless of the setting, if the peer requests 
		 that this peer flow control its transmissions, that 
		 request will be honored. Session Flow Control was part of 
		 draft specifications but not part of the RFC. This object 
		 should be set to Enable only if all the peers are using 
		 draft implementations."
	::= { csOrionL2tpSessionEntry 2 }

	csOrionL2tpSessionRWS OBJECT-TYPE
	SYNTAX	 Integer32
	MAX-ACCESS  read-only
	STATUS	current
	DESCRIPTION
		"This object controls the size of the session receive window. 
		 It will be advertised to the peer during session setup if 
		 csOrionL2tpConfigSessionFlowControl is set to Enable.

		 The value 0 has special significance. It indicates that
		 the peer must include sequence numbers in payload packets
		 but the peer need not flow control its transmissions. This
		 can be used to force a peer that is non-RFC compliant to
		 include sequence numbers in payload packets."
	::= { csOrionL2tpSessionEntry 3 }

	csOrionL2tpSessionTxQueueSize OBJECT-TYPE
	SYNTAX	 Integer32
	MAX-ACCESS  read-only
	STATUS	current
	DESCRIPTION
		"If the peer has requested flow control and the peer's session 
		 receive window is full, packets to be sent to that peer will be 
		 held in a queue waiting for the peer's receive window to open. 
		 This object controls the size of the session-specific transmit queue."
	::= { csOrionL2tpSessionEntry 4 }

	csOrionL2tpSessionPacketSequencing OBJECT-TYPE
	SYNTAX	 INTEGER{
		enable  (1),
		disable (2)
		}
	MAX-ACCESS  read-only
	STATUS	current
	DESCRIPTION
		"This object determines whether or not session payload
         packets will be requested to be sent with sequence
         numbers from the tunnel peer."
	::= { csOrionL2tpSessionEntry 5 }

	csOrionL2tpSessionUpTime OBJECT-TYPE
	SYNTAX	 Integer32
	MAX-ACCESS  read-only
	STATUS	current
	DESCRIPTION
		"This object indicates the number of seconds this session
		 has been up since established."
	::= { csOrionL2tpSessionEntry 6 }

	csOrionL2tpSessionRemoteCallId OBJECT-TYPE
	SYNTAX	Integer32
	MAX-ACCESS  read-only
	STATUS	current
	DESCRIPTION
		"This object is the identifier assigned to the session by 
		 the peer. This identifier is unique only for a given peer 
		 in a specific tunnel."
	::= { csOrionL2tpSessionEntry 7 }

	csOrionL2tpSessionRemoteFlowControl OBJECT-TYPE
	SYNTAX	INTEGER{
		enable  (1),
		disable (2)
	}
	MAX-ACCESS  read-only
	STATUS	current
	DESCRIPTION
		"This object indicates whether flow control is requested
		 by the peer or not."
	::= { csOrionL2tpSessionEntry 8 }

	csOrionL2tpSessionRemoteRWS OBJECT-TYPE
	SYNTAX	Integer32
	MAX-ACCESS  read-only
	STATUS	current
	DESCRIPTION
		"This is the session receive window size advertised by the 
		 peer during session creation. It specifies the number of 
		 payload packets that can be sent to the peer without waiting 
		 for an acknowledgement. If this is non-zero it means that 
		 the peer has requested flow control."
	::= { csOrionL2tpSessionEntry 9 }

	csOrionL2tpSessionUsername OBJECT-TYPE
	SYNTAX	DisplayString
	MAX-ACCESS  read-only
	STATUS	current
	DESCRIPTION
		"This is the name of the user on whose behalf the session 
		was created."
	::= { csOrionL2tpSessionEntry 10 }

	csOrionL2tpSessionRowStatus OBJECT-TYPE
	SYNTAX	RowStatus
	MAX-ACCESS  read-write
	STATUS	current
	DESCRIPTION
		"The row status for this table. Used only for deleting this session.
		 IMPORTANT: (1) entries on this table are created when a session is
					established by the peer. Therefore, creation of entry
					thru SNMP SET request is not allowed.
					(2) the peer usually tears down the session."
	::= { csOrionL2tpSessionEntry 11 }

	csOrionL2tpSessionLocalIpAddress OBJECT-TYPE
	SYNTAX	IpAddress
	MAX-ACCESS  read-only
	STATUS	current
	DESCRIPTION
		"The IP address for this sesssion. It is dynamically assigned form
		 the csOrionL2tpConfigPppIpPoolName."
	::= { csOrionL2tpSessionEntry 12 }


	csOrionL2tpSessionRemoteIpAddress OBJECT-TYPE
	SYNTAX	IpAddress
	MAX-ACCESS  read-only
	STATUS	current
	DESCRIPTION
		"The IP address on the other side of this sesssion."
	::= { csOrionL2tpSessionEntry 13 }

	csOrionL2tpSessionCallType OBJECT-TYPE
	SYNTAX INTEGER {
			lacIncoming(1),
            lnsIncoming(2),
            lacOutgoing(3),
            lnsOutgoing(4)
	}
	MAX-ACCESS read-only
	STATUS current
	DESCRIPTION
		"This object indicates the type of call and the
         role this tunnel peer is providing for this
         session. For example, lacIncoming(1) indicates
         that this tunnel peer is acting as a LAC and
         generated a Incoming-Call-Request to the tunnel
         peer (the LNS). Note that tunnel peers can be
         both LAC and LNS simultaneously."
	::= { csOrionL2tpSessionEntry 14 }

	csOrionL2tpSessionState OBJECT-TYPE
	SYNTAX INTEGER {
		sessionIdle				(1),
		sessionConnecting		(2),
		sessionEstablished		(3),
		sessionDisconnecting	(4)
	}
	MAX-ACCESS read-only
	STATUS current
	DESCRIPTION
		"This object determines the current state of the session or call."
	::= { csOrionL2tpSessionEntry 15 }

	--
	-- L2TP Network Server (LNS) Configuration 
	--

	csOrionLnsConfigTable OBJECT-TYPE
	SYNTAX  SEQUENCE OF CsOrionLnsConfigEntry
	MAX-ACCESS  not-accessible
	STATUS  current
	DESCRIPTION
		"This table contains general L2TP Network Server (LNS) 
		 configuration parameters."
    ::= { csOrionL2tpInfo 4 }

    csOrionLnsConfigEntry OBJECT-TYPE
	SYNTAX CsOrionLnsConfigEntry
	MAX-ACCESS not-accessible
	STATUS  current
	DESCRIPTION
		"Each entry represents a single LNS object for a Virtual Router. 
		 There is only one instance of LNS  on a Virtual Router. This 
		 object is created along with an L2TP object when a VR is created."
	INDEX   { csOrionGlobalVPNIndex, csOrionVPNVRouterIndex }
	::= { csOrionLnsConfigTable 1 }

    CsOrionLnsConfigEntry ::=
	SEQUENCE {
		csOrionLnsConfigAdminStatus
 			INTEGER
	}

    csOrionLnsConfigAdminStatus OBJECT-TYPE
	SYNTAX	 INTEGER {
		enable  (1),
		disable (2),
		drain   (3)
		}
	MAX-ACCESS  read-write
	STATUS	current
	DESCRIPTION
		"Setting this object to 'disable' causes all tunnels
		 to be immediately disconnected and no further tunnels
		 to be either initiated or accepted. Setting this 
		 object to 'drain' will prevent any new tunnels and/or
         sessions to be either initiated or accepted but does
         NOT disconnect any active tunnels/sessions."
	DEFVAL {disable}
	::= { csOrionLnsConfigEntry 1 }

	
	--
	-- L2TP Access Concentrator (LAC) Configuration 
	--

	csOrionLacConfigTable OBJECT-TYPE
	SYNTAX  SEQUENCE OF CsOrionLacConfigEntry
	MAX-ACCESS  not-accessible
	STATUS  current
	DESCRIPTION
		"This table contains general L2TP Network Server (LNS) 
		 configuration parameters."
    ::= { csOrionL2tpInfo 5 }

    csOrionLacConfigEntry OBJECT-TYPE
	SYNTAX CsOrionLacConfigEntry
	MAX-ACCESS not-accessible
	STATUS  current
	DESCRIPTION
		"Each entry represents a single LAC object for a Virtual Router. 
		 There is only one instance of LAC  on a Virtual Router. This 
		 object is created along with an L2TP object when a VR is created."
	INDEX   { csOrionGlobalVPNIndex, csOrionVPNVRouterIndex }
	::= { csOrionLacConfigTable 1 }

    CsOrionLacConfigEntry ::=
	SEQUENCE {
		csOrionLacConfigAdminStatus
 			INTEGER
	}

    csOrionLacConfigAdminStatus OBJECT-TYPE
	SYNTAX	 INTEGER {
		enable  (1),
		disable (2),
		drain   (3)
		}
	MAX-ACCESS  read-write
	STATUS	current
	DESCRIPTION
		"Setting this object to 'disable' causes all tunnels
		 to be immediately disconnected and no further tunnels
		 to be either initiated or accepted. Setting this 
		 object to 'drain' will prevent any new tunnels and/or
         sessions to be either initiated or accepted but does
         NOT disconnect any active tunnels/sessions."
	DEFVAL {disable}
	::= { csOrionLacConfigEntry 1 }


	-- ----------------------------------------
	--	
	-- Tunnel Switching Table 
	-- (base table)
	--
	-- ----------------------------------------

	csOrionTunnelSwitchTable OBJECT-TYPE
	SYNTAX  SEQUENCE OF CsOrionTunnelSwitchEntry
	MAX-ACCESS  not-accessible
	STATUS  current
	DESCRIPTION
		"to do..."
    ::= { csOrionL2tpInfo 6 }

    csOrionTunnelSwitchEntry OBJECT-TYPE
	SYNTAX CsOrionTunnelSwitchEntry
	MAX-ACCESS not-accessible
	STATUS  current
	DESCRIPTION
		"to do..."
	INDEX   { csOrionGlobalVPNIndex, csOrionVPNVRouterIndex,
			  csOrionTunnelSwitchClientName }
	::= { csOrionTunnelSwitchTable 1 }

    CsOrionTunnelSwitchEntry ::=
	SEQUENCE {
		csOrionTunnelSwitchClientName
 			OCTET STRING,
		csOrionTunnelSwitchMode
 			INTEGER,
		csOrionTunnelSwitchRowStatus
 			RowStatus
	}

	csOrionTunnelSwitchClientName OBJECT-TYPE
	SYNTAX	OCTET STRING (SIZE(1..80))
	MAX-ACCESS  not-accessible
	STATUS	current
	DESCRIPTION
		"This object identifies the client name of the originating tunnel."
	::= { csOrionTunnelSwitchEntry 1 }

    csOrionTunnelSwitchMode OBJECT-TYPE
	SYNTAX	 INTEGER {
		passThrough  (1),	-- always switch
		authenticate (2)	-- authenticate first, and then switch
	}
	MAX-ACCESS  read-create
	STATUS	current
	DESCRIPTION
		"This object determines the switching action."
	DEFVAL {passThrough}
	::= { csOrionTunnelSwitchEntry 2 }

	csOrionTunnelSwitchRowStatus OBJECT-TYPE
	SYNTAX		RowStatus
	MAX-ACCESS	read-create
	STATUS		current
	DESCRIPTION
		"."
	::= { csOrionTunnelSwitchEntry 3 }


	--
	-- Tunnel Target Table 
	-- (expansion of csOrionTunnelSwitchTable)
	--

	csOrionTunnelSwitchTargetTable OBJECT-TYPE
	SYNTAX  SEQUENCE OF CsOrionTunnelSwitchTargetEntry
	MAX-ACCESS  not-accessible
	STATUS  current
	DESCRIPTION
		"."
    ::= { csOrionL2tpInfo 7 }

    csOrionTunnelSwitchTargetEntry OBJECT-TYPE
	SYNTAX CsOrionTunnelSwitchTargetEntry
	MAX-ACCESS not-accessible
	STATUS  current
	DESCRIPTION
		"."
	INDEX   { csOrionGlobalVPNIndex, csOrionVPNVRouterIndex,
			  csOrionTunnelSwitchClientName, csOrionTunnelSwitchTargetIpAddress }
	::= { csOrionTunnelSwitchTargetTable 1 }

    CsOrionTunnelSwitchTargetEntry ::=
	SEQUENCE {
		csOrionTunnelSwitchTargetIpAddress
 			IpAddress,
		csOrionTunnelSwitchTargetPriority
 			Integer32,
		csOrionTunnelSwitchTargetMaxSession
 			Integer32,
		csOrionTunnelSwitchTargetSessionCount
 			Counter32,			
		csOrionTunnelSwitchTargetRowStatus
 			RowStatus
	}

    csOrionTunnelSwitchTargetIpAddress OBJECT-TYPE
	SYNTAX	 IpAddress 
	MAX-ACCESS  not-accessible
	STATUS	current
	DESCRIPTION
		"This object identifies the IP address of the destination LNS."
	::= { csOrionTunnelSwitchTargetEntry 1 }

	csOrionTunnelSwitchTargetPriority OBJECT-TYPE
	SYNTAX	Integer32(1..65535)
	MAX-ACCESS  read-create
	STATUS	current
	DESCRIPTION
		"This object determines the priority of this target address.
		 Priority value 1 being the highest."
	DEFVAL { 65535 }  -- lowest
	::= { csOrionTunnelSwitchTargetEntry 2 }

	csOrionTunnelSwitchTargetMaxSession OBJECT-TYPE
	SYNTAX	Integer32(1..65535)
	MAX-ACCESS  read-create
	STATUS	current
	DESCRIPTION
		"This object determines the maximum number of sessions that
		 can be handled by this target address."
	DEFVAL { 256 }
	::= { csOrionTunnelSwitchTargetEntry 3 }

	csOrionTunnelSwitchTargetSessionCount OBJECT-TYPE
	SYNTAX	Counter32
	MAX-ACCESS  read-only
	STATUS	current
	DESCRIPTION
		"This object keeps the count of the active sessions on
		 this target address."
	::= { csOrionTunnelSwitchTargetEntry 4 }

	csOrionTunnelSwitchTargetRowStatus OBJECT-TYPE
	SYNTAX		RowStatus
	MAX-ACCESS	read-create
	STATUS		current
	DESCRIPTION
		"Row status for this table."
	::= { csOrionTunnelSwitchTargetEntry 5 }


	--
	-- L2TP Base Status and Statistics Table
	--
    --   This table contains objects that can be used to desribe
    --   the current status and statistics of an L2TP object.
	--

	csOrionL2tpStatsTable OBJECT-TYPE
	SYNTAX  SEQUENCE OF CsOrionL2tpStatsEntry
	MAX-ACCESS  not-accessible
	STATUS  current
	DESCRIPTION
		"The L2TP Status and Statistics table."
    ::= { csOrionL2tpInfo 8 }

    csOrionL2tpStatsEntry OBJECT-TYPE
	SYNTAX CsOrionL2tpStatsEntry
	MAX-ACCESS not-accessible
	STATUS  current
	DESCRIPTION
		"An L2TP Stats entry. An entry in this table 
		 may correspond to a single endpoint or a group of
         tunnel endpoints."
	INDEX   { csOrionGlobalVPNIndex, csOrionVPNVRouterIndex }
	::= { csOrionL2tpStatsTable 1 }

    CsOrionL2tpStatsEntry ::=
	SEQUENCE {
		       csOrionL2tpStatsTotalTunnels
                   Counter32,
               csOrionL2tpStatsFailedTunnels
                   Counter32,
               csOrionL2tpStatsFailedAuthentications
                   Counter32,
               csOrionL2tpStatsActiveTunnels
                   Gauge32,
               csOrionL2tpStatsTotalSessions
                   Counter32,
               csOrionL2tpStatsFailedSessions
                   Counter32,
               csOrionL2tpStatsActiveSessions
                   Gauge32,
               csOrionL2tpStatsDrainingTunnels
                   INTEGER,
               csOrionL2tpStatsControlRecvOctets	-- not ready
                   Counter32,
               csOrionL2tpStatsControlRecvPackets
                   Counter32,
               csOrionL2tpStatsControlSendOctets	-- not ready
                   Counter32,
               csOrionL2tpStatsControlSendPackets
                   Counter32,
               csOrionL2tpStatsPayloadRecvOctets	-- ??
                   Counter32,
               csOrionL2tpStatsPayloadRecvPackets
                   Counter32,
               csOrionL2tpStatsPayloadRecvDiscards
                   Counter32,
               csOrionL2tpStatsPayloadSendOctets	-- not ready
                   Counter32,
               csOrionL2tpStatsPayloadSendPackets
                   Counter32
	}

   csOrionL2tpStatsTotalTunnels OBJECT-TYPE
           SYNTAX          Counter32
           MAX-ACCESS      read-only
           STATUS          current
           DESCRIPTION
              "This object returns the total number of tunnels
               that have successfully reached the established
               state."
           ::= { csOrionL2tpStatsEntry 1 }

   csOrionL2tpStatsFailedTunnels OBJECT-TYPE
           SYNTAX          Counter32
           MAX-ACCESS      read-only
           STATUS          current
           DESCRIPTION
              "This object returns the number of tunnels that
               failed to reach the established state."
           ::= { csOrionL2tpStatsEntry 2 }

   csOrionL2tpStatsFailedAuthentications OBJECT-TYPE
           SYNTAX          Counter32
           MAX-ACCESS      read-only
           STATUS          current
           DESCRIPTION
              "This object returns the number of failed tunnel
               connection attempts because the tunnel peer
			   failed authentication."
           ::= { csOrionL2tpStatsEntry 3 }

   csOrionL2tpStatsActiveTunnels OBJECT-TYPE
           SYNTAX          Gauge32
           MAX-ACCESS      read-only
           STATUS          current
           DESCRIPTION
              "This object returns the number of tunnels that
               are currently active."
           ::= { csOrionL2tpStatsEntry 4 }

   csOrionL2tpStatsTotalSessions OBJECT-TYPE
           SYNTAX          Counter32
           MAX-ACCESS      read-only
           STATUS          current
           DESCRIPTION
              "This object returns the total number of sessions
               that have successfully reached the established state."
           ::= { csOrionL2tpStatsEntry 5}

   csOrionL2tpStatsFailedSessions OBJECT-TYPE
           SYNTAX          Counter32
           MAX-ACCESS      read-only
           STATUS          current
           DESCRIPTION
              "This object returns the number of sessions that
               failed to reach the established state."
           ::= { csOrionL2tpStatsEntry 6 }

   csOrionL2tpStatsActiveSessions OBJECT-TYPE
           SYNTAX          Gauge32
           MAX-ACCESS      read-only
           STATUS          current
           DESCRIPTION
              "This object returns the number of sessions that
               are currently active."
           ::= { csOrionL2tpStatsEntry 7 }

   csOrionL2tpStatsDrainingTunnels OBJECT-TYPE
           SYNTAX          INTEGER {
                               yes(1),
                               no(2)
                           }
           MAX-ACCESS      read-only
           STATUS          current
           DESCRIPTION
              "This object indicates if this L2TP is draining
               off sessions from all tunnels. This object will
               return no(2) when the domain is not draining sessions
               or after the last L2TP session has disconnected when
               the domain is in the draining state."
           ::= { csOrionL2tpStatsEntry 8 }

   csOrionL2tpStatsControlRecvOctets OBJECT-TYPE
           SYNTAX          Counter32
           MAX-ACCESS      read-only
           STATUS          current
           DESCRIPTION
              "This object returns the number of control channel
               octets received.
			   NOTE : This is not currently supported. It will just
					  return zero. [Alan 10/12/2000]"
           ::= { csOrionL2tpStatsEntry 9 }

   csOrionL2tpStatsControlRecvPackets OBJECT-TYPE
           SYNTAX          Counter32
           MAX-ACCESS      read-only
           STATUS          current
           DESCRIPTION
              "This object returns the number of control packets
               received."
           ::= { csOrionL2tpStatsEntry 10 }

   csOrionL2tpStatsControlSendOctets OBJECT-TYPE
           SYNTAX          Counter32
           MAX-ACCESS      read-only
           STATUS          current
           DESCRIPTION
              "This object returns the number of control channel
               octets that were transmitted to tunnel endpoints.
			   NOTE : This is not currently supported. It will just
					  return zero. [Alan 10/12/2000]"
           ::= { csOrionL2tpStatsEntry 11 }

   csOrionL2tpStatsControlSendPackets OBJECT-TYPE
           SYNTAX          Counter32
           MAX-ACCESS      read-only
           STATUS          current
           DESCRIPTION
              "This object returns the number of control packets
               that were transmitted to tunnel endpoints."
           ::= { csOrionL2tpStatsEntry 12 }

   csOrionL2tpStatsPayloadRecvOctets OBJECT-TYPE
           SYNTAX          Counter32
           MAX-ACCESS      read-only
           STATUS          current
           DESCRIPTION
              "This object returns the number of payload channel
               octets that were received."
           ::= { csOrionL2tpStatsEntry 13 }

   csOrionL2tpStatsPayloadRecvPackets OBJECT-TYPE
           SYNTAX          Counter32
           MAX-ACCESS      read-only
           STATUS          current
           DESCRIPTION
              "This object returns the number of payload packets
               that were received."
           ::= { csOrionL2tpStatsEntry 14 }

   csOrionL2tpStatsPayloadRecvDiscards OBJECT-TYPE
           SYNTAX          Counter32
           MAX-ACCESS      read-only
           STATUS          current
           DESCRIPTION
              "This object returns the number of received payload
               packets that were discarded."
           ::= { csOrionL2tpStatsEntry 15 }

   csOrionL2tpStatsPayloadSendOctets OBJECT-TYPE
           SYNTAX          Counter32
           MAX-ACCESS      read-only
           STATUS          current
           DESCRIPTION
              "This object returns the number of payload channel
               octets that were transmitted to tunnel peers.
			   NOTE : This is not currently supported. It will just
					  return zero. [Alan 10/12/2000]"
           ::= { csOrionL2tpStatsEntry 16 }

   csOrionL2tpStatsPayloadSendPackets OBJECT-TYPE
           SYNTAX          Counter32
           MAX-ACCESS      read-only
           STATUS          current
           DESCRIPTION
              "This object returns the number of payload packets
               that were transmitted to tunnel peers."
           ::= { csOrionL2tpStatsEntry 17 }


   --
   --      The L2TP Tunnel Status and Statisticss Table
   --
   --      This table contains objects that can be used to describe
   --      the current status and statistics of a single L2TP tunnel.


   csOrionL2tpTunnelStatsTable    OBJECT-TYPE
           SYNTAX          SEQUENCE OF CsOrionL2tpTunnelStatsEntry
           MAX-ACCESS      not-accessible
           STATUS          current
           DESCRIPTION
              "The L2TP tunnel status and statistics table."
           ::= { csOrionL2tpInfo 9 }

   csOrionL2tpTunnelStatsEntry    OBJECT-TYPE
           SYNTAX          CsOrionL2tpTunnelStatsEntry
           MAX-ACCESS      not-accessible
           STATUS          current
           DESCRIPTION
              "An L2TP tunnel interface stats entry."
           INDEX { csOrionGlobalVPNIndex, csOrionVPNVRouterIndex, 
				   csOrionL2tpTunnelLocalId }
           ::= { csOrionL2tpTunnelStatsTable 1 }

   CsOrionL2tpTunnelStatsEntry ::=
           SEQUENCE {
               csOrionL2tpTunnelStatsState
                   INTEGER,
               csOrionL2tpTunnelStatsTotalSessions
                   Counter32,
               csOrionL2tpTunnelStatsFailedSessions
                   Counter32,
               csOrionL2tpTunnelStatsActiveSessions
                   Gauge32
           }

   csOrionL2tpTunnelStatsState    OBJECT-TYPE
           SYNTAX          INTEGER {
                               tunnelIdle(1),
                               tunnelConnecting(2),
                               tunnelEstablished(3),
                               tunnelDisconnecting(4)
                           }
           MAX-ACCESS      read-only
           STATUS          current
           DESCRIPTION
              "This field contains the current state of the control
               tunnel."
           ::= { csOrionL2tpTunnelStatsEntry 1 }

   csOrionL2tpTunnelStatsTotalSessions OBJECT-TYPE
           SYNTAX          Counter32
           MAX-ACCESS      read-only
           STATUS          current
           DESCRIPTION
              "This object contains the total number of sessions
               that this tunnel has successfully connected through
               to its tunnel peer since this tunnel was created."
           ::= { csOrionL2tpTunnelStatsEntry 2 }

   csOrionL2tpTunnelStatsFailedSessions OBJECT-TYPE
           SYNTAX          Counter32
           MAX-ACCESS      read-only
           STATUS          current
           DESCRIPTION
              "This object contains the total number of sessions
               that were initiated but failed to reach the
               established phase.
			   NOTE : This is not currently supported. It will just
					  return zero. [Alan 10/12/2000]"
           ::= { csOrionL2tpTunnelStatsEntry 3 }

   csOrionL2tpTunnelStatsActiveSessions OBJECT-TYPE
           SYNTAX          Gauge32
           MAX-ACCESS      read-only
           STATUS          current
           DESCRIPTION
              "This object contains the total number of sessions
               in the established state for this tunnel.
			   NOTE : This is not currently supported. It will just
					  return zero. [Alan 10/12/2000]"
           ::= { csOrionL2tpTunnelStatsEntry 4 }


------------------------------------------------------------------------------
--
--	        QOS Control Info    
--
------------------------------------------------------------------------------

--
-- DS Byte Filter Info
--

    csOrionDsByteFilterInfo	OBJECT IDENTIFIER ::= { csOrionQosInfo 1 }



    csOrionVrDsByteFilterTable OBJECT-TYPE
	SYNTAX	SEQUENCE OF CsOrionVrDsByteFilterEntry
	MAX-ACCESS  not-accessible
	STATUS	current
	DESCRIPTION
	    "This table specifies a set of acl's to be applied to
	    packets received by (and sent from) this virtual
	    router.  The first entry whose acl matches a packet causes
	    the DS Byte field of the packet to be set to the value
	    specified in the table entry.  If no entry's acl matches
	    the packet, the DS Byte field of the packet will be set
	    to the value specified in csOrionVPNVRouterIpDsByte."
	::= { csOrionDsByteFilterInfo 1 }

    csOrionVrDsByteFilterEntry OBJECT-TYPE
	SYNTAX 	 CsOrionVrDsByteFilterEntry
	MAX-ACCESS  not-accessible
	STATUS	current
	DESCRIPTION
	    "Each entry specifies whether packets satisfying a specific
	    access list entry will have their DS Byte field set to the
	    value indicated in the table entry."
	INDEX { csOrionGlobalVPNIndex, csOrionVPNVRouterIndex, 
		csOrionVrDsByteFilterIndex }
	::= { csOrionVrDsByteFilterTable 1 }

    CsOrionVrDsByteFilterEntry ::=
	SEQUENCE {
	csOrionVrDsByteFilterIndex
		Integer32,
	csOrionVrDsByteFilterAclId
		Integer32,
	csOrionVrDsByteFilterAction
		INTEGER,
	csOrionVrDsByteFilterValue
		Integer32,
	csOrionVrDsByteFilterDirection
		INTEGER,
	csOrionVrDsByteFilterRowStatus
		RowStatus
	}

    csOrionVrDsByteFilterIndex OBJECT-TYPE
	SYNTAX		Integer32 (1..65535)
	MAX-ACCESS	not-accessible
	STATUS		current
	DESCRIPTION
	    "The Index of this particular Packet Filter."
	::= { csOrionVrDsByteFilterEntry 1 }

    csOrionVrDsByteFilterAclId OBJECT-TYPE
	SYNTAX		Integer32 (0..65535)
	MAX-ACCESS	read-create
	STATUS		current
	DESCRIPTION
	    "The Id of an access list entry (from csOrionGenAclTable).
	    All packets transmitted or received on any of the virtual 
	    interfaces on this virtual router that satisfy that access 
	    list entry are acted upon by this filter."
	::= { csOrionVrDsByteFilterEntry 2 }

    csOrionVrDsByteFilterAction OBJECT-TYPE
	SYNTAX		INTEGER {
		setValue	(1)
	}
	MAX-ACCESS	read-create
	STATUS		current
	DESCRIPTION
	    "The action performed by this filter."
	DEFVAL { setValue }
	::= { csOrionVrDsByteFilterEntry 3 }

    csOrionVrDsByteFilterValue OBJECT-TYPE
	SYNTAX		Integer32 (0..256)
	MAX-ACCESS  read-create
	STATUS  current
	DESCRIPTION
		"This object defines the values to be placed in the TypeOfService
		octet of each IP packet sent out or forwarded by the VR. The valid 
		range covers both 7-bit configurations recommended in RFC 1349 
		(Precedence and TOS bits) and 6-bit configurations recommended 
		in RFC 2474 (Differentiated Services). If the value selected 
		is 256, the DsByte is not changed and packets are forwarded with 
		their existing TypeOfService byte value."
	DEFVAL { 256 }
	::= { csOrionVrDsByteFilterEntry 4 }

    csOrionVrDsByteFilterDirection OBJECT-TYPE
	SYNTAX		INTEGER {
		in	(1),
		out	(2)
	} 
	MAX-ACCESS	read-create
	STATUS		current
	DESCRIPTION
	    "The direction of packets on which this filter is applied."
	::= { csOrionVrDsByteFilterEntry 5 }
	
    csOrionVrDsByteFilterRowStatus OBJECT-TYPE
	SYNTAX		RowStatus
	MAX-ACCESS	read-create
	STATUS		current
	DESCRIPTION
	    "A row status type for this Table entry."
	::= { csOrionVrDsByteFilterEntry 6 }


--
-- This table specifies a set of packet filters applied on a specific
-- virtual interface.
--

    csOrionViDsByteFilterTable OBJECT-TYPE
	SYNTAX	SEQUENCE OF CsOrionViDsByteFilterEntry
	MAX-ACCESS  not-accessible
	STATUS	current
	DESCRIPTION
	    "This table specifies a set of acl's to be applied to
	    packets received over (or sent out) each the interfaces 
	    belonging to this virtual router.  The first entry 
	    whose acl matches a packet causes the DS Byte field of the 
	    packet to be set to the value specified in the table entry.  
	    If no entry's acl matches the packet, the DS Byte field of 
	    the packet will be set to the value specified in 
	    csOrionVPNVRouterIpDsByte."
	::= { csOrionDsByteFilterInfo 2 }

    csOrionViDsByteFilterEntry OBJECT-TYPE
	SYNTAX 	 CsOrionViDsByteFilterEntry
	MAX-ACCESS  not-accessible
	STATUS	current
	DESCRIPTION
	    "Each filter specifies whether packets satisfying a specific
	    access list entry are permitted or denied to be passed along
	    their route."
	INDEX { csOrionGlobalVPNIndex, csOrionVPNVRouterIndex, csOrionVIfIndex,
		csOrionViDsByteFilterIndex }
	::= { csOrionViDsByteFilterTable 1 }

    CsOrionViDsByteFilterEntry ::=
	SEQUENCE {
	csOrionViDsByteFilterIndex
		Integer32,
	csOrionViDsByteFilterAclId
		Integer32,
	csOrionViDsByteFilterAction
		INTEGER,
	csOrionViDsByteFilterValue
		Integer32,
	csOrionViDsByteFilterDirection
		INTEGER,
	csOrionViDsByteFilterRowStatus
		RowStatus
	}

    csOrionViDsByteFilterIndex OBJECT-TYPE
	SYNTAX		Integer32 (1..65535)
	MAX-ACCESS	not-accessible
	STATUS		current
	DESCRIPTION
	    "The Index of this particular Packet Filter."
	::= { csOrionViDsByteFilterEntry 1 }

    csOrionViDsByteFilterAclId OBJECT-TYPE
	SYNTAX		Integer32 (0..65535)
	MAX-ACCESS	read-create
	STATUS		current
	DESCRIPTION
	    "The Id of an access list entry (from csOrionGenAclTable).
	    All packets transmitted or received on this virtual interface
	    that access list entry are acted upon by this filter."
	::= { csOrionViDsByteFilterEntry 2 }

    csOrionViDsByteFilterAction OBJECT-TYPE
	SYNTAX		INTEGER {
		setValue	(1)
	}
	MAX-ACCESS	read-create
	STATUS		current
	DESCRIPTION
	    "The action performed by this filter."
	DEFVAL { setValue }
	::= { csOrionViDsByteFilterEntry 3 }

    csOrionViDsByteFilterValue OBJECT-TYPE
	SYNTAX		Integer32 (0..256)
	MAX-ACCESS  read-create
	STATUS  current
	DESCRIPTION
		"This object defines the values to be placed in the TypeOfService
		octet of each IP packet sent out or forwarded by the VR. The valid 
		range covers both 7-bit configurations recommended in RFC 1349 
		(Precedence and TOS bits) and 6-bit configurations recommended 
		in RFC 2474 (Differentiated Services). If the value selected 
		is 256, the DsByte is not changed and packets are forwarded with 
		their existing TypeOfService byte value."
	DEFVAL { 256 }
	::= { csOrionViDsByteFilterEntry 4 }

    csOrionViDsByteFilterDirection OBJECT-TYPE
	SYNTAX		INTEGER {
		in	(1),
		out	(2)
	} 
	MAX-ACCESS	read-create
	STATUS		current
	DESCRIPTION
	    "The direction of packets on which this filter is applied."
	::= { csOrionViDsByteFilterEntry 5 }
	
    csOrionViDsByteFilterRowStatus OBJECT-TYPE
	SYNTAX		RowStatus
	MAX-ACCESS	read-create
	STATUS		current
	DESCRIPTION
	    "A row status type for this Table entry."
	::= { csOrionViDsByteFilterEntry 6 }








------------------------------------------------------------------------------
--
--	       PPPoE
--
------------------------------------------------------------------------------

	csPppoeAcConfig	    OBJECT IDENTIFIER ::= { csOrionPppoeInfo 1 }
    csPppoeSession	    OBJECT IDENTIFIER ::= { csOrionPppoeInfo 2 }
	csPppoeStatistics   OBJECT IDENTIFIER ::= { csOrionPppoeInfo 3 }

	--
    --     PPPoE Access Concentrator Table
	--

	csPppoeAcIfConfigTable OBJECT-TYPE
    SYNTAX   SEQUENCE OF CsPppoeAcIfConfigEntry
    MAX-ACCESS   not-accessible
    STATUS   current
    DESCRIPTION
        "PPPoE Access Concentrators in given sub-interface (of ATM or FR)."
    ::= { csPppoeAcConfig 1 }

    csPppoeAcIfConfigEntry OBJECT-TYPE
    SYNTAX      CsPppoeAcIfConfigEntry
    MAX-ACCESS  not-accessible
    STATUS      current
    DESCRIPTION 
        "This list contains PPPoE Access Concentrator Servers."
    INDEX { csPppoeAcIfSlotIndex, csPppoeAcIfPortIndex,
				 csPppoeAcIfChannelIndex, csPppoeAcIfSubIfIndex }
	::= { csPppoeAcIfConfigTable 1 }

    CsPppoeAcIfConfigEntry ::=
	SEQUENCE {
	csPppoeAcIfSlotIndex
		Integer32,
	csPppoeAcIfPortIndex
		Integer32,
	csPppoeAcIfChannelIndex
		Integer32,
	csPppoeAcIfSubIfIndex
		Integer32,
	csPppoeAcIfConfigMaxSessions
		Integer32,
	csPppoeAcIfConfigMaxSessionsPerHost
		Integer32,
	csPppoeAcIfConfigTotalSessions
		Integer32,
	csPppoeAcIfConfigTotalActiveSessions
	    	Integer32,		
	csPppoeAcIfConfigPortEthernetAddress
		OCTET STRING,
	csPppoeAcIfConfigVolunteerServiceAdvertising
		INTEGER,
	csPppoeAcIfConfigName
		DisplayString,
	-- csPppoeAcIfConfigAccessVPN
    --     Integer32,
    -- csPppoeAcIfConfigAccessVR
    --     IpAddress,
	csPppoeAcIfConfigAdminStatus
		INTEGER,
	csPppoeAcIfConfigOperStatus
		OperStatus,
    csPppoeAcIfConfigServiceTemplateProfile
        DisplayString,
    csPppoeConfigPppIfAuth
        INTEGER
	}

	csPppoeAcIfSlotIndex OBJECT-TYPE
	SYNTAX	    Integer32 (1..'7fffffff'h)
	MAX-ACCESS  not-accessible
	STATUS	    current
	DESCRIPTION
	       "This object identifies the blade to which this instance
		   of AC is created."
	::= { csPppoeAcIfConfigEntry 1 }

	csPppoeAcIfPortIndex OBJECT-TYPE
	SYNTAX	    Integer32 (1..'7fffffff'h)
	MAX-ACCESS  not-accessible
	STATUS	    current
	DESCRIPTION
	       "This object identifies the port in the blade csPppoeAcIfSlotIndex
		   to which this instance of AC is created."
	::= { csPppoeAcIfConfigEntry 2 }

	csPppoeAcIfChannelIndex OBJECT-TYPE
	SYNTAX	    Integer32 (0..'7fffffff'h)
	MAX-ACCESS  not-accessible
	STATUS	    current
	DESCRIPTION
	       "This object identifies the channel number."
	::= { csPppoeAcIfConfigEntry 3 }

    csPppoeAcIfSubIfIndex OBJECT-TYPE
	SYNTAX	    Integer32 (1..'7fffffff'h)
	MAX-ACCESS  not-accessible
	STATUS	    current
	DESCRIPTION
	       "This object identifies the sub-if number."
	::= { csPppoeAcIfConfigEntry 4 }

	csPppoeAcIfConfigMaxSessions OBJECT-TYPE
	SYNTAX	    Integer32 (1..64)
	MAX-ACCESS  read-write
	STATUS	    current
	DESCRIPTION
	    "Maximum sesions that it can accepted on this AC." 
	DEFVAL{ 8 }
	::= { csPppoeAcIfConfigEntry 5 }

	csPppoeAcIfConfigMaxSessionsPerHost OBJECT-TYPE
	SYNTAX	    Integer32 (1..8)
	MAX-ACCESS  read-write
	STATUS	    current
	DESCRIPTION
	    "Maximum number of sessions that this AC can accept
	     from a given host." 
	DEFVAL{ 2 }
	::= { csPppoeAcIfConfigEntry 6 }

	csPppoeAcIfConfigTotalSessions OBJECT-TYPE
	SYNTAX	    Integer32
	MAX-ACCESS  read-only
	STATUS	    current
	DESCRIPTION
	    "Total Number of sessions established with this AC
	     subjecting to maximum of csPppoeAcIfConfigMaxSessions."
	::= { csPppoeAcIfConfigEntry 7 }

	csPppoeAcIfConfigTotalActiveSessions OBJECT-TYPE
	SYNTAX	    Integer32
	MAX-ACCESS  read-only
	STATUS	    current
	DESCRIPTION
	    "Total Number of active sessions in this AC."
	::= { csPppoeAcIfConfigEntry 8 }

	csPppoeAcIfConfigPortEthernetAddress OBJECT-TYPE
	SYNTAX      OCTET STRING (SIZE(6))
	MAX-ACCESS  read-only
	STATUS	    current
	DESCRIPTION
	    "This object conatins the MAC Address of this PPPoE AC." 
	::= { csPppoeAcIfConfigEntry 9 }

	csPppoeAcIfConfigVolunteerServiceAdvertising OBJECT-TYPE
	SYNTAX	INTEGER {
			enable (1),
			disable (2)
	}
	MAX-ACCESS  read-write
	STATUS	    current
	DESCRIPTION
	    "If this object contains  'enable' then it advertise
	     service profiles in PADO packets"
	DEFVAL{ enable }
	::= { csPppoeAcIfConfigEntry 10 }

	csPppoeAcIfConfigName OBJECT-TYPE
	SYNTAX	    DisplayString (SIZE(0..32))
	MAX-ACCESS  read-write
	STATUS	    current
	DESCRIPTION
	    "This object conatins the name of this PPPoE AC."
	DEFVAL{ "" }
	::= { csPppoeAcIfConfigEntry 11 }

	--csPppoeAcIfConfigAccessVPN OBJECT-TYPE
	--SYNTAX	Integer32 
	--MAX-ACCESS  read-only
	--STATUS	current
	--DESCRIPTION
	--    "This object contains the VPN number in which this PPPoE AC is
    --     managed." 
	--::= { csPppoeAcIfConfigEntry 12 }

	--csPppoeAcIfConfigAccessVR OBJECT-TYPE
	--SYNTAX	    IpAddress 
	--MAX-ACCESS  read-only
	--STATUS	    current
	--DESCRIPTION
	--    "This object contains the VR Identifier in which this PPPoE AC is
    --     managed." 
	--::= { csPppoeAcIfConfigEntry 13 }"

	csPppoeAcIfConfigAdminStatus OBJECT-TYPE
	SYNTAX	INTEGER {
			enable (1),
			disable (2)
	}
	MAX-ACCESS  read-write
	STATUS	    current
	DESCRIPTION
	    "This object is used to enable or disable this PPPoE AC." 
	DEFVAL{ disable }
	::= { csPppoeAcIfConfigEntry 12 }

	csPppoeAcIfConfigOperStatus OBJECT-TYPE
	SYNTAX	    OperStatus
	MAX-ACCESS  read-only
	STATUS	    current
	DESCRIPTION
	    "This object contains operational status of PPPoE AC. This
	     object value depends on operational status of corresponding
	     underneath interface." 
	::= { csPppoeAcIfConfigEntry 13 }
    
	csPppoeAcIfConfigServiceTemplateProfile OBJECT-TYPE
	SYNTAX	    DisplayString
	MAX-ACCESS  read-write
	STATUS	    current
	DESCRIPTION
	    "This object contains service template, a list of connection profiles,
        serves the purpose of service name concept in PPPOE AC."
    DEFVAL{""}     
	::= { csPppoeAcIfConfigEntry 14 }
    
    csPppoeConfigPppIfAuth OBJECT-TYPE
	SYNTAX  INTEGER {
		none			(1),
		pap				(2),
		chapmd5			(3),
		mschapv1Server	(4)
	}
	MAX-ACCESS  read-write
	STATUS  current
	DESCRIPTION
		"The type of authentication used by PPP over pppoe sessions on this
		 PPPoE AC server."
	DEFVAL { chapmd5 }
	::= { csPppoeAcIfConfigEntry 15 }



	--
	--
    --     PPPoE Session Table
	--

	csPppoeSessionTable OBJECT-TYPE
    SYNTAX       SEQUENCE OF CsPppoeSessionEntry
    MAX-ACCESS   not-accessible
    STATUS       current
    DESCRIPTION
        "This is the list of all PPPoE sessions in a given PPPoE
	     Access Concentrator Server."
         ::= { csPppoeSession 1}

    csPppoeSessionEntry OBJECT-TYPE
    SYNTAX      CsPppoeSessionEntry
    MAX-ACCESS  not-accessible
    STATUS      current
    DESCRIPTION
        "This list contains PPPoE Sessions in a given Access Concentrator Server."
    INDEX { csPppoeAcIfSlotIndex,     csPppoeAcIfPortIndex,
		    csPppoeAcIfChannelIndex,  csPppoeAcIfSubIfIndex,
		    csPppoeSessionId }
	     ::= { csPppoeSessionTable 1 }

    CsPppoeSessionEntry ::=
	SEQUENCE {
	csPppoeSessionId
		Integer32,
	csPppoeSessionUserName
	   DisplayString,
	csPppoeSessionOperStatus
		OperStatus,
	csPppoeSessionPeerAddress
		OCTET STRING,		
	csPppoeSessionServiceName
		DisplayString,
	csPppoeSessionDuration
		Integer32,
    csPppoeSessionIPPoolNameInUse
        DisplayString,
    csPppoeSessionServiceVPN 
        Integer32,
    csPppoeSessionServiceVR
        IpAddress,
	csPppoeSessionReceivedPkts
		Counter32,
	csPppoeSessionReceivedOctets
		Counter32,
	csPppoeSessionTranmittedPkts
		Counter32,
	csPppoeSessionTransmittedOctets
		Counter32,
	csPppoeSessionReceiveOperDown
		Counter32,
	csPppoeSessionTransmitOperDown
		Counter32,
    csPppoeSessionReceivedErrors
        Counter32,
	csPppoeSessionRowStatus
		RowStatus
	}

	csPppoeSessionId OBJECT-TYPE
	SYNTAX	    Integer32 
	MAX-ACCESS  not-accessible
	STATUS	    current
	DESCRIPTION
	    "This object contains the session identifier for this session
	     as assigned by the PPPoE AC in the PADS message." 
	::= { csPppoeSessionEntry 2 }

	csPppoeSessionUserName OBJECT-TYPE
	SYNTAX	    DisplayString
	MAX-ACCESS  read-only
	STATUS	    current
	DESCRIPTION
	    "This object contains the user name for this session."
	::= { csPppoeSessionEntry 1 }

	csPppoeSessionOperStatus OBJECT-TYPE
	SYNTAX	    OperStatus
	MAX-ACCESS  read-only
	STATUS	    current
	DESCRIPTION
	    "This object contains the operational status for this session."
	::= { csPppoeSessionEntry 3 }

	csPppoeSessionPeerAddress OBJECT-TYPE
	SYNTAX	    OCTET STRING (SIZE(6)) 
	MAX-ACCESS  read-only
	STATUS	    current
	DESCRIPTION
	    "This object contains the MAC address for this session peer."
	::= { csPppoeSessionEntry 4 }

	csPppoeSessionServiceName OBJECT-TYPE
	SYNTAX	    DisplayString
	MAX-ACCESS  read-only
	STATUS	    current
	DESCRIPTION
	    "This object contains the service name for which this session
	     is established." 
	::= { csPppoeSessionEntry 5 }

	csPppoeSessionDuration OBJECT-TYPE
	SYNTAX	Integer32  
	-- need to decide, but print format should be like
	-- hh:mm:ss   
	MAX-ACCESS  read-only
	STATUS	current
	DESCRIPTION
	    "This object contains the duration for this session since its
	     establishment."
	::= { csPppoeSessionEntry 6 }

	csPppoeSessionIPPoolNameInUse OBJECT-TYPE
	SYNTAX	DisplayString  
	MAX-ACCESS  read-only
	STATUS	current
	DESCRIPTION
	    "This object contains the IP Address Pool Name which is used to
         dynamically allocate IP Addresses."
	::= { csPppoeSessionEntry 7 }

	csPppoeSessionServiceVPN OBJECT-TYPE
	SYNTAX	Integer32 
	MAX-ACCESS  read-only
	STATUS	current
	DESCRIPTION
	    "This object contains the VPN number in which this PPPoE-Session is
         being served." 
	::= { csPppoeSessionEntry 8 }

	csPppoeSessionServiceVR OBJECT-TYPE
	SYNTAX	IpAddress 
	MAX-ACCESS  read-only
	STATUS	current
	DESCRIPTION
	       "This object contains the VR Identifier in which this PPPoE Session is
           Served." 
	::= { csPppoeSessionEntry 9 }    

	csPppoeSessionReceivedPkts OBJECT-TYPE
	SYNTAX	Counter32 
	MAX-ACCESS  read-only
	STATUS	current
	DESCRIPTION
	       "This object contains the number of session packets received by
	       this PPPoE Session."
	::= { csPppoeSessionEntry 10 }

	csPppoeSessionReceivedOctets OBJECT-TYPE
	SYNTAX	Counter32 
	MAX-ACCESS  read-only
	STATUS	current
	DESCRIPTION
	       "This object contains the number of session octets received by
	       this PPPoE Session."
	::= { csPppoeSessionEntry 11 }

	csPppoeSessionTranmittedPkts OBJECT-TYPE
	SYNTAX	Counter32 
	MAX-ACCESS  read-only
	STATUS	current
	DESCRIPTION
	       "This object contains the number of session packets transmitted by
	       this PPPoE Session."
	::= { csPppoeSessionEntry 12 }

	csPppoeSessionTransmittedOctets OBJECT-TYPE
	SYNTAX	Counter32 
	MAX-ACCESS  read-only
	STATUS	current
	DESCRIPTION
	       "This object contains the number of session octets transmitted by
	       this PPPoE Session."
	::= { csPppoeSessionEntry 13 }

	csPppoeSessionReceiveOperDown OBJECT-TYPE
	SYNTAX	Counter32 
	MAX-ACCESS  read-only
	STATUS	current
	DESCRIPTION
	       "This object contains the number of session packets received by
	       this PPPoE Session from its peer while its operational status is down."
	::= { csPppoeSessionEntry 14 }

	csPppoeSessionTransmitOperDown OBJECT-TYPE
	SYNTAX	Counter32 
	MAX-ACCESS  read-only
	STATUS	current
	DESCRIPTION
	       "This object contains the number of session packets received
	       for to transmit to peer by this PPPoE Session."
	::= { csPppoeSessionEntry 15 }
	
	csPppoeSessionReceivedErrors OBJECT-TYPE
	SYNTAX	Counter32 
	MAX-ACCESS  read-only
	STATUS	current
	DESCRIPTION
	       "This object contains the number of session packets received
	        and having protocol header errors."
	::= { csPppoeSessionEntry 16 }
	
	csPppoeSessionRowStatus OBJECT-TYPE
	SYNTAX      RowStatus
	MAX-ACCESS  read-create
	STATUS	    current
	DESCRIPTION
	    "The row status for this table. Used only for deleting this session.
		 IMPORTANT: (1) entries on this table are created when a session is
					    established. Therefore, creation of entry thru 
						SNMP SET Request is not allowed. 
					(2) session is usually torn down by the peer."
	::= { csPppoeSessionEntry 17 }



	--
	--
    --     PPPoE Statistics Table
	--

	csPppoeAcIfStatTable OBJECT-TYPE
    SYNTAX   SEQUENCE OF CsPppoeAcIfStatEntry
    MAX-ACCESS   not-accessible
    STATUS   current
    DESCRIPTION
        "The PPPoE Access Concentrators statistics counter table."
    ::= { csPppoeStatistics 1 }

    csPppoeAcIfStatEntry OBJECT-TYPE
    SYNTAX      CsPppoeAcIfStatEntry
    MAX-ACCESS  not-accessible
    STATUS      current
    DESCRIPTION 
        "A set of statistics for a single PPPoE Access Concentrator."
    INDEX { csPppoeAcIfSlotIndex, csPppoeAcIfPortIndex,
				 csPppoeAcIfChannelIndex, csPppoeAcIfSubIfIndex }
	::= { csPppoeAcIfStatTable 1 }

    CsPppoeAcIfStatEntry ::=
	SEQUENCE {
	csPppoeAcIfStatPADIReceive
		Counter32,
	csPppoeAcIfStatPADIReject
		Counter32,
	csPppoeAcIfStatPADRReceive
		Counter32,
	csPppoeAcIfStatPADRReject
		Counter32,
	csPppoeAcIfStatPADOTransmit
		Counter32,
	csPppoeAcIfStatPADSTransmit
		Counter32,
	csPppoeAcIfStatPADTReceive
		Counter32,
	csPppoeAcIfStatPADTTransmit
		Counter32,
	csPppoeAcIfStatGenericErrorReceive
		Counter32,
	csPppoeAcIfStatGenericErrorTransmit
		Counter32,
	csPppoeAcIfStatMalformedPkts
		Counter32,
	csPppoeAcIfStatServiceNameErrors
		Counter32,
	csPppoeAcIfStatACSystemErrors
		Counter32
	}

	csPppoeAcIfStatPADIReceive OBJECT-TYPE
	SYNTAX	    Counter32 
	MAX-ACCESS  read-only
	STATUS	    current
	DESCRIPTION
	    "This object contains the number of PADI received by this PPPoE AC." 
	::= { csPppoeAcIfStatEntry 1 }

	csPppoeAcIfStatPADIReject OBJECT-TYPE
	SYNTAX	    Counter32 
	MAX-ACCESS  read-only
	STATUS	    current
	DESCRIPTION
	       "This object contains the number of PADI discarded by this PPPoE AC." 
	::= { csPppoeAcIfStatEntry 2 }

	csPppoeAcIfStatPADRReceive OBJECT-TYPE
	SYNTAX	    Counter32 
	MAX-ACCESS  read-only
	STATUS	    current
	DESCRIPTION
	       "This object contains the number of PADR received by this PPPoE AC." 
	::= { csPppoeAcIfStatEntry 15 }

	csPppoeAcIfStatPADRReject OBJECT-TYPE
	SYNTAX	    Counter32 
	MAX-ACCESS  read-only
	STATUS	    current
	DESCRIPTION
	       "This object contains the number of PADR discarded by this PPPoE AC." 
	::= { csPppoeAcIfStatEntry 16 }

	csPppoeAcIfStatPADOTransmit OBJECT-TYPE
	SYNTAX	    Counter32 
	MAX-ACCESS  read-only
	STATUS	    current
	DESCRIPTION
	       "This object contains the number of PADO transmitted by this PPPoE AC." 
	::= { csPppoeAcIfStatEntry 17 }

	csPppoeAcIfStatPADSTransmit OBJECT-TYPE
	SYNTAX	    Counter32 
	MAX-ACCESS  read-only
	STATUS	    current
	DESCRIPTION
	       "This object contains the number of PADS transmitted by this PPPoE AC." 
	::= { csPppoeAcIfStatEntry 18 }

	csPppoeAcIfStatPADTReceive OBJECT-TYPE
	SYNTAX	    Counter32 
	MAX-ACCESS  read-only
	STATUS	    current
	DESCRIPTION
	       "This object contains the number of PADT received by this PPPoE AC." 
	::= { csPppoeAcIfStatEntry 19 }

	csPppoeAcIfStatPADTTransmit OBJECT-TYPE
	SYNTAX	    Counter32 
	MAX-ACCESS  read-only
	STATUS	    current
	DESCRIPTION
	       "This object contains the number of PADT transmitted by this PPPoE AC." 
	::= { csPppoeAcIfStatEntry 20 }

	csPppoeAcIfStatGenericErrorReceive OBJECT-TYPE
	SYNTAX	    Counter32 
	MAX-ACCESS  read-only
	STATUS	    current
	DESCRIPTION
	       "This object contains the number of PPPoE Generic-Error tags
	       received by this PPPoE AC." 
	::= { csPppoeAcIfStatEntry 21 }

	csPppoeAcIfStatGenericErrorTransmit OBJECT-TYPE
	SYNTAX	    Counter32 
	MAX-ACCESS  read-only
	STATUS	    current
	DESCRIPTION
	       "This object contains the number of PPPoE Generic-Error tags
	       transmitted by this PPPoE AC." 
	::= { csPppoeAcIfStatEntry 22 }

	csPppoeAcIfStatMalformedPkts OBJECT-TYPE
	SYNTAX	    Counter32 
	MAX-ACCESS  read-only
	STATUS	    current
	DESCRIPTION
	       "This object contains the number of malformed packets received by this
	       PPPoE AC." 
	::= { csPppoeAcIfStatEntry 23 }

	csPppoeAcIfStatServiceNameErrors OBJECT-TYPE
	SYNTAX	    Counter32 
	MAX-ACCESS  read-only
	STATUS	    current
	DESCRIPTION
	       "This object contains the number of PPPoE Service-Name-Error
	       tags received/transmitted by this PPPoE AC." 
	::= { csPppoeAcIfStatEntry 24 }

	csPppoeAcIfStatACSystemErrors OBJECT-TYPE
	SYNTAX	    Counter32 
	MAX-ACCESS  read-only
	STATUS	    current
	DESCRIPTION
	       "This object contains the number of PPPoE AC-System-Error tags
	       received/transmitted by this PPPoE AC." 
	::= { csPppoeAcIfStatEntry 13 }



------------------------------------------------------------------------------
--
--    PPP Multilink Bundles
--
------------------------------------------------------------------------------


    csOrionMlpppBundleTable OBJECT-TYPE
        SYNTAX  SEQUENCE OF CsOrionMlpppBundleEntry
        MAX-ACCESS  not-accessible
        STATUS  current
        DESCRIPTION
            "This table contains information about PPP multilink bundles."
        ::= { csOrionMlpppInfo 1 }

    csOrionMlpppBundleEntry OBJECT-TYPE
        SYNTAX CsOrionMlpppBundleEntry
        MAX-ACCESS not-accessible
        STATUS  current
        DESCRIPTION
            "Each entry represents a PPP multilink bundle."
        INDEX { csOrionMlpppBundleSlot,
                csOrionMlpppBundleIndex }
        ::= { csOrionMlpppBundleTable 1 }

    CsOrionMlpppBundleEntry ::=
        SEQUENCE {
            csOrionMlpppBundleSlot                  Integer32,
            csOrionMlpppBundleIndex                 Integer32,
            csOrionMlpppBundleMaxLinks              Integer32,
            csOrionMlpppBundleQueueSize             Integer32,
            csOrionMlpppBundleFragmentsPerPacket    Integer32,
            csOrionMlpppBundleReorderTimeout        Integer32,
            csOrionMlpppBundleTxMRRU                Integer32,
            csOrionMlpppBundleRxMRRU                Integer32,
            csOrionMlpppBundleEventLogLevel         INTEGER,
            csOrionMlpppBundleAdminStatus           INTEGER,
            csOrionMlpppBundleOperStatus            OperStatus,
            csOrionMlpppBundleRowStatus             RowStatus,
            csOrionMlpppBundleActiveLinks           Integer32,
            csOrionMlpppBundlePacketsSent           Counter32,
            csOrionMlpppBundlePacketsReceived       Counter32,
            csOrionMlpppBundleBytesSent             Counter32,
            csOrionMlpppBundleBytesReceived         Counter32,
            csOrionMlpppBundleSiteName              DisplayString
        }

    csOrionMlpppBundleSlot OBJECT-TYPE
        SYNTAX     Integer32 (1..26)
        MAX-ACCESS not-accessible
        STATUS     current
        DESCRIPTION
            "The slot on which this bundle is to be created.  This
            value must be specified at creation and, henceforth,
            cannot be changed."
        ::= { csOrionMlpppBundleEntry 1 }

    csOrionMlpppBundleIndex OBJECT-TYPE
        SYNTAX     Integer32 (1..65535)
        MAX-ACCESS not-accessible
        STATUS     current
        DESCRIPTION
            "The index associated with this PPP multilink bundle."
        ::= { csOrionMlpppBundleEntry 2 }

    csOrionMlpppBundleMaxLinks OBJECT-TYPE
        SYNTAX     Integer32 (1..32)
        MAX-ACCESS read-create
        STATUS     current
        DESCRIPTION
            "The maximum number of links that can be configured to
            be part of this PPP multilink bundle."
        DEFVAL { 8 }
        ::= { csOrionMlpppBundleEntry 3 }

    csOrionMlpppBundleQueueSize OBJECT-TYPE
        SYNTAX     Integer32 (0..256)
        MAX-ACCESS read-create
        STATUS     current
        DESCRIPTION
            "The maximum size of this bundle's re-sequencing queue."
        DEFVAL { 16 }
        ::= { csOrionMlpppBundleEntry 4 }

    csOrionMlpppBundleFragmentsPerPacket OBJECT-TYPE
        SYNTAX     Integer32 (1..1)
        MAX-ACCESS read-only
        STATUS     current
        DESCRIPTION
            "The number of fragments per packet."
        ::= { csOrionMlpppBundleEntry 5 }

    csOrionMlpppBundleReorderTimeout OBJECT-TYPE
        SYNTAX     Integer32 (1000..10000)
        MAX-ACCESS read-create
        STATUS     current
        DESCRIPTION
            "The configured reorder timeout value for this bundle,
            expressed in milliseconds."
        DEFVAL { 3000 }
        ::= { csOrionMlpppBundleEntry 6 }

    csOrionMlpppBundleTxMRRU OBJECT-TYPE
        SYNTAX     Integer32
        MAX-ACCESS read-only
        STATUS     current
        DESCRIPTION
            "The maximum receive reconstructed unit in the transmit
            direction."
        ::= { csOrionMlpppBundleEntry 7 }

    csOrionMlpppBundleRxMRRU OBJECT-TYPE
        SYNTAX     Integer32
        MAX-ACCESS read-only
        STATUS     current
        DESCRIPTION
            "The maximum receive reconstructed unit in the receive
            direction."
        ::= { csOrionMlpppBundleEntry 8 }

    csOrionMlpppBundleEventLogLevel OBJECT-TYPE
        SYNTAX  INTEGER {
               off(0),
               veryLow(1),
               low(2),
               medium(3),
               high(4),
               veryHigh(5)
           }
       MAX-ACCESS read-create
       STATUS     current
       DESCRIPTION
           "The desired level of event logging for this bundle."
       DEFVAL { off }
       ::= { csOrionMlpppBundleEntry 9 }

   csOrionMlpppBundleAdminStatus OBJECT-TYPE
       SYNTAX  INTEGER {
               enable(1),
               disable(2)
           }
       MAX-ACCESS  read-create
       STATUS      current
       DESCRIPTION
           "The desired state of the bundle."
       DEFVAL { disable }
       ::= { csOrionMlpppBundleEntry 10 }

   csOrionMlpppBundleOperStatus OBJECT-TYPE
       SYNTAX  OperStatus
       MAX-ACCESS  read-only
       STATUS      current
       DESCRIPTION
           "The actual of the bundle."
       ::= { csOrionMlpppBundleEntry 11 }

   csOrionMlpppBundleRowStatus OBJECT-TYPE
       SYNTAX     RowStatus
       MAX-ACCESS read-create
       STATUS     current
       DESCRIPTION
            "This object is used to create and delete
            PPP multilink bundles."
        ::= { csOrionMlpppBundleEntry 12 }

    csOrionMlpppBundleActiveLinks OBJECT-TYPE
        SYNTAX     Integer32
        MAX-ACCESS read-only
        STATUS     current
        DESCRIPTION
            "The number of active links in this bundle."
        ::= { csOrionMlpppBundleEntry 13 }

    csOrionMlpppBundlePacketsSent OBJECT-TYPE
        SYNTAX     Counter32
        MAX-ACCESS read-only
        STATUS     current
        DESCRIPTION
            "The number of packets sent on this bundle."
        ::= { csOrionMlpppBundleEntry 14 }

    csOrionMlpppBundlePacketsReceived OBJECT-TYPE
        SYNTAX     Counter32
        MAX-ACCESS read-only
        STATUS     current
        DESCRIPTION
            "The number of packets received on this bundle."
        ::= { csOrionMlpppBundleEntry 15 }

    csOrionMlpppBundleBytesSent OBJECT-TYPE
        SYNTAX     Counter32
        MAX-ACCESS read-only
        STATUS     current
        DESCRIPTION
            "The number of bytes sent on this bundle."
        ::= { csOrionMlpppBundleEntry 16 }

    csOrionMlpppBundleBytesReceived OBJECT-TYPE
        SYNTAX     Counter32
        MAX-ACCESS read-only
        STATUS     current
        DESCRIPTION
            "The number of bytes received on this bundle."
        ::= { csOrionMlpppBundleEntry 17 }

    csOrionMlpppBundleSiteName OBJECT-TYPE
        SYNTAX     DisplayString (SIZE(0..25))
        MAX-ACCESS read-create
        STATUS     current
        DESCRIPTION
            "A textual string containing the site name of this
                        Mlppp Bundle interface."
        ::= { csOrionMlpppBundleEntry 18 }


    csOrionMlpppLinkTable OBJECT-TYPE
        SYNTAX  SEQUENCE OF CsOrionMlpppLinkEntry
        MAX-ACCESS  not-accessible
        STATUS  current
        DESCRIPTION
            "This table contains information about PPP multilink links."
        ::= { csOrionMlpppInfo 2 }

    csOrionMlpppLinkEntry OBJECT-TYPE
        SYNTAX CsOrionMlpppLinkEntry
        MAX-ACCESS not-accessible
        STATUS  current
        DESCRIPTION
            "Each entry represents a PPP multilink link."
        INDEX { csOrionMlpppBundleSlot,
				csOrionMlpppBundleIndex,
                csOrionMlpppLinkSlotIndex,
                csOrionMlpppLinkPortIndex,
                csOrionMlpppLinkChannelIndex,
                csOrionMlpppLinkSubIfIndex }
        ::= { csOrionMlpppLinkTable 1 }

    CsOrionMlpppLinkEntry ::=
        SEQUENCE {
            csOrionMlpppLinkSlotIndex               Integer32,
            csOrionMlpppLinkPortIndex               Integer32,
            csOrionMlpppLinkChannelIndex            Integer32,
            csOrionMlpppLinkSubIfIndex              Integer32,
            csOrionMlpppLinkRowStatus               RowStatus
        }

    csOrionMlpppLinkSlotIndex OBJECT-TYPE
        SYNTAX     Integer32 (1..26)
        MAX-ACCESS not-accessible
        STATUS     current
        DESCRIPTION
            "The slot of this PPP multilink link."
        ::= { csOrionMlpppLinkEntry 1 }

    csOrionMlpppLinkPortIndex OBJECT-TYPE
        SYNTAX     Integer32 (1..4)
        MAX-ACCESS not-accessible
        STATUS     current
        DESCRIPTION
            "The port of this PPP multilink link."
        ::= { csOrionMlpppLinkEntry 2 }

    csOrionMlpppLinkChannelIndex OBJECT-TYPE
	SYNTAX	Integer32 (0..512)
	MAX-ACCESS  not-accessible
	STATUS	current
	DESCRIPTION
	       "Channel number of this link."
	::= { csOrionMlpppLinkEntry 3 }

    csOrionMlpppLinkSubIfIndex OBJECT-TYPE
    	SYNTAX	Integer32 (1..512)
    	MAX-ACCESS	not-accessible
    	STATUS	current
    	DESCRIPTION
	    "The sub-interface number of this link."
        ::= { csOrionMlpppLinkEntry 4 }

    csOrionMlpppLinkRowStatus OBJECT-TYPE
        SYNTAX     RowStatus
        MAX-ACCESS read-create
        STATUS     current
        DESCRIPTION
            "This object is used to add and remove
            PPP multilink links from a bundle."
        ::= { csOrionMlpppLinkEntry 5 }


------------------------------------------------------------------------------
--
--	        Hardware Control Info    
--
------------------------------------------------------------------------------

--
-- definitions for power supplies.
--

-- Table definition for power supply.

    csOrionPowerSupplyTable OBJECT-TYPE
	SYNTAX	SEQUENCE OF CsOrionPowerSupplyEntry
	MAX-ACCESS  not-accessible
	STATUS	current
	DESCRIPTION
		"A table for power supplies."
	::= { csOrionHWControlInfo 1 }

    csOrionPowerSupplyEntry OBJECT-TYPE
	SYNTAX 	 CsOrionPowerSupplyEntry
	MAX-ACCESS  not-accessible
	STATUS	current
	DESCRIPTION
		"An entry containing power supply state information."
	INDEX   { csOrionPowerSupplyIndex }
	::= { csOrionPowerSupplyTable 1 }

    CsOrionPowerSupplyEntry ::=
	SEQUENCE {
	csOrionPowerSupplyIndex
 		Integer32,
	csOrionPowerSupplyInputPowerState
		INTEGER,
	csOrionPowerSupplyOutputPowerState
 		INTEGER
	}

    csOrionPowerSupplyIndex OBJECT-TYPE
	SYNTAX	Integer32 (1..4)
	MAX-ACCESS  not-accessible
	STATUS	current
	DESCRIPTION
		"An index for a power supply table."
	::= { csOrionPowerSupplyEntry 1 }

    csOrionPowerSupplyInputPowerState OBJECT-TYPE
	SYNTAX	 INTEGER
	{
		ok(1),
		not-ok(2)
	}
	MAX-ACCESS  not-accessible
	STATUS	current
	DESCRIPTION
		"A power supply's input power state."
	::= { csOrionPowerSupplyEntry 2 }

    csOrionPowerSupplyOutputPowerState OBJECT-TYPE
	SYNTAX	 INTEGER
	{
		ok(1),
		not-ok(2)
	}
	MAX-ACCESS  not-accessible
	STATUS	current
	DESCRIPTION
		"A power supply's output power state."
	::= { csOrionPowerSupplyEntry 3 }


-- Table definitions for fans.

    csOrionFanTable OBJECT-TYPE
    	SYNTAX  SEQUENCE OF CsOrionFanEntry
        MAX-ACCESS  not-accessible
 	STATUS      current
	DESCRIPTION
            "A table for fans."
        ::= { csOrionHWControlInfo 2 }

    csOrionFanEntry OBJECT-TYPE
        SYNTAX   CsOrionFanEntry
        MAX-ACCESS  not-accessible
        STATUS  current
        DESCRIPTION
            "An entry containing management information applicable
            to fans."
        INDEX   { csOrionFanTray, csOrionFanIndex }
        ::= { csOrionFanTable 1 }

    CsOrionFanEntry ::=
        SEQUENCE {
            csOrionFanIndex
                    Integer32,
            csOrionFanState
                    INTEGER,
            csOrionFanSpeed
                    Gauge32
        }

    csOrionFanIndex OBJECT-TYPE
        SYNTAX  Integer32 (1..16)
        MAX-ACCESS  not-accessible
        STATUS  current
        DESCRIPTION
            "An index for a fan table."
        ::= { csOrionFanEntry 1 }

    csOrionFanState OBJECT-TYPE
        SYNTAX   INTEGER{
            ok(1),
            not-ok(2)
        }
        MAX-ACCESS  not-accessible
        STATUS  current
        DESCRIPTION
            "A fan operational state."
        ::= { csOrionFanEntry 2 }

    csOrionFanSpeed OBJECT-TYPE
        SYNTAX   Gauge32
        MAX-ACCESS  not-accessible
        STATUS  current
        DESCRIPTION
            "A fan speed (in RPS: Revolutions Per Second)."
        ::= { csOrionFanEntry 3 }


-- definitions for power supply controller.

    csOrionPowerSupplyHWRevision OBJECT-TYPE
	SYNTAX	DisplayString(SIZE(0..3)) 
	MAX-ACCESS  not-accessible
	STATUS	current
        DESCRIPTION
             "The hardward revision information of the power supply controller."
        ::= { csOrionPowerSupplyControlInfo 1 }

    csOrionPowerSupplyFWMajorRevision OBJECT-TYPE
	SYNTAX	DisplayString (SIZE(0..3))
	MAX-ACCESS  not-accessible
	STATUS	current
        DESCRIPTION
             "The major firmware revision information of the power supply controller."
        ::= { csOrionPowerSupplyControlInfo 2 }

    csOrionPowerSupplyFWMinorRevision OBJECT-TYPE
	SYNTAX	DisplayString (SIZE(0..3))
	MAX-ACCESS  not-accessible
	STATUS	current
        DESCRIPTION
             "The minor firmware revision information of the power supply controller."
        ::= { csOrionPowerSupplyControlInfo 3 }

    csOrionPowerSupplyFWRelease OBJECT-TYPE
	SYNTAX	DisplayString (SIZE (0..3))
	MAX-ACCESS  not-accessible
	STATUS	current
        DESCRIPTION
             "The firmware release of the power supply controller."
        ::= { csOrionPowerSupplyControlInfo 4 }

    csOrionPowerSupplyFWReleaseDate OBJECT-TYPE
	SYNTAX 	DisplayString (SIZE (0..8))
	MAX-ACCESS not-accessible
	STATUS 	current
	DESCRIPTION
		"A textual string containing information about the
		date of the firmware release."
	::= { csOrionPowerSupplyControlInfo 5 }

    csOrionPowerSupplyEventTrapGeneration OBJECT-TYPE
	SYNTAX INTEGER {
		enable  (1),
		disable (2)
	}
	MAX-ACCESS  read-write
	STATUS	current
        DESCRIPTION
	    "This object is used to enable/disable the generation of events and traps
	    of the power supply."
	::= { csOrionPowerSupplyControlInfo 6 }


--  Table definitions for fan tray controller.

    csOrionFanTrayControlTable OBJECT-TYPE
        SYNTAX  SEQUENCE OF CsOrionFanTrayControlEntry
        MAX-ACCESS  not-accessible
        STATUS  current
        DESCRIPTION
            "There is a controller for each of the fan tray.
	    This table contains entries of the hardware and firmware revision
	    information and entries used to enable/disable the event/trap generation."
    ::= { csOrionHWControlInfo 5 }

    csOrionFanTrayControlEntry OBJECT-TYPE
        SYNTAX   CsOrionFanTrayControlEntry
        MAX-ACCESS  not-accessible
        STATUS  current
        DESCRIPTION
            "An entry containing PIC H/W and F/W Revision information applicable
            to fan tray controllers."
        INDEX   { csOrionFanTray }
        ::= { csOrionFanTrayControlTable 1 }

    CsOrionFanTrayControlEntry ::=
        SEQUENCE {
            csOrionFanTray
                INTEGER,
            csOrionFanTrayHWRevision
                DisplayString,
            csOrionFanTrayFWMajorRevision
                DisplayString,
            csOrionFanTrayFWMinorRevision
                DisplayString,
            csOrionFanTrayFWRelease
                DisplayString,
            csOrionFanTrayFWReleaseDate
                DisplayString,
            csOrionFanTrayEventTrapGeneration
                INTEGER
        }

    csOrionFanTray OBJECT-TYPE
        SYNTAX  INTEGER {
            lowerOrFront (1), 
            upperOrRear (2)  
        }        
	MAX-ACCESS  not-accessible
        STATUS  current
        DESCRIPTION
            "Identifies the upper or lower fan tray."
        ::= { csOrionFanTrayControlEntry 1 }

    csOrionFanTrayHWRevision OBJECT-TYPE
	SYNTAX	DisplayString (SIZE(0..3))
	MAX-ACCESS  read-only
	STATUS	current
        DESCRIPTION
             "Fan tray's hardward Revision information"
        ::= { csOrionFanTrayControlEntry 2 }

    csOrionFanTrayFWMajorRevision OBJECT-TYPE
	SYNTAX	DisplayString (SIZE(0..3))
	MAX-ACCESS  read-only
	STATUS	current
        DESCRIPTION
          "Fan tray's firmware major Revision information."
        ::= { csOrionFanTrayControlEntry 3 }

    csOrionFanTrayFWMinorRevision OBJECT-TYPE
	SYNTAX	DisplayString (SIZE(0..3))
	MAX-ACCESS  read-only
	STATUS	current
        DESCRIPTION
           "Fan tray's firmware minor Revision information."
        ::= { csOrionFanTrayControlEntry 4 }

    csOrionFanTrayFWRelease OBJECT-TYPE
	SYNTAX	DisplayString (SIZE(0..3))
	MAX-ACCESS read-only      
	STATUS	current
        DESCRIPTION
             "The firmware release of the fan tray controller."
    ::= { csOrionFanTrayControlEntry 5 }

    csOrionFanTrayFWReleaseDate OBJECT-TYPE
	SYNTAX 	DisplayString (SIZE (0..8))
	MAX-ACCESS read-only       
	STATUS 	current
	DESCRIPTION
		"A textual string containing information about the
		date of the firmware release."
	::= { csOrionFanTrayControlEntry 6 }

    csOrionFanTrayEventTrapGeneration OBJECT-TYPE
	SYNTAX INTEGER {
		enable  (1),
		disable (2)
	}
	MAX-ACCESS  read-write
	STATUS	current
        DESCRIPTION
            "Fan tray's firmware minor Revision information."
        ::= { csOrionFanTrayControlEntry 7 }

-- Table definitions for fan Temperature sensors.

    csOrionFanTempSensorTable OBJECT-TYPE
    SYNTAX  SEQUENCE OF CsOrionFanTempSensorEntry
    MAX-ACCESS  not-accessible
    STATUS  current
    DESCRIPTION
        "A table for fans."
    ::= { csOrionHWControlInfo 4 }

    csOrionFanTempSensorEntry OBJECT-TYPE
    SYNTAX   CsOrionFanTempSensorEntry
    MAX-ACCESS  not-accessible
    STATUS  current
    DESCRIPTION
            "An entry containing management information applicable
            to fans."
    INDEX   { csOrionFanTray, csOrionFanIndex }
    ::= { csOrionFanTempSensorTable 1 }

    CsOrionFanTempSensorEntry ::=
    SEQUENCE {
    csOrionFanTempSensorState
            INTEGER,
	csOrionFanTempSensorTemperature
			Integer32
    }

    csOrionFanTempSensorState OBJECT-TYPE
    SYNTAX   INTEGER{
            ok(1),
            not-ok(2)
    }
    MAX-ACCESS  not-accessible
    STATUS  current
    DESCRIPTION
            "the temperature sensor's operational status of a fan."
    ::= { csOrionFanTempSensorEntry 1 }

    csOrionFanTempSensorTemperature OBJECT-TYPE
    SYNTAX Integer32 (-67..257)
    MAX-ACCESS  not-accessible
    STATUS  current
    DESCRIPTION
            "A temperature (in Fahrenheit or Celsius) of the Fan."
    ::= { csOrionFanTempSensorEntry 2 }

-- definitions for Temperature Air Flow Card.

    csOrionTempAirFlowCardTable OBJECT-TYPE
    SYNTAX  SEQUENCE OF CsOrionTempAirFlowCardEntry
    MAX-ACCESS  not-accessible
    STATUS  current
    DESCRIPTION
        "A table for temperature air flow card."
    ::= { csOrionTemperatureAirFlowCardInfo 1 }

    csOrionTempAirFlowCardEntry OBJECT-TYPE
    SYNTAX   CsOrionTempAirFlowCardEntry
    MAX-ACCESS  not-accessible
    STATUS  current
    DESCRIPTION
            "An entry containing management information applicable
            to temperature air flow card."
    INDEX   { csOrionAirFlowCardIndex }
    ::= { csOrionTempAirFlowCardTable 1 }

    CsOrionTempAirFlowCardEntry ::=
    SEQUENCE {
      csOrionAirFlowCardIndex
                      INTEGER,
      csOrionAirFlowCardHWRevision
                      DisplayString,
      csOrionAirFlowCardFWMajorRevision
                      DisplayString,
      csOrionAirFlowCardFWMinorRevision
                      DisplayString,
      csOrionAirFlowCardFWRelease
                      DisplayString,
      csOrionAirFlowCardFWReleaseDate
                      DisplayString,
      csOrionAirFlowCardTemperature
                      Integer32,
      csOrionAirFlowCardTempState
                      INTEGER,
      csOrionAirFlowCardEventTrapGeneration
                      INTEGER
    }

    csOrionAirFlowCardIndex OBJECT-TYPE
      SYNTAX INTEGER {
            front (1),
            rear (2)
      }
      MAX-ACCESS  not-accessible
    STATUS  current
    DESCRIPTION
            "Identifies the temperature air flow card."
    ::= { csOrionTempAirFlowCardEntry 1 }

    csOrionAirFlowCardHWRevision OBJECT-TYPE
    SYNTAX  DisplayString (SIZE(0..3))
      MAX-ACCESS  read-only
    STATUS  current
    DESCRIPTION
            "The air flow card's hardward Revision information."
    ::= { csOrionTempAirFlowCardEntry 2 }

    csOrionAirFlowCardFWMajorRevision OBJECT-TYPE
    SYNTAX  DisplayString (SIZE(0..3))
      MAX-ACCESS  read-only
    STATUS  current
    DESCRIPTION
            "The air flow card's firmwar major Revision information."
    ::= { csOrionTempAirFlowCardEntry 3 }

    csOrionAirFlowCardFWMinorRevision OBJECT-TYPE
    SYNTAX  DisplayString (SIZE(0..3))
      MAX-ACCESS  read-only
    STATUS  current
    DESCRIPTION
            "The air flow card's firmware minor Revision information."
    ::= { csOrionTempAirFlowCardEntry 4 }

    csOrionAirFlowCardFWRelease OBJECT-TYPE
    SYNTAX  DisplayString (SIZE(0..3))
    MAX-ACCESS  read-only
    STATUS  current
    DESCRIPTION
            "The air flow card's firmware release information."
    ::= { csOrionTempAirFlowCardEntry 5 }

    csOrionAirFlowCardFWReleaseDate OBJECT-TYPE
	SYNTAX 	DisplayString (SIZE (0..8))
	MAX-ACCESS read-only
	STATUS 	current
	DESCRIPTION
		"A textual string containing information about the
		date of the firmwre release."
	::= { csOrionTempAirFlowCardEntry 6 }

    csOrionAirFlowCardTemperature OBJECT-TYPE
    SYNTAX  Integer32 (-67..257)
      MAX-ACCESS  read-only
    STATUS  current
    DESCRIPTION
            "The air flow card's temperature."
    ::= { csOrionTempAirFlowCardEntry 7 }

    csOrionAirFlowCardTempState OBJECT-TYPE
    SYNTAX   INTEGER{
            ok(1),
            not-ok(2)
    }
    MAX-ACCESS  read-only
    STATUS  current
    DESCRIPTION
            "An inlet air flow temperature sensor operational state."
    ::= { csOrionTempAirFlowCardEntry 8 }

    csOrionAirFlowCardEventTrapGeneration OBJECT-TYPE
      SYNTAX INTEGER {
              enable  (1),
              disable (2)
      }
      MAX-ACCESS  read-write
    STATUS  current
    DESCRIPTION
            "The air flow card's trap/event generation status."
    ::= { csOrionTempAirFlowCardEntry 9 }


-- definitions for status panel controller.


    csOrionStatusPanelHWRevision OBJECT-TYPE
	SYNTAX	DisplayString (SIZE(0..3))
	MAX-ACCESS  not-accessible
	STATUS	current
        DESCRIPTION
             "The hardward revision information of the status panel controller."
        ::= { csOrionStatusPanelControlInfo 1 }

    csOrionStatusPanelFWMajorRevision OBJECT-TYPE
	SYNTAX	DisplayString (SIZE(0..3))
	MAX-ACCESS  not-accessible
	STATUS	current
        DESCRIPTION
             "The major firmware revision information of the status panel controller."
        ::= { csOrionStatusPanelControlInfo 2 }

    csOrionStatusPanelFWMinorRevision OBJECT-TYPE
	SYNTAX	DisplayString (SIZE(0..3))
	MAX-ACCESS  not-accessible
	STATUS	current
        DESCRIPTION
             "The minor firmware revision information of the status panel controller."
        ::= { csOrionStatusPanelControlInfo 3 }

    csOrionStatusPanelFWRelease OBJECT-TYPE
	SYNTAX	DisplayString (SIZE (0..3))
	MAX-ACCESS  not-accessible
	STATUS	current
        DESCRIPTION
             "The firmware release of the power supply controller."
        ::= { csOrionStatusPanelControlInfo 4 }

    csOrionStatusPanelFWReleaseDate OBJECT-TYPE
	SYNTAX 	DisplayString (SIZE (0..8))
	MAX-ACCESS not-accessible
	STATUS 	current
	DESCRIPTION
		"A textual string containing information about the
		date of the firmware release."
	::= { csOrionStatusPanelControlInfo 5 }


------------------------------------------------------------------------------
--
-- 		Backplane Info 
--
------------------------------------------------------------------------------

    csOrionBackplaneUtilization OBJECT-TYPE
	SYNTAX 	Gauge32
	MAX-ACCESS  read-only
	STATUS	current
	DESCRIPTION
		"A % of utilization for backplane."
	::= { csOrionBackplaneInfo 1 }




------------------------------------------------------------------------------
--
--	        Orion General Snmp Group    
--
------------------------------------------------------------------------------

    csOrionSnmpGenTable OBJECT-TYPE
	SYNTAX	SEQUENCE OF CsOrionSnmpGenEntry
	MAX-ACCESS  not-accessible
	STATUS 	       current
	DESCRIPTION 
	       "This table controls the activation of the snmp agent
	       on a particular Virtual Router.  Note, only one agent instance
	       can be enabled at a time."
	::= { csOrionGenSnmp 1 }

    csOrionSnmpGenEntry OBJECT-TYPE
	SYNTAX     CsOrionSnmpGenEntry
	MAX-ACCESS not-accessible
	STATUS     current
	DESCRIPTION
	       "Each entry represents a single Virtual Router."
	INDEX { csOrionGlobalVPNIndex, csOrionVPNVRouterIndex }
	::= { csOrionSnmpGenTable 1 }
	
    CsOrionSnmpGenEntry ::=
	SEQUENCE {
	csOrionSnmpGenStatus
		INTEGER
	}

    csOrionSnmpGenStatus OBJECT-TYPE
	SYNTAX INTEGER {
		enable  (1),
		disable (2)
	}
	MAX-ACCESS read-write
	STATUS     current
	DESCRIPTION
	       "This object is used to enable/disable the snmp server
	       on this Virtual Router.  If this object is disabled, the snmp
	       server will not respond to any snmp requests and it
	       won't send any traps."
	::= { csOrionSnmpGenEntry 1 }



    --
    -- The SNMP Community String Table
    --
 
    csOrionSnmpCommTable OBJECT-TYPE
	SYNTAX	SEQUENCE OF CsOrionSnmpCommEntry
	MAX-ACCESS  not-accessible
	STATUS 	       current
	DESCRIPTION 
	       "This table contains all the community strings recognized
	       by the snmp server on this device."
	::= { csOrionGenSnmp 2 }

    csOrionSnmpCommEntry OBJECT-TYPE
	SYNTAX     CsOrionSnmpCommEntry
	MAX-ACCESS not-accessible
	STATUS     current
	DESCRIPTION
	       "Each entry represents a single community string."
	INDEX { csOrionGlobalVPNIndex, csOrionVPNVRouterIndex,
		csOrionSnmpCommString, csOrionSnmpCommAddr }
	::= { csOrionSnmpCommTable 1 }
	
    CsOrionSnmpCommEntry ::=
	SEQUENCE {
	csOrionSnmpCommString
		DisplayString,
	csOrionSnmpCommAddr
		IpAddress,
	csOrionSnmpCommPriv
		INTEGER,
	csOrionSnmpCommRowStatus
		RowStatus
	}

    csOrionSnmpCommString OBJECT-TYPE
	SYNTAX		DisplayString (SIZE(1..80))
	MAX-ACCESS	not-accessible
	STATUS		current
	DESCRIPTION
	       "This object identifies one community string recognized by the
	       snmp server on this device."
	::= { csOrionSnmpCommEntry 1 }

    csOrionSnmpCommAddr OBJECT-TYPE
	SYNTAX		IpAddress
	MAX-ACCESS	not-accessible
	STATUS		current
	DESCRIPTION
	       "This object identifies the Ip Address of a manager allowed
	       to use this community string."
	::= { csOrionSnmpCommEntry 2 }

    csOrionSnmpCommPriv OBJECT-TYPE
	SYNTAX		INTEGER {
		readOnly  (1),
		readWrite (2)
	}
	MAX-ACCESS	read-create
	STATUS		current
	DESCRIPTION
	       "This object indicates the privilege level of this community
	       string.  If the value of this object is readOnly(1), this snmp
	       server will respond only to GET, GETNEXT, and GETBULK requests
	       from snmp managers using this community string.  If this value 
	       of this object is readWrite(2), this snmp server will respond to
	       any requests from snmp managers using this community string."
	DEFVAL { readOnly }
	::= { csOrionSnmpCommEntry 3 }

    csOrionSnmpCommRowStatus OBJECT-TYPE
	SYNTAX		RowStatus 
	MAX-ACCESS	read-create
	STATUS		current
	DESCRIPTION
	       "A row status type for the Snmp Community Table."
	::= { csOrionSnmpCommEntry 4 }

------------------------------------------------------------------------------
--
--   SNMP Agent Error Table
--
-------------------------------------------------------------------------------



	csOrionSnmpAgentErrorTable OBJECT-TYPE
	SYNTAX	SEQUENCE OF CsOrionSnmpAgentErrorEntry
	MAX-ACCESS  not-accessible
	STATUS 	    current
	DESCRIPTION 
	       "This table keeps track of the errors that happened when a NMS 
		   node tried to a SET operation. Since standard error codes returned 
		   by the SNMP response PDU was not comprehensive enough to indicate the 
		   actual problem, this table evolved. The NMS node has to keep the 
		   request-id field and the UDP port of the SET PDU that is being sent
		   to the Orion SNMP agent. If the response-PDU corresponding to that 
		   SET returns an error, NMS node can browse this table with the saved 
		   request-id of the failed SET-PDU to get more information about the error."
	::= { csOrionGenSnmp 3 }

	csOrionSnmpAgentErrorEntry OBJECT-TYPE
	SYNTAX	CsOrionSnmpAgentErrorEntry
	MAX-ACCESS  not-accessible
	STATUS 	       current
	DESCRIPTION 
		"Each entry represent an error associated with a set operation by a management 
		station. The Orion SNMP agent keeps track of the last 25 instances of such 
		errors. Older entries give way for new entries. "
	INDEX { csOrionSnmpAgentErrorNmsIpAddress, csOrionSnmpAgentErrorNmsPort, csOrionSnmpAgentErrorNmsRequestId}
	::= { csOrionSnmpAgentErrorTable 1 }


	CsOrionSnmpAgentErrorEntry ::=
	SEQUENCE {
	csOrionSnmpAgentErrorNmsIpAddress
 		IpAddress,
	csOrionSnmpAgentErrorNmsPort
		Integer32,
	csOrionSnmpAgentErrorNmsRequestId  
		Integer32,
	csOrionSnmpAgentErrorCode
		Integer32,
	csOrionSnmpAgentErrorMsg
		DisplayString
	}

	csOrionSnmpAgentErrorNmsIpAddress OBJECT-TYPE
	SYNTAX		IpAddress
	MAX-ACCESS	read-only
	STATUS		current
	DESCRIPTION 
		 "IP address of the management station which made an unsuccessful SET operation."
	::= { csOrionSnmpAgentErrorEntry 1 }

	csOrionSnmpAgentErrorNmsPort OBJECT-TYPE
	SYNTAX          Integer32
	MAX-ACCESS      read-only
	STATUS          current
	DESCRIPTION
		 "The UDP port of the SNMP SET request which resulted in an error."
	::= { csOrionSnmpAgentErrorEntry 2 }

	csOrionSnmpAgentErrorNmsRequestId OBJECT-TYPE
	SYNTAX          Integer32
	MAX-ACCESS      read-only
	STATUS          current
	DESCRIPTION
		   "The requst-id field of the SNMP SET request which resulted in an error."
	::= { csOrionSnmpAgentErrorEntry 3 }

	csOrionSnmpAgentErrorCode OBJECT-TYPE
	SYNTAX          Integer32
	MAX-ACCESS      read-only
	STATUS          current
	DESCRIPTION
		   "The error code set when  the SNMP SET request resulted in an error."
	::= { csOrionSnmpAgentErrorEntry 4 }
	
	csOrionSnmpAgentErrorMsg OBJECT-TYPE
	SYNTAX		DisplayString (SIZE (1..128))
	MAX-ACCESS	read-only
	STATUS		current
	DESCRIPTION 
		   "Error message corresponding to the SET operation."
	::= { csOrionSnmpAgentErrorEntry 5 }




------------------------------------------------------------------------------
--
--	Orion Trap Group    
--
------------------------------------------------------------------------------

    csOrionSnmpTrapTable OBJECT-TYPE
	SYNTAX	SEQUENCE OF CsOrionSnmpTrapEntry
	MAX-ACCESS  not-accessible
	STATUS 	       current
	DESCRIPTION 
	       "This table controls the generation of traps by this
	       Virtual Router."
	::= { csOrionTrapInfo 1 }

    csOrionSnmpTrapEntry OBJECT-TYPE
	SYNTAX     CsOrionSnmpTrapEntry
	MAX-ACCESS not-accessible
	STATUS     current
	DESCRIPTION
	       "Each entry represents a single Virtual Router."
	INDEX { csOrionGlobalVPNIndex, csOrionVPNVRouterIndex }
	::= { csOrionSnmpTrapTable 1 }
	
    CsOrionSnmpTrapEntry ::=
	SEQUENCE {
	csOrionSnmpTrapStatus
		INTEGER
	}

    csOrionSnmpTrapStatus OBJECT-TYPE
	SYNTAX	INTEGER {
		enable  (1),
		disable (2)
	}
	MAX-ACCESS	read-write
	STATUS		current
	DESCRIPTION
	       "This object is used to control the trap function for the snmp 
	       server on this device.  If the value of this object is enable(1),
	       the snmp server will send traps.  If the value is disable(2), the
	       snmp server will not send traps."
	::= { csOrionSnmpTrapEntry 1 }

    --
    -- the Trap Receiver Table
    --

    csOrionTrapReceiverTable OBJECT-TYPE
	SYNTAX	SEQUENCE OF CsOrionTrapReceiverEntry
	MAX-ACCESS  not-accessible
	STATUS 	    current
	DESCRIPTION 
	       "The trap receiver table (0 to 25 entries).  This
	       table lists the addresses of stations that should
	       receive trap messages from this entity when an exception 
	       condition occurs."
	::= { csOrionTrapInfo 2 }

    csOrionTrapReceiverEntry OBJECT-TYPE
	SYNTAX	CsOrionTrapReceiverEntry
	MAX-ACCESS  not-accessible
	STATUS 	       current
	DESCRIPTION "A trap receiver table entry."
	INDEX { csOrionGlobalVPNIndex, csOrionVPNVRouterIndex,
		csOrionTrapReceiverComm, csOrionTrapReceiverAddr }
	::= { csOrionTrapReceiverTable 1 }


    CsOrionTrapReceiverEntry ::=
	SEQUENCE {
	csOrionTrapReceiverComm
 		DisplayString,
	csOrionTrapReceiverAddr
 		IpAddress,
	csOrionTrapReceiverRowStatus
		RowStatus,
        csOrionTrapReceiverPort
                Integer32,
        csOrionTrapReceiverTrapType
                INTEGER
	}

    csOrionTrapReceiverComm OBJECT-TYPE
	SYNTAX		DisplayString (SIZE (1..20))
	MAX-ACCESS	not-accessible
	STATUS		current
	DESCRIPTION 
	       "Community string used for trap messages to this
	       trap receiver."
	::= { csOrionTrapReceiverEntry 1 }

    csOrionTrapReceiverAddr OBJECT-TYPE
	SYNTAX		IpAddress
	MAX-ACCESS	not-accessible
	STATUS		current
	DESCRIPTION 
	       " IP address for trap receiver."
	::= { csOrionTrapReceiverEntry 2 }

    csOrionTrapReceiverRowStatus OBJECT-TYPE
	SYNTAX		RowStatus 
	MAX-ACCESS	read-create
	STATUS		current
	DESCRIPTION
	       "A row status type for the Trap Receiver Table.  This object
	       is used to add or remove entries from this table."
	::= { csOrionTrapReceiverEntry 3 }

    csOrionTrapReceiverPort OBJECT-TYPE
        SYNTAX          Integer32
        MAX-ACCESS      read-create
        STATUS          current
        DESCRIPTION
               " UDP port number for trap receiver. By default, all
        traps are sent to Port 162."
        DEFVAL    {162}
        ::= { csOrionTrapReceiverEntry 4 }

    csOrionTrapReceiverTrapType OBJECT-TYPE
        SYNTAX          INTEGER {
                          v1Trap(1),
                          v2Inform(2),
                          v1TrapAndv2Inform(3)
        }
        MAX-ACCESS      read-create
        STATUS          current
        DESCRIPTION
               " The trap type, which the Receiver wish to receive from
        this managed entity. By default, v2 inform request type is
        used to notify traps."
        DEFVAL { v2Inform }
        ::= { csOrionTrapReceiverEntry 5 }



------------------------------------------------------------------------------
--
--	        Accounting-related information
--
------------------------------------------------------------------------------

--
-- This first group presents accouting information for static,
-- or nailed up, connections
--

--
-- This table presents composite stats for each VPN
--

    csOrionVpnAcctTable OBJECT-TYPE
	SYNTAX	SEQUENCE OF CsOrionVpnAcctEntry
	MAX-ACCESS  not-accessible
	STATUS 	    current
	DESCRIPTION 
	       "This table contains composite stats for each
	       of the VPNs in this Orion."
	::= { csOrionStaticConn 1 }

    csOrionVpnAcctEntry OBJECT-TYPE
	SYNTAX	CsOrionVpnAcctEntry
	MAX-ACCESS  not-accessible
	STATUS 	       current
	DESCRIPTION "Each entry contains composite stats for a single VPN."
	INDEX { csOrionGlobalVPNIndex }
	::= { csOrionVpnAcctTable 1 }


    CsOrionVpnAcctEntry ::=
	SEQUENCE {
	csOrionVpnAcctCompStats
		OCTET STRING (SIZE (0..1000))
	}

    csOrionVpnAcctCompStats OBJECT-TYPE
	SYNTAX		OCTET STRING (SIZE (0..1000))
	MAX-ACCESS	read-only
	STATUS		current
	DESCRIPTION 
	       "Composite stats for this VPN"
	::= { csOrionVpnAcctEntry 1 }

--
-- This table presents composite stats for each VR
--

    csOrionVrAcctTable OBJECT-TYPE
	SYNTAX	SEQUENCE OF CsOrionVrAcctEntry
	MAX-ACCESS  not-accessible
	STATUS 	    current
	DESCRIPTION 
	       "This table contains composite stats for each
	       of the VRs in this Orion."
	::= { csOrionStaticConn 2 }

    csOrionVrAcctEntry OBJECT-TYPE
	SYNTAX	CsOrionVrAcctEntry
	MAX-ACCESS  not-accessible
	STATUS 	       current
	DESCRIPTION "Each entry contains composite stats for a single VPN."
	INDEX { csOrionGlobalVPNIndex, csOrionVPNVRouterIndex }
	::= { csOrionVrAcctTable 1 }


    CsOrionVrAcctEntry ::=
	SEQUENCE {
	csOrionVrAcctCompStats
		OCTET STRING (SIZE (0..1000))
	}

    csOrionVrAcctCompStats OBJECT-TYPE
	SYNTAX		OCTET STRING (SIZE (0..1000))
	MAX-ACCESS	read-only
	STATUS		current
	DESCRIPTION 
	       "Composite stats for this VPN"
	::= { csOrionVrAcctEntry 1 }

--
-- This group presents accounting information for dynamic
-- connections (e.g., pptp dial in connections).  
--

--
-- This object is used to flush the contents of the csOrionRadiusAcctTable.
--

    csOrionRadiusAcctFlush OBJECT-TYPE
	SYNTAX		INTEGER {
		flush (1)
	}
	MAX-ACCESS	read-write
	STATUS		current
	DESCRIPTION
		"This object is used to flush the contents of the
		csOrionRadiusAcctTable.  To flush the table, set
		the value of this object to 1."
	::= { csOrionDynamicConn 1 }

--
-- The information in this table is presented as standard radius 
-- accounting data, with each table entry marking either the beginning 
-- or end of a single connection
--

    csOrionRadiusAcctTable OBJECT-TYPE
	SYNTAX	SEQUENCE OF CsOrionRadiusAcctEntry
	MAX-ACCESS  not-accessible
	STATUS 	    current
	DESCRIPTION 
	       "This table contains composite stats for each
	       of the VRs in this Orion."
	::= { csOrionDynamicConn 2 }

    csOrionRadiusAcctEntry OBJECT-TYPE
	SYNTAX	CsOrionRadiusAcctEntry
	MAX-ACCESS  not-accessible
	STATUS 	       current
	DESCRIPTION "Each entry contains composite stats for a single VPN."
	INDEX { csOrionGlobalVPNIndex, csOrionVPNVRouterIndex, 
		csOrionRadiusAcctIndex }
	::= { csOrionRadiusAcctTable 3 }


    CsOrionRadiusAcctEntry ::=
	SEQUENCE {
	csOrionRadiusAcctIndex
		Integer32,
	csOrionRadiusAcctTimestamp
		TimeTicks,
	csOrionRadiusAcctVpnId
		Integer32,
	csOrionRadiusAcctVrId
		IpAddress,
	csOrionRadiusAcctInfo
		OCTET STRING (SIZE (0..1000))
	}

    csOrionRadiusAcctIndex OBJECT-TYPE
	SYNTAX		Integer32
	MAX-ACCESS	not-accessible
	STATUS		current
	DESCRIPTION 
		"The index of this radius accounting entry.  The values
		will increase monotonically, even after the entries have
		been flushed."
	::= { csOrionRadiusAcctEntry 1 }

    csOrionRadiusAcctTimestamp OBJECT-TYPE
	SYNTAX		TimeTicks
	MAX-ACCESS	read-only
	STATUS		current
	DESCRIPTION 
		"The value of sysUpTime when this entry was created."
	::= { csOrionRadiusAcctEntry 2 }

    csOrionRadiusAcctVpnId OBJECT-TYPE
	SYNTAX		Integer32
	MAX-ACCESS	read-only
	STATUS		current
	DESCRIPTION 
		"The Id of the VPN that originated this radius accounting
		entry."
	::= { csOrionRadiusAcctEntry 3 }
    
    csOrionRadiusAcctVrId OBJECT-TYPE
	SYNTAX		IpAddress
	MAX-ACCESS	read-only
	STATUS		current
	DESCRIPTION 
		"The Id of the VR that originated this radius accounting
		entry."
	::= { csOrionRadiusAcctEntry 4 }
    

    csOrionRadiusAcctInfo OBJECT-TYPE
	SYNTAX		OCTET STRING (SIZE (0..1000))
	MAX-ACCESS	read-only
	STATUS		current
	DESCRIPTION 
		"Information describing the creation or termination of
		a dynamic connection to a virtual router.  The information
		is presented in standard radius accounting format."
	::= { csOrionRadiusAcctEntry 5 }


--
-- The Telnet Server Table
--

    csTelnetSvrConfTable OBJECT-TYPE
	SYNTAX  SEQUENCE OF CsTelnetSvrConfEntry
	MAX-ACCESS  not-accessible
	STATUS  current
	DESCRIPTION
	    "A table of telnet server configuration parameters."
	::= { csTelnetSvrInfo 1 }

    csTelnetSvrConfEntry OBJECT-TYPE
	SYNTAX  CsTelnetSvrConfEntry
	MAX-ACCESS  not-accessible
	STATUS  current
	DESCRIPTION
	    "Each entry contains a set of configuration paramters 
		for telnet server in a VR. Note, that only a single instance
		of telnet server is enabledat a time."
	INDEX { csOrionGlobalVPNIndex, csOrionVPNVRouterIndex }
	::= { csTelnetSvrConfTable 1 }

    CsTelnetSvrConfEntry ::=
	SEQUENCE {
	csTelnetSvrConfAdminStatus
		INTEGER,
	csTelnetSvrConfTimeout
		Integer32
	}

    csTelnetSvrConfAdminStatus OBJECT-TYPE
	SYNTAX	INTEGER {
		enable  (1),
		disable (2)
	}
	MAX-ACCESS	read-write
	STATUS		current
	DESCRIPTION
	    "Enable/Disable the use of telnet server."
	DEFVAL { disable }
	::= { csTelnetSvrConfEntry 1 }

    csTelnetSvrConfTimeout OBJECT-TYPE
        SYNTAX  Integer32 (0..65535)
        MAX-ACCESS      read-write
        STATUS          current
        DESCRIPTION
            "A user configurable telnet timeout value in minutes"
        DEFVAL { 30 }
        ::= { csTelnetSvrConfEntry 2 }

--
-- Active Telnet connection session table
--

	csTelnetConnTable OBJECT-TYPE
	SYNTAX SEQUENCE OF CsTelnetConnEntry
	MAX-ACCESS not-accessible
	STATUS current
	DESCRIPTION
		"Table lists all the currently active telnet connection."
	::= { csTelnetSvrInfo 2 }

	csTelnetConnEntry OBJECT-TYPE
	SYNTAX CsTelnetConnEntry
	MAX-ACCESS not-accessible
	STATUS current
	DESCRIPTION
		"Each entry lists one currently active telnet connection."
	INDEX {csOrionGlobalVPNIndex, csOrionVPNVRouterIndex, csTelnetConnId }
	::= {csTelnetConnTable 1 }

	CsTelnetConnEntry ::=
	SEQUENCE {
		csTelnetConnId
			Integer32,
		csTelnetConnIpAddr
			IpAddress,
		csTelnetConnPort
			Integer32,
		csTelnetConnRowStatus
			RowStatus
	}

	csTelnetConnId OBJECT-TYPE
	SYNTAX Integer32 	(1..256)
	MAX-ACCESS not-accessible
	STATUS current
	DESCRIPTION
		"Connection Id of this particular telnet session."
	::= { csTelnetConnEntry 1 }

	csTelnetConnIpAddr OBJECT-TYPE
	SYNTAX IpAddress
	MAX-ACCESS read-create
	STATUS current
	DESCRIPTION
		"The remote peer's ip address of this telnet session."
	::= { csTelnetConnEntry 2 }

	csTelnetConnPort OBJECT-TYPE
	SYNTAX Integer32	(0..65535)
	MAX-ACCESS read-create
	STATUS current
	DESCRIPTION
		"The remote peer's port number of this telnet session."
	::= { csTelnetConnEntry 3 }

	csTelnetConnRowStatus OBJECT-TYPE
	SYNTAX RowStatus
	MAX-ACCESS read-create
	STATUS current
	DESCRIPTION
		"The admin status type for this entry in the connection table."
	::= { csTelnetConnEntry 4 }

------------------------------------------------------------------------------
--
--	        Orion Syslogd Info
--
------------------------------------------------------------------------------

    csOrionSyslogdTable OBJECT-TYPE
	SYNTAX	SEQUENCE OF CsOrionSyslogdEntry
	MAX-ACCESS  not-accessible
	STATUS 	       current
	DESCRIPTION 
	       "This table controls the activation of the syslogd client
	       on a particular Virtual Router.  Note, only one client
	       can be enabled at a time."
	::= { csOrionSyslogd 1 }

    csOrionSyslogdEntry OBJECT-TYPE
	SYNTAX     CsOrionSyslogdEntry
	MAX-ACCESS not-accessible
	STATUS     current
	DESCRIPTION
	       "Each entry represents a single Virtual Router."
	INDEX { csOrionGlobalVPNIndex, csOrionVPNVRouterIndex }
	::= { csOrionSyslogdTable 1 }
	
    CsOrionSyslogdEntry ::=
	SEQUENCE {
	csOrionSyslogdStatus
		INTEGER,
	csOrionSyslogdReceiverAddr	
		IpAddress,
	csOrionSyslogdFacility1
		INTEGER,
	csOrionSyslogdFacility2
		INTEGER,
	csOrionSyslogdFacility3
		INTEGER,
	csOrionSyslogdFacility4
		INTEGER,
	csOrionSyslogdFacility5
		INTEGER,
	csOrionSyslogdFacility6
		INTEGER,
	csOrionSyslogdFacility7
		INTEGER,
	csOrionSyslogdFacility8
		INTEGER,
	csOrionSyslogdLevel1
		INTEGER,
	csOrionSyslogdLevel2
		INTEGER,
	csOrionSyslogdLevel3
		INTEGER,
	csOrionSyslogdLevel4
		INTEGER,
	csOrionSyslogdLevel5
		INTEGER,
	csOrionSyslogdFacility9
		INTEGER,
	csOrionSyslogdFacility10
		INTEGER,
	csOrionSyslogdFacility11
		INTEGER
	}

    csOrionSyslogdStatus OBJECT-TYPE
	SYNTAX INTEGER {
		enable  (1),
		disable (2)
	}
	MAX-ACCESS read-write
	STATUS     current
	DESCRIPTION
	       "This object is used to enable/disable the syslogd client
	       on this Virtual Router.  If this object is disabled, the
	       syslogd client will not forward any ev_log messages to a
	       syslogd server."
	::= { csOrionSyslogdEntry 1 }

    csOrionSyslogdReceiverAddr OBJECT-TYPE
	SYNTAX		IpAddress
	MAX-ACCESS	read-write
	STATUS		current
	DESCRIPTION 
	       " IP address for syslogd server."
	::= { csOrionSyslogdEntry 2 }

    csOrionSyslogdFacility1 OBJECT-TYPE
	SYNTAX INTEGER (1..24)
	MAX-ACCESS read-write
	STATUS     current
	DESCRIPTION
	       "Mapping to Facility from Area 1"
	::= { csOrionSyslogdEntry 3 }
    csOrionSyslogdFacility2 OBJECT-TYPE
	SYNTAX INTEGER (1..24)
	MAX-ACCESS read-write
	STATUS     current
	DESCRIPTION
	       "Mapping to Facility from Area 2"
	::= { csOrionSyslogdEntry 4 }
    csOrionSyslogdFacility3 OBJECT-TYPE
	SYNTAX INTEGER (1..24)
	MAX-ACCESS read-write
	STATUS     current
	DESCRIPTION
	       "Mapping to Facility from Area 3"
	::= { csOrionSyslogdEntry 5 }
    csOrionSyslogdFacility4 OBJECT-TYPE
	SYNTAX INTEGER (1..24)
	MAX-ACCESS read-write
	STATUS     current
	DESCRIPTION
	       "Mapping to Facility from Area 4"
	::= { csOrionSyslogdEntry 6 }
    csOrionSyslogdFacility5 OBJECT-TYPE
	SYNTAX INTEGER (1..24)
	MAX-ACCESS read-write
	STATUS     current
	DESCRIPTION
	       "Mapping to Facility from Area 5"
	::= { csOrionSyslogdEntry 7 }
    csOrionSyslogdFacility6 OBJECT-TYPE
	SYNTAX INTEGER (1..24)
	MAX-ACCESS read-write
	STATUS     current
	DESCRIPTION
	       "Mapping to Facility from Area 6"
	::= { csOrionSyslogdEntry 8 }
    csOrionSyslogdFacility7 OBJECT-TYPE
	SYNTAX INTEGER (1..24)
	MAX-ACCESS read-write
	STATUS     current
	DESCRIPTION
	       "Mapping to Facility from Area 7"
	::= { csOrionSyslogdEntry 9 }
    csOrionSyslogdFacility8 OBJECT-TYPE
	SYNTAX INTEGER (1..24)
	MAX-ACCESS read-write
	STATUS     current
	DESCRIPTION
	       "Mapping to Facility from Area 8"
	::= { csOrionSyslogdEntry 10 }
    csOrionSyslogdLevel1 OBJECT-TYPE
	SYNTAX INTEGER (1..7)
	MAX-ACCESS read-write
	STATUS     current
	DESCRIPTION
	       "Mapping to syslogd Level from evlog level 1"
	::= { csOrionSyslogdEntry 11 }
    csOrionSyslogdLevel2 OBJECT-TYPE
	SYNTAX INTEGER (1..7)
	MAX-ACCESS read-write
	STATUS     current
	DESCRIPTION
	       "Mapping to syslogd Level from evlog level 2"
	::= { csOrionSyslogdEntry 12 }
    csOrionSyslogdLevel3 OBJECT-TYPE
	SYNTAX INTEGER (1..7)
	MAX-ACCESS read-write
	STATUS     current
	DESCRIPTION
	       "Mapping to syslogd Level from evlog level 3"
	::= { csOrionSyslogdEntry 13 }
    csOrionSyslogdLevel4 OBJECT-TYPE
	SYNTAX INTEGER (1..7)
	MAX-ACCESS read-write
	STATUS     current
	DESCRIPTION
	       "Mapping to syslogd Level from evlog level 4"
	::= { csOrionSyslogdEntry 14 }
    csOrionSyslogdLevel5 OBJECT-TYPE
	SYNTAX INTEGER (1..7)
	MAX-ACCESS read-write
	STATUS     current
	DESCRIPTION
	       "Mapping to syslogd Level from evlog level 5"
	::= { csOrionSyslogdEntry 15 }
    csOrionSyslogdFacility9 OBJECT-TYPE
	SYNTAX INTEGER (1..24)
	MAX-ACCESS read-write
	STATUS     current
	DESCRIPTION
	       "Mapping to Facility from Area 9"
	::= { csOrionSyslogdEntry 16 }
    csOrionSyslogdFacility10 OBJECT-TYPE
	SYNTAX INTEGER (1..24)
	MAX-ACCESS read-write
	STATUS     current
	DESCRIPTION
	       "Mapping to Facility from Area 10"
	::= { csOrionSyslogdEntry 17 }
    csOrionSyslogdFacility11 OBJECT-TYPE
	SYNTAX INTEGER (1..24)
	MAX-ACCESS read-write
	STATUS     current
	DESCRIPTION
	       "Mapping to Facility from Area 11"
	::= { csOrionSyslogdEntry 18 }


------------------------------------------------------------------------------
--
--       This set of objects are used only in the varbinds of Orion Traps
--
------------------------------------------------------------------------------


    csOrionFanEvent OBJECT-TYPE
        SYNTAX   INTEGER{
                speedRisingAboveLowerCriticalThreshold  (1),
                speedFallingBelowLowerCriticalThreshold (2),
                speedRisingAboveUpperCriticalThreshold  (3),
                speedFallingBelowUpperCriticalThreshold (4)
        }
        MAX-ACCESS  accessible-for-notify
        STATUS  current
        DESCRIPTION
                "A fan event."
        ::= { csOrionHWNotifyInfo 1 }

    csOrionTemperatureEvent OBJECT-TYPE
        SYNTAX   INTEGER{
                tempRisingAboveUpperCriticalThreshold  (1),
                tempFallingBelowUpperCriticalThreshold (2),
                tempRisingAboveUpperNonRecoverableThreshold  (3),
                tempFallingBelowUpperNonRecoverableThreshold (4),
                tempExceedsMaxValue (5),
                tempEnteringNormalRange (6)
        }
        MAX-ACCESS  accessible-for-notify
        STATUS  current
        DESCRIPTION
                "A fan event.  Note that the first four event types
                 apply to analog temperature sensors (for example,
                 those used to measure inlet and outlet air flow 
                 temperature), and the last two apply to digital
                 temperature sensors (for example, those in the
                 power supplies)."
        ::= { csOrionHWNotifyInfo 2 }

    csOrionPowerSupplyEvent OBJECT-TYPE
        SYNTAX   INTEGER{
                supplyModuleInserted  (1),
                supplyModuleRemoved   (2),
                inputVoltageRisingAboveLowerCriticalThreshold  (3),
                inputVoltageFallingBelowLowerCriticalThreshold (4),
                outputVoltageRisingAboveLowerCriticalThreshold  (5),
                outputVoltageFallingBelowLowerCriticalThreshold (6),
                outputCurrentRisingAboveUpperCriticalThreshold  (7),
                outputCurrentFallingBelowUpperCriticalThreshold (8),
                auxVoltageRisingAboveLowerCriticalThreshold (9),
                auxVoltageFallingBelowLowerCriticalThreshold (10),
                temperatureExceedsMaxValue (11),
                temperatureEnteringNormalRange (12),
                currentShareRisingAboveLowerCriticalThreshold (13),
                currentShareFallingBelowLowerCriticalThreshold (14)
        }
        MAX-ACCESS  accessible-for-notify
        STATUS  current
        DESCRIPTION
                "A power supply event."
        ::= { csOrionHWNotifyInfo 3 }

    csOrionFanSpeedThreshold OBJECT-TYPE
        SYNTAX  INTEGER (0..255)
        MAX-ACCESS  accessible-for-notify
        STATUS  current
        DESCRIPTION
            "The fan speed threshold (in revolutions per second)."
        ::= { csOrionHWNotifyInfo 4 }

    csOrionTemperatureSensorIndex OBJECT-TYPE
        SYNTAX  INTEGER (1..4)
        MAX-ACCESS  accessible-for-notify
        STATUS  current
        DESCRIPTION
            "Identifies a particular temperature sensor."
        ::= { csOrionHWNotifyInfo 5 }

    csOrionTemperature OBJECT-TYPE
        SYNTAX  INTEGER (0..255)
        MAX-ACCESS  accessible-for-notify
        STATUS  current
        DESCRIPTION
            "The temperature reported by a temperature sensor."
        ::= { csOrionHWNotifyInfo 6 }

    csOrionTemperatureThreshold OBJECT-TYPE
        SYNTAX  INTEGER (0..255)
        MAX-ACCESS  accessible-for-notify
        STATUS  current
        DESCRIPTION
            "The temperature threshold (in degress celsius)."
        ::= { csOrionHWNotifyInfo 7 }

    csOrionPacketRingPrimToProtCurrentEndpointSlot OBJECT-TYPE
 	SYNTAX	Integer32 (1..26)
        MAX-ACCESS  accessible-for-notify
        STATUS  current
        DESCRIPTION
            "Current slot number of the primary-to-protection endpoint."
        ::= { csOrionHWNotifyInfo 8 }

    csOrionPacketRingPrimToProtPreviousEndpointSlot OBJECT-TYPE
 	SYNTAX	Integer32 (1..26)
        MAX-ACCESS  accessible-for-notify
        STATUS  current
        DESCRIPTION
            "Previous slot number of the primary-to-protection endpoint."
        ::= { csOrionHWNotifyInfo 9 }

    csOrionPacketRingProtToPrimCurrentEndpointSlot OBJECT-TYPE
 	SYNTAX	Integer32 (1..26)
        MAX-ACCESS  accessible-for-notify
        STATUS  current
        DESCRIPTION
            "Current slot number of the protection-to-primary endpoint."
        ::= { csOrionHWNotifyInfo 10 }

    csOrionPacketRingProtToPrimPreviousEndpointSlot OBJECT-TYPE
 	SYNTAX	Integer32 (1..26)
        MAX-ACCESS  accessible-for-notify
        STATUS  current
        DESCRIPTION
            "Previous slot number of the protection-to-primary endpoint."
        ::= { csOrionHWNotifyInfo 11 }

    csOrionTempAirFlowCard OBJECT-TYPE
        SYNTAX  INTEGER {
            front (1),
            rear (2)
        }        
        MAX-ACCESS  accessible-for-notify
        STATUS  current
        DESCRIPTION
            "The temperature/airflow sense card for which we are resporting
             an event.  Note there is only one temperature/airflow sense card
             on 3500 chassis."
        ::= { csOrionHWNotifyInfo 12 }

     csOrionI2CDeviceId OBJECT-TYPE
        SYNTAX  INTEGER {
            statusPanel (1),
            fanTray3500 (2),
            frontFanTray9500 (3),
            rearFanTray9500 (4),
            tempAirFlowCard3500 (5),
            frontTempAirFlowCard9500 (6),
            rearTempAirFlowCard9500 (7),
            powerSupplyMonitor (8)
        }        
        MAX-ACCESS  accessible-for-notify
        STATUS  current
        DESCRIPTION
            "An I2C device."
        ::= { csOrionHWNotifyInfo 13 }

     csOrionI2CDevicePresent OBJECT-TYPE 
        SYNTAX  INTEGER {
            devicePresent (1),
            deviceNotPresent (2)
        }        
        MAX-ACCESS  accessible-for-notify
        STATUS  current
        DESCRIPTION
            "Indicates  whether a given I2C device is present or not."
        ::= { csOrionHWNotifyInfo 14 }

    csOrionPowerSupplyMonitorEvent OBJECT-TYPE
        SYNTAX   INTEGER{
                redundancyRegained (1),
                redundancyLost (2),
                auxVoltageRisingAboveLowerCriticalThreshold (3),
                auxVoltageFallingBelowLowerCriticalThreshold (4),
                outputVoltageRisingAboveLowerCriticalThreshold (5),
                outputVoltageFallingBelowLowerCriticalThreshold (6)
        }
        MAX-ACCESS  accessible-for-notify
        STATUS  current
        DESCRIPTION
                "A power supply monitor event."
        ::= { csOrionHWNotifyInfo 15 }

    csOrionTrapPowerSupplyIndex OBJECT-TYPE
      SYNTAX  Integer32 (1..4)
      MAX-ACCESS  accessible-for-notify
      STATUS  current
      DESCRIPTION
              "An index for the power supply to be used in power supply
               trap."
      ::= { csOrionHWNotifyInfo 16 }

    cbrFileType OBJECT-TYPE
      SYNTAX  INTEGER {
		bootcfg(1), 
		config(2), 
		password(3)
      }
      MAX-ACCESS  accessible-for-notify
      STATUS  current
      DESCRIPTION
              "The kind of file that is being copied from master to standby
	       control blade:

		bootcfg(1) - boot configuration file
		config(2)  - configuration file
		password(3) - password file"
      ::= { csOrionHWNotifyInfo 17 }

    cbrFileName OBJECT-TYPE
      SYNTAX  DisplayString
      MAX-ACCESS  accessible-for-notify
      STATUS  current
      DESCRIPTION
              "Name of the file that is being copied from master to standby
               control blade."
      ::= { csOrionHWNotifyInfo 18 }

    cbrFileErrorType OBJECT-TYPE
      SYNTAX  INTEGER {
		cantOpenConfig(-6),
		cantSaveConfig(-5),
		cantChangeDirConfig(-4),
		cantWritePassword(-3),
		cantOpenPassword(-2),
		cantChangeDirPassword(-1),
		savedBootcfg(1),
		savedConfig(2),
		savedPassword(3)
      }
      MAX-ACCESS  accessible-for-notify
      STATUS  current
      DESCRIPTION
              "Type of error that occurred during a file copy operation from 
	       master to standby control blade:

		cantOpenConfig(-6) - unable to open/create config file on
				     standby control blade
		cantSaveConfig(-5) - unable to save config file on standby
				     control blade
		cantChangeDirConfig(-4) - unable to change directory when
				          updating config file on standby
					  control blade
		cantWritePassword(-3) - unable to write into the password
					file on a standby control blade
		cantOpenPassword(-2) - unable to open/create password file on
				       standby control blade
		cantChangeDirPassword(-1) - unable to change directory when
					    updating password file on standby
					    control blade
		savedBootcfg(1) - boot config file is saved successfully on
				  standby control blade
		savedConfig(2) - configuration file is saved successfully on
				 standby control blade
		savedPassword(3) - password file is saved successfully on
				   standby control blade."
      ::= { csOrionHWNotifyInfo 19 }

    cbrFileErrorCode OBJECT-TYPE
      SYNTAX  Integer32
      MAX-ACCESS  accessible-for-notify
      STATUS  current
      DESCRIPTION
              "pHILE+ error code associated with the file copy operation from
	       master to standby control blade. Please consult the pSOS Manual
	       for the possible values and the meanings of the error code."
      ::= { csOrionHWNotifyInfo 20 }


------------------------------------------------------------------------------
--
-- 		Status Panel Info 
--
------------------------------------------------------------------------------

-- definitions for Status Panel ports.

    csOrionStatusPanelPortTable OBJECT-TYPE
	SYNTAX	SEQUENCE OF CsOrionStatusPanelPortEntry
	MAX-ACCESS  not-accessible
	STATUS	current
	DESCRIPTION
		"A table containing information about the Status Panel ports."
	::= { csOrionStatusPanelInfo 1 }

    csOrionStatusPanelPortEntry OBJECT-TYPE
	SYNTAX 	 CsOrionStatusPanelPortEntry
	MAX-ACCESS  not-accessible
	STATUS	current
	DESCRIPTION
		"An entry containing management information applicable
		to a particular Status Panel port."
	INDEX   { csOrionStatusPanelPortIndex }
        ::= { csOrionStatusPanelPortTable 1 }

    CsOrionStatusPanelPortEntry ::=
        SEQUENCE {
            csOrionStatusPanelPortIndex              Integer32,
            csOrionStatusPanelPortBaudRate           SPPBaudRate,
            csOrionStatusPanelPortLoopback           SPPLoopbackStatus,
            csOrionStatusPanelPortModemStatus        SPPModemStatus,
            csOrionStatusPanelPortRedundantStatus    SPPRedundantStatus
        }

    csOrionStatusPanelPortIndex OBJECT-TYPE
        SYNTAX    Integer32 (1..2)
        MAX-ACCESS  not-accessible
        STATUS    current
        DESCRIPTION
		"An index for a Status Panel port."
	::= { csOrionStatusPanelPortEntry 1 }

     
    csOrionStatusPanelPortBaudRate OBJECT-TYPE
        SYNTAX        SPPBaudRate
        MAX-ACCESS    read-create
        STATUS        current
        DESCRIPTION
		"The baud rate of a Status Panel port."
	DEFVAL{ baud9600 }
	::= { csOrionStatusPanelPortEntry 2 }

     
    csOrionStatusPanelPortLoopback OBJECT-TYPE
        SYNTAX        SPPLoopbackStatus
        MAX-ACCESS    read-create
        STATUS        current
        DESCRIPTION
		"The loopback state of a Status Panel port."
	DEFVAL{ noLoop }
	::= { csOrionStatusPanelPortEntry 3 }

     
    csOrionStatusPanelPortModemStatus OBJECT-TYPE
        SYNTAX        SPPModemStatus
        MAX-ACCESS    read-only
        STATUS        current
        DESCRIPTION
		"Whether or not a modem is connect to this Status Panel port."
	::= { csOrionStatusPanelPortEntry 4 }

     
    csOrionStatusPanelPortRedundantStatus OBJECT-TYPE
        SYNTAX        SPPRedundantStatus
        MAX-ACCESS    read-only
        STATUS        current
        DESCRIPTION
		"????  Ask Bev ????."
	::= { csOrionStatusPanelPortEntry 5 }

------------------------------------------------------------------------------
--
--	        Orion system-related traps definitions
--
------------------------------------------------------------------------------


    csOrionEventsInfo	OBJECT IDENTIFIER ::= { csOrionEvents 1 }

    csOrionBladeRemoved NOTIFICATION-TYPE
	OBJECTS { csOrionBladeSlotLocation }
	STATUS  current
	DESCRIPTION
		"A orionBladeRemoved trap signifies that the SNMPv2 entity,
		acting in an agent role, has detected that the one of the 
		existing Blade was removed from it's slot."
	::= { csOrionEventsInfo 1 }

    csOrionBladeInserted NOTIFICATION-TYPE
	OBJECTS { csOrionBladeSlotLocation, csOrionBladeDescr }
	STATUS  current
	DESCRIPTION
		"A csOrionBladeInserted trap signifies that SNMPv2 entity,
		acting in an agent role, has detected that the one of the 
		Blade was inserted in the empty slot."
	::= { csOrionEventsInfo 2 }

    csOrionBladeStateChange NOTIFICATION-TYPE
	OBJECTS { csOrionBladeSlotLocation, csOrionBladeDescr, csOrionBladeState }
	STATUS  current
	DESCRIPTION
		"A csOrionBladeStateChange signifies that the SNMPv2 entity
		acting in an agent role, has detected that a Blade has
		changed states.  A description of the Blade as well as
		the entered state is identified in this trap."
	::= { csOrionEventsInfo 3 }

    csOrionFanStatusChange NOTIFICATION-TYPE
        OBJECTS { csOrionFanTray,
                  csOrionFanIndex,
                  csOrionFanEvent,
                  csOrionFanSpeed,
                  csOrionFanSpeedThreshold }
        STATUS  current
        DESCRIPTION
                "A csOrionFanStatusChange trap signifies that the
                SNMPv2 entity, acting in an agent role, has detected
                a change in the status of a fan."
        ::= { csOrionEventsInfo 4 }

    csOrionConfigChange NOTIFICATION-TYPE
	OBJECTS { csOrionChangeSourceUserName,
		    csOrionChangeTableOID,
		    csOrionChangeSource,
			csOrionConfigChangeType,
			csOrionNumConfigChanges
			}
	STATUS  current
	DESCRIPTION
		"A csOrionConfigChange trap signifies that the SNMPv2 entity,
		acting in an agent role, has detected that Configuration was 
		changed.
		The Trap PDU for this csOrionConfigChange, also carries each of the
		modified object's OID followed by the changed value. In effect,
		there are one or more VarBinds follows the csOrionNumConfigChanges object
		of the Trap PDU. Since these OIDs are the member of one of the table
		defined in this MIB, type information of the value shall be got from
		the OID.
		If the csOrionConfigChangeType is delete, the VarBind that follows the
		csOrionNumConfigChanges contains the Index(es) of the entry which was
		deleted. If the  csOrionConfigChangeType is addModify, then  the
		VarBind contains all the changed OID-Value pairs followed by the index(es)." 
	::= { csOrionEventsInfo 5 }

    csOrionTempStatusChange NOTIFICATION-TYPE
        OBJECTS { csOrionFanTray,
                  csOrionTemperatureSensorIndex,
                  csOrionTemperatureEvent,
                  csOrionTemperature,
                  csOrionTemperatureThreshold }
        STATUS current
        DESCRIPTION
                "This trap indicates that the temperature status of the Orion
                system has changed states.  If the value of csOrionSystemTempStatus
                is tempRisingAboveUpperCriticalThreshold(1), the given sensor has
                detected a transition from the normal temperature range to the hot
                range.  If the value of csOrionSystemTempStatus is tempFallingBelow-
                UpperCriticalThreshold (2), the given sensor has detected a transition
                from the 'hot' range back down to the normal range."
        ::= { csOrionEventsInfo 6 }

   csOrionPowerSupplyStatusChange NOTIFICATION-TYPE
        OBJECTS { csOrionPowerSupplyIndex,
                  csOrionPowerSupplyEvent }
        STATUS current
        DESCRIPTION
                "This trap indicates one of the power supplies has
                changed state.  The following events are reported:

                        supplyModuleInserted (1)
                        supplyModuleRemoved (2)
                        inputVoltageRisingAbovePastLowerCriticalThreshold (3)
                        inputVoltageFallingBelowLowerCriticalThreshold (4)
                        outputVoltageRisingAboveLowerCriticalThreshold (5)
                        outputVoltageFallingBelowLowerCriticalThreshold (6)
                        outputCurrentRisingAboveUpperCriticalThreshold  (7)
                        outputCurrentFallingBelowUpperCriticalThreshold (8)
                        auxVoltageRisingAboveLowerCriticalThreshold (9)
                        auxVoltageFallingBelowLowerCriticalThreshold (10)
                        temperatureRisingAboveUpperCriticalThreshold (11)
                        temperatureFallingBelowUpperCriticalThreshold (12)
                        currentShareRisingAboveLowerCriticalThreshold (13)
                        currentShareFallingBelowLowerCriticalThreshold (14)"
        ::= { csOrionEventsInfo 7 }

   csOrionLogLinkDown NOTIFICATION-TYPE
	OBJECTS{ csOrionLogLinkSlotIndex, csOrionLogLinkPortIndex,
		 csOrionLogLinkChannelIndex, csOrionLogLinkSubIfIndex }
	STATUS  current
	DESCRIPTION
	    "This trap indicates that a Logical Link on the Orion is about
	    to enter the down state."
	::= { csOrionEventsInfo 8 }

   csOrionLogLinkUp NOTIFICATION-TYPE
	OBJECTS{ csOrionLogLinkSlotIndex, csOrionLogLinkPortIndex,
		 csOrionLogLinkChannelIndex, csOrionLogLinkSubIfIndex }
	STATUS  current
	DESCRIPTION
	    "This trap indicates that a Logical Link on the Orion is about
	    to enter the up state."
	::= { csOrionEventsInfo 9 }

   csOrionVIfDown NOTIFICATION-TYPE
	    OBJECTS { csOrionGlobalVPNIndex, csOrionVPNVRouterIndex, csOrionVIfIndex, csOrionVIfRowStatus, csOrionVIfOperStatus }
	    STATUS  current
	    DESCRIPTION
		"A csOrionVIfDown trap signifies that the SNMPv2 entity,
		acting in an agent role, has detected that the
		csOrionVIfOperStatus object for one of its communication links
		is about to enter the down state from some other state
		(but not from the notPresent state).  This other state
		is indicated by the included value of csOrionVIfOperStatus."
	::= { csOrionEventsInfo 10 }

   csOrionVIfUp NOTIFICATION-TYPE
	    OBJECTS { csOrionGlobalVPNIndex, csOrionVPNVRouterIndex, csOrionVIfIndex, csOrionVIfRowStatus, csOrionVIfOperStatus }
	    STATUS  current
	    DESCRIPTION
		"A csOrionVIfUp trap signifies that the SNMPv2 entity,
		acting in an agent role, has detected that the
		ifOperStatus object for one of its communication links
		left the down state and transitioned into some other
		state (but not into the notPresent state).  This other
		state is indicated by the included value of
		ifOperStatus."
	::= { csOrionEventsInfo 11 }


    csOrionOspfIfStateChange NOTIFICATION-TYPE
        OBJECTS {
		    csOrionGlobalVPNIndex,
		    csOrionVPNVRouterIndex,
                    csOspfRouterId, -- The originator of the trap
                    csOspfIfIpAddress,
                    csOspfAddressLessIf,
                    csOspfIfState   -- The new state
                  }
        STATUS             current
        DESCRIPTION
           "An csOspfIfStateChange trap signifies that there
           has been a change in the state of a non-virtual
           OSPF interface. This trap should  be  generated
           when  the interface state regresses (e.g., goes
           from Dr to Down) or progresses  to  a  terminal
           state  (i.e.,  Point-to-Point, DR Other, Dr, or
           Backup)."
   ::= { csOrionEventsInfo 12 }


    csOrionOspfVirtIfStateChange NOTIFICATION-TYPE
        OBJECTS {
		    csOrionGlobalVPNIndex,
		    csOrionVPNVRouterIndex,
                    csOspfRouterId, -- The originator of the trap
                    csOspfVirtIfAreaId,
                    csOspfVirtIfNeighbor,
                    csOspfVirtIfState  -- The new state
                  }
        STATUS             current
        DESCRIPTION
           "A csOspfIfStateChange trap signifies that there
           has  been a change in the state of an OSPF vir-
           tual interface.
           This trap should be generated when  the  inter-
           face  state  regresses  (e.g., goes from Point-
           to-Point to Down) or progresses to  a  terminal
           state (i.e., Point-to-Point)."
   ::= { csOrionEventsInfo 13 }


    csOrionOspfNbrStateChange NOTIFICATION-TYPE
        OBJECTS {
		    csOrionGlobalVPNIndex,
		    csOrionVPNVRouterIndex,
                    csOspfRouterId, -- The originator of the trap
                    csOspfNbrIpAddr,
                    csOspfNbrAddressLessIndex,
                    csOspfNbrRtrId,
                    csOspfNbrState  -- The new state
                  }
        STATUS             current
        DESCRIPTION
           "A csOspfNbrStateChange  trap  signifies   that
           there  has been a change in the state of a non-
           virtual OSPF neighbor.   This  trap  should  be
           generated  when  the  neighbor  state regresses
           (e.g., goes from Attempt or Full  to  1-Way  or
           Down)  or progresses to a terminal state (e.g.,
           2-Way or Full).  When an  neighbor  transitions
           from  or  to Full on non-broadcast multi-access
           and broadcast networks, the trap should be gen-
           erated  by the designated router.  A designated
           router transitioning to Down will be  noted  by
           csOspfIfStateChange."
   ::= { csOrionEventsInfo 14 }


    csOrionOspfVirtNbrStateChange NOTIFICATION-TYPE
        OBJECTS {
		    csOrionGlobalVPNIndex,
		    csOrionVPNVRouterIndex,
                    csOspfRouterId, -- The originator of the trap
                    csOspfVirtNbrArea,
                    csOspfVirtNbrRtrId,
                    csOspfVirtNbrState  -- The new state
                  }
        STATUS             current
        DESCRIPTION
           "An csOspfIfStateChange trap signifies that there
           has  been a change in the state of an OSPF vir-
           tual neighbor.  This trap should  be  generated
           when  the  neighbor state regresses (e.g., goes
           from Attempt or  Full  to  1-Way  or  Down)  or
           progresses to a terminal state (e.g., Full)."
   ::= { csOrionEventsInfo 15 }


    csOrionOspfIfConfigError NOTIFICATION-TYPE
        OBJECTS {
		    csOrionGlobalVPNIndex,
		    csOrionVPNVRouterIndex,
                    csOspfRouterId, -- The originator of the trap
                    csOspfIfIpAddress,
                    csOspfAddressLessIf,
                    csOspfPacketSrc,  -- The source IP address
                    csOspfConfigErrorType, -- Type of error
                    csOspfPacketType
                  }
        STATUS             current
        DESCRIPTION
           "An csOspfIfConfigError  trap  signifies  that  a
           packet  has  been received on a non-virtual in-
           terface  from  a  router  whose   configuration
           parameters  conflict  with this router's confi-
           guration parameters.  Note that the  event  op-
           tionMismatch  should  cause  a  trap only if it
           prevents an adjacency from forming."
	::= { csOrionEventsInfo 16 }


    csOrionOspfVirtIfConfigError NOTIFICATION-TYPE
        OBJECTS {
		    csOrionGlobalVPNIndex,
		    csOrionVPNVRouterIndex,
                    csOspfRouterId, -- The originator of the trap
                    csOspfVirtIfAreaId,
                    csOspfVirtIfNeighbor,
                    csOspfConfigErrorType, -- Type of error
                    csOspfPacketType
                  }
        STATUS             current
        DESCRIPTION
           "An csOspfConfigError trap signifies that a pack-
           et  has  been  received  on a virtual interface
           from a router  whose  configuration  parameters
           conflict   with   this  router's  configuration
           parameters.  Note that the event optionMismatch
           should  cause a trap only if it prevents an ad-
           jacency from forming."
   ::= { csOrionEventsInfo 17 }


    csOrionOspfIfAuthFailure NOTIFICATION-TYPE
        OBJECTS {
		    csOrionGlobalVPNIndex,
		    csOrionVPNVRouterIndex,
                    csOspfRouterId, -- The originator of the trap
                    csOspfIfIpAddress,
                    csOspfAddressLessIf,
                    csOspfPacketSrc,  -- The source IP address
                    csOspfConfigErrorType, -- authTypeMismatch or
                                         -- authFailure
                    csOspfPacketType
                  }
        STATUS             current
        DESCRIPTION
           "An csOspfIfAuthFailure  trap  signifies  that  a
           packet  has  been received on a non-virtual in-
           terface from a router whose authentication  key
           or  authentication  type  conflicts  with  this
           router's authentication key  or  authentication
           type."
   ::= { csOrionEventsInfo 18 }


    csOrionOspfVirtIfAuthFailure NOTIFICATION-TYPE
        OBJECTS {
		    csOrionGlobalVPNIndex,
		    csOrionVPNVRouterIndex,
                    csOspfRouterId, -- The originator of the trap
                    csOspfVirtIfAreaId,
                    csOspfVirtIfNeighbor,
                    csOspfConfigErrorType, -- authTypeMismatch or
                                         -- authFailure
                    csOspfPacketType
                  }
        STATUS             current
        DESCRIPTION
           "An csOspfVirtIfAuthFailure trap signifies that a
           packet has been received on a virtual interface
           from a router whose authentication key  or  au-
           thentication  type conflicts with this router's
           authentication key or authentication type."
   ::= { csOrionEventsInfo 19 }


    csOrionOspfIfRxBadPacket NOTIFICATION-TYPE
        OBJECTS {
		    csOrionGlobalVPNIndex,
		    csOrionVPNVRouterIndex,
                    csOspfRouterId, -- The originator of the trap
                    csOspfIfIpAddress,
                    csOspfAddressLessIf,
                    csOspfPacketSrc,  -- The source IP address
                    csOspfPacketType
                  }
        STATUS             current
        DESCRIPTION
           "An csOspfIfRxBadPacket trap  signifies  that  an
           OSPF  packet has been received on a non-virtual
           interface that cannot be parsed."
   ::= { csOrionEventsInfo 20 }


    csOrionOspfVirtIfRxBadPacket NOTIFICATION-TYPE
        OBJECTS {
		    csOrionGlobalVPNIndex,
		    csOrionVPNVRouterIndex,
                    csOspfRouterId, -- The originator of the trap
                    csOspfVirtIfAreaId,
                    csOspfVirtIfNeighbor,
                    csOspfPacketType
                  }
        STATUS             current
        DESCRIPTION
           "An csOspfRxBadPacket trap signifies that an OSPF
           packet has been received on a virtual interface
           that cannot be parsed."
   ::= { csOrionEventsInfo 21 }


    csOrionOspfTxRetransmit NOTIFICATION-TYPE
        OBJECTS {
		    csOrionGlobalVPNIndex,
		    csOrionVPNVRouterIndex,
                    csOspfRouterId, -- The originator of the trap
                    csOspfIfIpAddress,
                    csOspfAddressLessIf,
                    csOspfNbrRtrId, -- Destination
                    csOspfPacketType,
                    csOspfLsdbType,
                    csOspfLsdbLsid,
                    csOspfLsdbRouterId
                  }
        STATUS             current
        DESCRIPTION
           "An csOspfTxRetransmit  trap  signifies  than  an
           OSPF  packet  has  been retransmitted on a non-
           virtual interface.  All packets that may be re-
           transmitted  are associated with an LSDB entry.
           The LS type, LS ID, and Router ID are  used  to
           identify the LSDB entry."
   ::= { csOrionEventsInfo 22 }


    csOrionOspfVirtIfTxRetransmit NOTIFICATION-TYPE
        OBJECTS {
		    csOrionGlobalVPNIndex,
		    csOrionVPNVRouterIndex,
                    csOspfRouterId, -- The originator of the trap
                    csOspfVirtIfAreaId,
                    csOspfVirtIfNeighbor,
                    csOspfPacketType,
                    csOspfLsdbType,
                    csOspfLsdbLsid,
                    csOspfLsdbRouterId
                  }
        STATUS             current
        DESCRIPTION
           "An csOspfTxRetransmit  trap  signifies  than  an
           OSPF packet has been retransmitted on a virtual
           interface.  All packets that may be retransmit-
           ted  are  associated with an LSDB entry. The LS
           type, LS ID, and Router ID are used to identify
           the LSDB entry."
   ::= { csOrionEventsInfo 23 }


    csOrionOspfOriginateLsa NOTIFICATION-TYPE
        OBJECTS {
		    csOrionGlobalVPNIndex,
		    csOrionVPNVRouterIndex,
                    csOspfRouterId, -- The originator of the trap
                    csOspfLsdbAreaId,  -- 0.0.0.0 for AS Externals
                    csOspfLsdbType,
                    csOspfLsdbLsid,
                    csOspfLsdbRouterId
                  }
        STATUS             current
        DESCRIPTION
           "An csOspfOriginateLsa trap signifies that a  new
           LSA  has  been originated by this router.  This
           trap should not be invoked for simple refreshes
           of  LSAs  (which happesn every 30 minutes), but
           instead will only be invoked  when  an  LSA  is
           (re)originated due to a topology change.  Addi-
           tionally, this trap does not include LSAs  that
           are  being  flushed  because  they have reached
           MaxAge."
   ::= { csOrionEventsInfo 24 }


    csOrionOspfMaxAgeLsa NOTIFICATION-TYPE
        OBJECTS {
		    csOrionGlobalVPNIndex,
		    csOrionVPNVRouterIndex,
                    csOspfRouterId, -- The originator of the trap
                    csOspfLsdbAreaId,  -- 0.0.0.0 for AS Externals
                    csOspfLsdbType,
                    csOspfLsdbLsid,
                    csOspfLsdbRouterId
                  }
        STATUS             current
        DESCRIPTION
           "An csOspfMaxAgeLsa trap signifies  that  one  of
           the LSA in the router's link-state database has
           aged to MaxAge."
   ::= { csOrionEventsInfo 25 }

    csOrionOspfLsdbOverflow NOTIFICATION-TYPE
        OBJECTS {
		    csOrionGlobalVPNIndex,
		    csOrionVPNVRouterIndex,
                    csOspfRouterId, -- The originator of the trap
                    csOspfExtLsdbLimit
                  }
        STATUS             current
        DESCRIPTION
           "An csOspfLsdbOverflow trap  signifies  that  the
           number of LSAs in the router's link-state data-
           base has exceeded csOspfExtLsdbLimit."
   ::= { csOrionEventsInfo 26 }


    csOrionOspfLsdbApproachingOverflow NOTIFICATION-TYPE
        OBJECTS {
		    csOrionGlobalVPNIndex,
		    csOrionVPNVRouterIndex,
                    csOspfRouterId, -- The originator of the trap
                    csOspfExtLsdbLimit
                  }
        STATUS             current
        DESCRIPTION
           "An csOspfLsdbApproachingOverflow trap  signifies
           that  the  number of LSAs in the router's link-
           state database has exceeded ninety  percent  of
           csOspfExtLsdbLimit."
   ::= { csOrionEventsInfo 27 }

    csOrionCustomerVrUp NOTIFICATION-TYPE
        OBJECTS { csOrionGlobalVPNIndex, csOrionVPNVRouterIndex }
        STATUS             current
        DESCRIPTION
           "A csOrionCustomerVrUp trap signifies that a Virtual
            Router which services a customer network has has come up."
   ::= { csOrionEventsInfo 28 }

    csOrionCustomerVrDown NOTIFICATION-TYPE
        OBJECTS { csOrionGlobalVPNIndex, csOrionVPNVRouterIndex }
        STATUS             current
        DESCRIPTION
           "A csOrionCustomerVrDown trap signifies that a Virtual
            Router which services a customer network has gone down."
   ::= { csOrionEventsInfo 29 }

    csOrionServiceProviderVrUp NOTIFICATION-TYPE
        OBJECTS { csOrionGlobalVPNIndex, csOrionVPNVRouterIndex }
        STATUS             current
        DESCRIPTION
           "A csOrionServiceProviderVrUp trap signifies that a Virtual
            Router which is designated as a service provider VR has has come up."
   ::= { csOrionEventsInfo 30 }

    csOrionServiceProviderVrDown NOTIFICATION-TYPE
        OBJECTS { csOrionGlobalVPNIndex, csOrionVPNVRouterIndex }
        STATUS             current
        DESCRIPTION
           "A csOrionServiceProviderVrDown trap signifies that a Virtual
            Router which is designated as a service provider VR  has gone down."
   ::= { csOrionEventsInfo 31 }

    csOrionControlVrUp NOTIFICATION-TYPE
        OBJECTS { csOrionGlobalVPNIndex, csOrionVPNVRouterIndex }
        STATUS             current
        DESCRIPTION
           "A csOrionControlVrUp trap signifies that a Virtual
            Router which is designated as a control VR has come up.
            If a csOrionBladeRemoved Trap precedes this trap and if that
            blade is the master control blade then this trap might be from
            the control VR of the new master blade." 
   ::= { csOrionEventsInfo 32 }

    csOrionControlVrDown NOTIFICATION-TYPE
        OBJECTS { csOrionGlobalVPNIndex, csOrionVPNVRouterIndex }
        STATUS             current
        DESCRIPTION
           "A csOrionControlVrDown trap signifies that a Virtual
            Router which  is designated as a control VR has gone down."
   ::= { csOrionEventsInfo 33 }

    csOrionServiceProviderVIfUp NOTIFICATION-TYPE
        OBJECTS { csOrionGlobalVPNIndex, csOrionVPNVRouterIndex, csOrionVIfIndex}
        STATUS             current
        DESCRIPTION
           "A csOrionServiceProviderVIfUp trap signifies that a Virtual
            Interface on a Service Provider VR has come up."
   ::= { csOrionEventsInfo 34 }

    csOrionServiceProviderVIfDown NOTIFICATION-TYPE
        OBJECTS { csOrionGlobalVPNIndex, csOrionVPNVRouterIndex, csOrionVIfIndex }
        STATUS             current
        DESCRIPTION
           "A csOrionServiceProviderVIfDown trap signifies that a Virtual
            Interface on a Service Provider VR has gone down."
   ::= { csOrionEventsInfo 35 }

------------  
--  The following traps are related to Ds3 specific or events that can be
--  corresponding to both DS3 and OC3 blades.
--
------------
   csOrionLossOfSignal NOTIFICATION-TYPE
        OBJECTS { csOrionBladeSlotLocation, csOrionPortIndex, csOrionBladeType}
        STATUS             current
        DESCRIPTION
           "A csOrionLossOfSignal trap signifies that a physical port
            on a blade experiencing   loss of signal(LOS) on the line. 
			Applicable to both DS3 and OC3."
   ::= { csOrionEventsInfo 36 }

   csOrionLossOfFrame NOTIFICATION-TYPE
        OBJECTS { csOrionBladeSlotLocation, csOrionPortIndex, csOrionBladeType}
        STATUS             current
        DESCRIPTION
           "A csOrionLossOfFrame trap signifies that a physical port
            on a blade experiencing   loss of Frame(LOF) on the line.
			Applicable to both DS3 and OC3."
   ::= { csOrionEventsInfo 37 }

   csOrionDs3AlarmIndication NOTIFICATION-TYPE
        OBJECTS { csOrionBladeSlotLocation, csOrionPortIndex, csOrionBladeType}
        STATUS             current
        DESCRIPTION
           "A csOrionAlarmIndication trap signifies that a physical port
            on a blade  generates  an alarm (AIS)  that indicates a failure
			in upstream far end."
   ::= { csOrionEventsInfo 38 }

   csOrionLossOfClock NOTIFICATION-TYPE
        OBJECTS { csOrionBladeSlotLocation, csOrionPortIndex, csOrionBladeType}
        STATUS             current
        DESCRIPTION
           "A csOrionLossOfClock trap signifies that a physical port
            on a blade experiencing  loss of Clock(LOC) on the line.
			Applicable to both DS3 and OC3."
   ::= { csOrionEventsInfo 39 }

	csOrionBladeRestore NOTIFICATION-TYPE
		OBJECTS { csOrionRestoreBladeStatus,
				csOrionRestoreSlotIndex,
				csOrionRestoreNumVRs
				}
		STATUS  current
		DESCRIPTION
			"A csOrionBladeRestore trap signifies that a blade had been
			 restored successfully or not. The VarBind that follow contains
			 the list of VPN/VRs affected." 
	::= { csOrionEventsInfo 40 }


	csOrionDs3PortIdle	NOTIFICATION-TYPE
		OBJECTS { csOrionBladeSlotLocation, csOrionPortIndex, csOrionBladeType}
        STATUS             current
        DESCRIPTION
           "A csOrionDs3PortIdle trap signifies that a physical port
            on a blade received an IDLE signal from the far end indicating
			it is unequipped to handle any data transfer."
   ::= { csOrionEventsInfo 41 }


	csOrionAlarmClear	NOTIFICATION-TYPE
		OBJECTS { csOrionBladeSlotLocation, csOrionPortIndex, csOrionBladeType, csOrionAlarmType}
        STATUS             current
        DESCRIPTION
           "A csOrionAlarmClear trap signifies that a physical port
            on a blade, which had sent an alarm earlier, indicates that
			the previous alarm is cleared. Applicable to DS3."
   ::= { csOrionEventsInfo 42 }

	csOrionOc3Alarm		NOTIFICATION-TYPE
		OBJECTS { csOrionBladeSlotLocation, csOrionPortIndex, csOrionOc3AlarmType, csOrionAlarmAffectType, csOrionAlarmSeverityType}
        STATUS             current
        DESCRIPTION
           "A csOrionOc3Alarm trap signifies that an OC3 physical port
            on a blade, which had sent an alarm. "
   ::= { csOrionEventsInfo 43 }

	csOrionOc3AlarmClear	NOTIFICATION-TYPE
		OBJECTS { csOrionBladeSlotLocation, csOrionPortIndex, csOrionOc3AlarmType, csOrionAlarmAffectType, csOrionAlarmSeverityType}
        STATUS             current
        DESCRIPTION
           "A csOrionOc3AlarmClear trap signifies that an OC3 physical port
            on a blade, which had sent an alarm earlier, indicates that
		    the prvious alarm is cleared."
   ::= { csOrionEventsInfo 44 }

   csOrionPacketRingStatusChange NOTIFICATION-TYPE
	OBJECTS { csOrionPacketRingPrimToProtCurrentEndpointSlot,
		  csOrionPacketRingPrimToProtPreviousEndpointSlot,
		  csOrionPacketRingProtToPrimCurrentEndpointSlot,
		  csOrionPacketRingProtToPrimPreviousEndpointSlot }
        STATUS             current
        DESCRIPTION
           "A csOrionPacketRingStatusChange trap signifies that the packet ring
	    status of the chassis has changed.

	    If both endpoints change from zero to r[1,26], that means the
	    status has changed to protection ring.
       	    If both endpoints change from r[1,26] to zero, that means the
	    status has changed to no protection ring.
            If one/both endpoints change from r[1,26] to different r[1,26], 
            that means the topology has changed but not ring status."
   ::= { csOrionEventsInfo 45 }

    csOrionInletAirTempStatusChange NOTIFICATION-TYPE
        OBJECTS { csOrionTempAirFlowCard,
                  csOrionTemperatureSensorIndex,
                  csOrionTemperatureEvent,
                  csOrionTemperature,
                  csOrionTemperatureThreshold }
        STATUS current
        DESCRIPTION
                "This trap indicates that the inlet air temperature has
                changed states.  If the value of csOrionSystemTempStatus
                is tempRisingAboveUpperCriticalThreshold(1), the given sensor 
                has detected a transition from the normal temperature range 
                to the hot range.  If the value of csOrionSystemTempStatus is
                tempFallingBelowUpperCriticalThreshold (2), the given sensor
                has detected a transition from the 'hot' range back down to 
                the normal range."
        ::= { csOrionEventsInfo 46 }

    csOrionDevicePresent NOTIFICATION-TYPE
        OBJECTS { csOrionI2CDeviceId,
                  csOrionI2CDevicePresent }
        STATUS current
        DESCRIPTION
                "This trap indicates that a given I2C device is present.
                 This trap will occur on 9500 and 3500 chassis only."
        ::= { csOrionEventsInfo 47 }

   csOrionPowerSupplyMonitorStatusChange NOTIFICATION-TYPE
        OBJECTS { csOrionPowerSupplyMonitorEvent }
        STATUS current
        DESCRIPTION
                "This trap indicates a power supply monitor event.
                 The following events are reported:

                     redundancyRegained (1)
                     redundancyLost (2)
                     auxVoltageRisingAboveLowerCriticalThreshold (3)
                     auxVoltageFallingBelowLowerCriticalThreshold (4)"
        ::= { csOrionEventsInfo 48 }

   csOrionFarEndReceiveFailure NOTIFICATION-TYPE
        OBJECTS { csOrionPortIndex, csOrionBladeType}
        STATUS             current
        DESCRIPTION
           "A csOrionFarEndReceiveFailure trap signifies that the physical port
            on the remote end is receiving an alarm.
			Applicable to DS3."
   ::= { csOrionEventsInfo 49 }

   csOrionCBRFileError NOTIFICATION-TYPE
        OBJECTS { cbrFileType, cbrFileName, cbrFileErrorType, cbrFileErrorCode }
        STATUS             current
        DESCRIPTION
           "This trap reports on the status of the copy operation of a system 
	    file from master to standby control blade.

	    Generated only if there is control blade redundancy (cbr)."
   ::= { csOrionEventsInfo 50 }

END
