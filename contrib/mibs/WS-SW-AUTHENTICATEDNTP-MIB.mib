-- vim: syntax=mib
--
-- WS-SW-AUTHENTICATEDNTP-MIB.my
-- MIB generated by MG-SOFT Visual MIB Builder Version 6.0  Build 88
-- Friday, September 08, 2006 at 15:55:33
--

--  WS-SW-AUTHENTICATEDNTP-MIB.mib
-- MIB generated by MG-SOFT Visual MIB Builder Version 5.0  Build 250
-- Tuesday, June 20, 2006 at 17:38:24
--
--  WS-SW-AUTHENTICATEDNTP-MIB.mib
-- MIB generated by MG-SOFT Visual MIB Builder Version 5.0  Build 250
-- Thursday, June 15, 2006 at 19:50:10

	WS-SW-AUTHENTICATEDNTP-MIB DEFINITIONS ::= BEGIN

		IMPORTS
			OBJECT-GROUP, MODULE-COMPLIANCE
				FROM SNMPv2-CONF
			Integer32, Unsigned32, OBJECT-TYPE, MODULE-IDENTITY
				FROM SNMPv2-SMI
			TruthValue, DisplayString, RowStatus, TEXTUAL-CONVENTION
				FROM SNMPv2-TC
			wsSwNtp
				FROM WS-SW-SMI;


--   1.3.6.1.4.1.388.14.2.12.1
-- June 13, 2006 at 14:54 GMT
-- 1.3.6.1.4.1.388.14.2.12.1
-- June 13, 2006 at 14:54 GMT
		-- 1.3.6.1.4.1.388.14.2.12.1
		wsSwNTPModule MODULE-IDENTITY
			LAST-UPDATED "200606131454Z"		-- June 13, 2006 at 14:54 GMT
			ORGANIZATION
				"Symbol Technologies"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"Description."
			::= { wsSwNtp 1 }



--
-- Textual conventions
--

--  Textual conventions
--
		NTPLeapIndicator ::= TEXTUAL-CONVENTION
			STATUS current
			DESCRIPTION
				"This is a two-bit code warning of an impending leap
				second to be inserted in the NTP timescale.  The bits
				are set before 23:59 on the day of insertion and reset
				after 00:00 on the following day.  This causes the
				number of seconds (rollover interval) in the day of
				insertion to be increased or decreased by one.  The two
				bits are coded as below,
				00, no warning
				01, last minute has 61 seconds
				10, last minute has 59 seconds
				11, alarm condition (clock not synchronized)"
			REFERENCE
				"D.L. Mills, 'Network Time Protocol(Version 3)',
				RFC-1305, March 1992, Section 3.2.1"
			SYNTAX INTEGER
				{
				noWarning(0),
				addSecond(1),
				subtractSecond(2),
				alarm(3)
				}

		NTPStratum ::= TEXTUAL-CONVENTION
			STATUS current
			DESCRIPTION
				"Indicates the stratum of the clock.  The stratum
				defines the accuracy of a time server.  Higher the
				stratum, lower the accuracy.
				0, unspecified
				1, primary reference (e.g., calibrated atomic clock,
				   radio clock)
				2-255, secondary reference (via NTP)"
			REFERENCE
				"D.L. Mills, 'Network Time Protocol (Version 3)',
				RFC-1305, March 1992, Section 2.2"
			SYNTAX Integer32 (0..255)

		NTPSignedTimeValue ::= TEXTUAL-CONVENTION
			DISPLAY-HINT
				"2d.2d"
			STATUS current
			DESCRIPTION
				"The time in seconds that could represent signed
				quantities like time delay with respect to some
				source.  This textual-convention is specific to Cisco
				implementation of NTP where 32-bit integers are used
				for such quantities.  The signed integer part is in
				the first 16 bits and the fraction part is in the
				last 16 bits."
			REFERENCE
				"D.L. Mills, 'Network Time Protocol (Version 3)',
				RFC-1305, March 1992, Sections 2,  3.2.1"
			SYNTAX OCTET STRING (SIZE (4))

		NTPUnsignedTimeValue ::= TEXTUAL-CONVENTION
			DISPLAY-HINT
				"2d.2d"
			STATUS current
			DESCRIPTION
				"The time in seconds that could represent unsigned
				quantities like maximum error of the local clock
				with respect to some source.  This textual-convention
				is specific to Cisco implementation of NTP where
				32-bit integers are used for such quantities.  The
				unsigned integer part is in the first 16 bits and the
				fraction part is in the last 16 bits."
			REFERENCE
				"D.L. Mills, 'Network Time Protocol (Version 3)',
				RFC-1305, March 1992, Sections 2, 3.2.1"
			SYNTAX OCTET STRING (SIZE (4))

		NTPRefId ::= TEXTUAL-CONVENTION
			STATUS current
			DESCRIPTION
				"The reference clock identifier.  In the case of
				stratum 0 (unspecified) or stratum 1 (primary
				reference source), this is a four-octet,
				left-justified, zero-padded ASCII string as defined
				in RFC-1305.  In the case of stratum 2 and greater
				(secondary reference) this is the four-octet Internet
				address of the peer selected for synchronization.

				Some examples of stratum 0 identifiers are,
				DCN, DCN routing protocol
				NIST, NIST public modem
				TSP, TSP time protocol
				DTS, Digital Time Service

				Some examples of stratum 1 identifiers are,
				ATOM, Atomic clock (calibrated)
				VLF, VLF radio (OMEGA,, etc.)
				LORC, LORAN-C radionavigation
				GOES, GOES UHF environment satellite
				GPS, GPS UHF satellite positioning"
			REFERENCE
				"D.L. Mills, Network Time Protocol (Version 3)',
				RFC-1305, March 1992, Section 3.2.1"
			SYNTAX OCTET STRING (SIZE (4))

		NTPTimeStamp ::= TEXTUAL-CONVENTION
			DISPLAY-HINT
				"4d.4d"
			STATUS current
			DESCRIPTION
				"NTP timestamps are represented as a 64-bit
				unsigned fixed-point number, in seconds relative to
				00:00 on 1 January 1900.  The integer part is in the
				first 32 bits and the fraction part is in the last
				32 bits."
			REFERENCE
				"D.L. Mills, 'Network Time Protocol (Version 3)',
				RFC-1305, March 1992, Section 3.1"
			SYNTAX OCTET STRING (SIZE (8))

		NTPPollInterval ::= TEXTUAL-CONVENTION
			STATUS current
			DESCRIPTION
				"The minimum interval between transmitted NTP
				messages, in seconds as a power of two.  For
				instance, a value of six indicates a minimum
				interval of 64 seconds."
			SYNTAX Integer32 (-20..20)

		NTPAssocIdentifier ::= TEXTUAL-CONVENTION
			STATUS current
			DESCRIPTION
				"The association identifier of the peer.  Every peer
				with which an NTP server is associated with is
				identified by an association identifier."
			SYNTAX Integer32 (0..2147483647)

		NtpKeyIdentifier ::= TEXTUAL-CONVENTION
			STATUS current
			DESCRIPTION
				"Description."
			SYNTAX Integer32 (1..255)

--   Textual conventions
--
		NtpKeySource ::= TEXTUAL-CONVENTION
			STATUS current
			DESCRIPTION
				"Description."
			SYNTAX INTEGER (0..255)


--
-- Node definitions
--

--  Node definitions
--
-- Node definitions
--
-- Time (in microseconds) taken by NTP broadcast packet
-- on the wire.
-- 1.3.6.1.4.1.388.14.2.12.1.1
-- 1.3.6.1.4.1.388.14.2.12.1.1
		-- 1.3.6.1.4.1.388.14.2.12.1.1
		ntpBroadcastDelay OBJECT-TYPE
			SYNTAX INTEGER (1..999999)
			MAX-ACCESS read-write
			STATUS current
			DESCRIPTION
				"Description."
			::= { wsSwNTPModule 1 }


--   Enable/disable local hardware clock as a master clock for
-- this switch. Make sure the local clock is synchronized to a
-- reliable source.
-- 1.3.6.1.4.1.388.14.2.12.1.2
-- 1.3.6.1.4.1.388.14.2.12.1.2
		-- 1.3.6.1.4.1.388.14.2.12.1.2
		ntpMasterClockMode OBJECT-TYPE
			SYNTAX TruthValue
			MAX-ACCESS read-write
			STATUS current
			DESCRIPTION
				"Description."
			::= { wsSwNTPModule 2 }


--   Stratum number for the local master clock.
-- 1.3.6.1.4.1.388.14.2.12.1.3
-- 1.3.6.1.4.1.388.14.2.12.1.3
		-- 1.3.6.1.4.1.388.14.2.12.1.3
		ntpMasterClockStratum OBJECT-TYPE
			SYNTAX INTEGER (1..15)
			MAX-ACCESS read-write
			STATUS current
			DESCRIPTION
				"Description."
			::= { wsSwNTPModule 3 }


--   Enable/disbale ntp broadcast client mode.
-- 1.3.6.1.4.1.388.14.2.12.1.4
-- 1.3.6.1.4.1.388.14.2.12.1.4
		-- 1.3.6.1.4.1.388.14.2.12.1.4
		ntpBroadcastClientMode OBJECT-TYPE
			SYNTAX TruthValue
			MAX-ACCESS read-write
			STATUS current
			DESCRIPTION
				"Description."
			::= { wsSwNTPModule 4 }


		-- 1.3.6.1.4.1.388.14.2.12.1.5
		ntpaccessGroupPeer OBJECT-TYPE
			SYNTAX Integer32
			MAX-ACCESS read-write
			STATUS current
			DESCRIPTION
				"Description."
			::= { wsSwNTPModule 5 }


		-- 1.3.6.1.4.1.388.14.2.12.1.6
		ntpaccessGroupQueryOnly OBJECT-TYPE
			SYNTAX Integer32
			MAX-ACCESS read-write
			STATUS current
			DESCRIPTION
				"Description."
			::= { wsSwNTPModule 6 }


		-- 1.3.6.1.4.1.388.14.2.12.1.7
		ntpaccessGroupServe OBJECT-TYPE
			SYNTAX Integer32
			MAX-ACCESS read-write
			STATUS current
			DESCRIPTION
				"Description."
			::= { wsSwNTPModule 7 }


		-- 1.3.6.1.4.1.388.14.2.12.1.8
		ntpaccessGroupServeOnly OBJECT-TYPE
			SYNTAX Integer32
			MAX-ACCESS read-write
			STATUS current
			DESCRIPTION
				"Description."
			::= { wsSwNTPModule 8 }


		-- 1.3.6.1.4.1.388.14.2.12.1.9
		ntpAutoKey OBJECT-TYPE
			SYNTAX INTEGER
				{
				disabled(0),
				hostEnabled(1),
				clientOnlyEnabled(2)
				}
			MAX-ACCESS read-write
			STATUS current
			DESCRIPTION
				"Description."
			::= { wsSwNTPModule 9 }


		-- 1.3.6.1.4.1.388.14.2.12.1.10
		ntpAuthenticate OBJECT-TYPE
			SYNTAX TruthValue
			MAX-ACCESS read-write
			STATUS current
			DESCRIPTION
				"Description."
			::= { wsSwNTPModule 10 }


--   1.3.6.1.4.1.388.14.2.12.1.5
-- 1.3.6.1.4.1.388.14.2.12.1.5
		-- 1.3.6.1.4.1.388.14.2.12.1.11
		wsSwNtpSystem OBJECT IDENTIFIER ::= { wsSwNTPModule 11 }


--   Two-bit code warning of an impending leap second to
-- be inserted in the NTP timescale.
-- This object can be set only when the wsSwSysStratum has a value of 1
-- 1.3.6.1.4.1.388.14.2.1.5.1
-- 1.3.6.1.4.1.388.14.2.12.1.5.1
		-- 1.3.6.1.4.1.388.14.2.12.1.11.1
		wsSwSysLeap OBJECT-TYPE
			SYNTAX NTPLeapIndicator
			MAX-ACCESS read-only
			STATUS current
			DESCRIPTION
				"Description."
			::= { wsSwNtpSystem 1 }


--   1.3.6.1.4.1.388.14.2.1.5.2
-- 1.3.6.1.4.1.388.14.2.12.1.5.2
		-- 1.3.6.1.4.1.388.14.2.12.1.11.2
		wsSwSysStratum OBJECT-TYPE
			SYNTAX NTPStratum
			MAX-ACCESS read-only
			STATUS current
			DESCRIPTION
				"Description."
			::= { wsSwNtpSystem 2 }


--   1.3.6.1.4.1.388.14.2.1.5.3
-- 1.3.6.1.4.1.388.14.2.12.1.5.3
		-- 1.3.6.1.4.1.388.14.2.12.1.11.3
		wsSwSysPrecision OBJECT-TYPE
			SYNTAX Integer32 (-20..20)
			MAX-ACCESS read-only
			STATUS current
			DESCRIPTION
				"Description."
			::= { wsSwNtpSystem 3 }


--   1.3.6.1.4.1.388.14.2.1.5.4
-- 1.3.6.1.4.1.388.14.2.12.1.5.4
		-- 1.3.6.1.4.1.388.14.2.12.1.11.4
		wsSwSysRootDelay OBJECT-TYPE
			SYNTAX DisplayString
			MAX-ACCESS read-only
			STATUS current
			DESCRIPTION
				"Description."
			::= { wsSwNtpSystem 4 }


--   1.3.6.1.4.1.388.14.2.1.5.5
-- 1.3.6.1.4.1.388.14.2.12.1.5.5
		-- 1.3.6.1.4.1.388.14.2.12.1.11.5
		wsSwSysRootDispersion OBJECT-TYPE
			SYNTAX DisplayString
			MAX-ACCESS read-only
			STATUS current
			DESCRIPTION
				"Description."
			::= { wsSwNtpSystem 5 }


--   1.3.6.1.4.1.388.14.2.1.5.6
-- 1.3.6.1.4.1.388.14.2.12.1.5.6
		-- 1.3.6.1.4.1.388.14.2.12.1.11.6
		wsSwSysRefId OBJECT-TYPE
			SYNTAX NTPRefId
			MAX-ACCESS read-only
			STATUS current
			DESCRIPTION
				"Description."
			::= { wsSwNtpSystem 6 }


--   1.3.6.1.4.1.388.14.2.1.5.7
-- 1.3.6.1.4.1.388.14.2.12.1.5.7
		-- 1.3.6.1.4.1.388.14.2.12.1.11.7
		wsSwSysRefTime OBJECT-TYPE
			SYNTAX DisplayString
			MAX-ACCESS read-only
			STATUS current
			DESCRIPTION
				"Description."
			::= { wsSwNtpSystem 7 }


--   1.3.6.1.4.1.388.14.2.1.5.8
-- 1.3.6.1.4.1.388.14.2.12.1.5.8
		-- 1.3.6.1.4.1.388.14.2.12.1.11.8
		wsSwSysPoll OBJECT-TYPE
			SYNTAX NTPPollInterval
			MAX-ACCESS read-only
			STATUS current
			DESCRIPTION
				"Description."
			::= { wsSwNtpSystem 8 }


--   1.3.6.1.4.1.388.14.2.1.5.10
-- 1.3.6.1.4.1.388.14.2.12.1.5.10
		-- 1.3.6.1.4.1.388.14.2.12.1.11.9
		wsSwSysClock OBJECT-TYPE
			SYNTAX DisplayString
			MAX-ACCESS read-only
			STATUS current
			DESCRIPTION
				"Description."
			::= { wsSwNtpSystem 9 }


--   1.3.6.1.4.1.388.14.2.1.5.12
-- 1.3.6.1.4.1.388.14.2.12.1.5.12
		-- 1.3.6.1.4.1.388.14.2.12.1.11.10
		wsSwSysFrequency OBJECT-TYPE
			SYNTAX DisplayString
			MAX-ACCESS read-only
			STATUS current
			DESCRIPTION
				"Description."
			::= { wsSwNtpSystem 10 }


--   1.3.6.1.4.1.388.14.2.1.5.13
-- 1.3.6.1.4.1.388.14.2.12.1.5.13
		-- 1.3.6.1.4.1.388.14.2.12.1.11.11
		wsSwSysJitter OBJECT-TYPE
			SYNTAX DisplayString
			MAX-ACCESS read-only
			STATUS current
			DESCRIPTION
				"Description."
			::= { wsSwNtpSystem 11 }


--   1.3.6.1.4.1.388.14.2.1.5.14
-- 1.3.6.1.4.1.388.14.2.12.1.5.14
		-- 1.3.6.1.4.1.388.14.2.12.1.11.12
		wsSwSysStability OBJECT-TYPE
			SYNTAX DisplayString
			MAX-ACCESS read-only
			STATUS current
			DESCRIPTION
				"Description."
			::= { wsSwNtpSystem 12 }


--   1.3.6.1.4.1.388.14.2.1.6
-- 1.3.6.1.4.1.388.14.2.12.1.6
		-- 1.3.6.1.4.1.388.14.2.12.1.12
		wsSwNtpSymmKeyTable OBJECT-TYPE
			SYNTAX SEQUENCE OF WsSwNtpSymmKeyEntry
			MAX-ACCESS not-accessible
			STATUS current
			DESCRIPTION
				"Description."
			::= { wsSwNTPModule 12 }


--   1.3.6.1.4.1.388.14.2.1.6.1
-- 1.3.6.1.4.1.388.14.2.12.1.6.1
		-- 1.3.6.1.4.1.388.14.2.12.1.12.1
		wsSwNtpSymmKeyEntry OBJECT-TYPE
			SYNTAX WsSwNtpSymmKeyEntry
			MAX-ACCESS not-accessible
			STATUS current
			DESCRIPTION
				"Description."
			INDEX { wsSwNtpKeyId }
			::= { wsSwNtpSymmKeyTable 1 }


		WsSwNtpSymmKeyEntry ::=
			SEQUENCE {
				wsSwNtpKeyId
					NtpKeyIdentifier,
				wsSwNtpKeyValue
					DisplayString,
				wsSwNtpKeyIfTrusted
					TruthValue,
				wsSwNtpKeyRowStatus
					RowStatus
			 }

--   1.3.6.1.4.1.388.14.2.1.6.1.1
-- 1.3.6.1.4.1.388.14.2.12.1.6.1.1
		-- 1.3.6.1.4.1.388.14.2.12.1.12.1.1
		wsSwNtpKeyId OBJECT-TYPE
			SYNTAX NtpKeyIdentifier
			MAX-ACCESS read-only
			STATUS current
			DESCRIPTION
				"Description."
			::= { wsSwNtpSymmKeyEntry 1 }


--   1.3.6.1.4.1.388.14.2.1.6.1.2
-- 1.3.6.1.4.1.388.14.2.12.1.6.1.2
		-- 1.3.6.1.4.1.388.14.2.12.1.12.1.2
		wsSwNtpKeyValue OBJECT-TYPE
			SYNTAX DisplayString
			MAX-ACCESS read-create
			STATUS current
			DESCRIPTION
				"Description."
			::= { wsSwNtpSymmKeyEntry 2 }


--   1.3.6.1.4.1.388.14.2.1.6.1.3
-- 1.3.6.1.4.1.388.14.2.12.1.6.1.3
		-- 1.3.6.1.4.1.388.14.2.12.1.12.1.3
		wsSwNtpKeyIfTrusted OBJECT-TYPE
			SYNTAX TruthValue
			MAX-ACCESS read-create
			STATUS current
			DESCRIPTION
				"Description."
			::= { wsSwNtpSymmKeyEntry 3 }


--   1.3.6.1.4.1.388.14.2.1.6.1.4
-- 1.3.6.1.4.1.388.14.2.12.1.6.1.4
		-- 1.3.6.1.4.1.388.14.2.12.1.12.1.4
		wsSwNtpKeyRowStatus OBJECT-TYPE
			SYNTAX RowStatus
			MAX-ACCESS read-create
			STATUS current
			DESCRIPTION
				"Description."
			::= { wsSwNtpSymmKeyEntry 4 }


--   1.3.6.1.4.1.388.14.2.1.7
-- 1.3.6.1.4.1.388.14.2.12.1.7
		-- 1.3.6.1.4.1.388.14.2.12.1.13
		wsSwNTPNeighborTable OBJECT-TYPE
			SYNTAX SEQUENCE OF WsSwNTPNeighborEntry
			MAX-ACCESS not-accessible
			STATUS current
			DESCRIPTION
				"Description."
			::= { wsSwNTPModule 13 }


--   1.3.6.1.4.1.388.14.2.1.7.1
-- 1.3.6.1.4.1.388.14.2.12.1.7.1
		-- 1.3.6.1.4.1.388.14.2.12.1.13.1
		wsSwNTPNeighborEntry OBJECT-TYPE
			SYNTAX WsSwNTPNeighborEntry
			MAX-ACCESS not-accessible
			STATUS current
			DESCRIPTION
				"Each peers' entry provides NTP information retrieved
				from a particular peer NTP server.  Each peer is
				identified by a unique association identifier.

				Entries are automatically created when the user
				configures the NTP server to be associated with remote
				peers.  Similarly entries are deleted when the user
				removes the peer association from the NTP server.

				Entries can also be created by the management station
				by setting values for the following objects:
				cntpPeersPeerAddress or cntpPeersPeerName,
				cntpPeersHostAddress and
				cntpPeersMode and making the cntpPeersEntryStatus as
				active(1).  At the least, the management station has
				to set a value for cntpPeersPeerAddress or
				cntpPeersPeerName to make the row active."
			INDEX { wsSwNeighborPeerName, wsSwNeighborType }
			::= { wsSwNTPNeighborTable 1 }


		WsSwNTPNeighborEntry ::=
			SEQUENCE {
				wsSwNeighborPeerName
					DisplayString,
				wsSwNeighborType
					INTEGER,
				wsSwNeighborAuthKey
					INTEGER,
				wsSwNeighborPrefPeer
					INTEGER,
				wsSwNeighborNtpVersion
					INTEGER,
				wsSwNeighborEntryStatus
					RowStatus
			 }

--   1.3.6.1.4.1.388.14.2.1.7.1.1
-- 1.3.6.1.4.1.388.14.2.12.1.7.1.1
		-- 1.3.6.1.4.1.388.14.2.12.1.13.1.1
		wsSwNeighborPeerName OBJECT-TYPE
			SYNTAX DisplayString
			MAX-ACCESS read-only
			STATUS current
			DESCRIPTION
				"The address of the peer. "
			::= { wsSwNTPNeighborEntry 1 }


--   1.3.6.1.4.1.388.14.2.1.7.1.2
-- 1.3.6.1.4.1.388.14.2.12.1.7.1.2
		-- 1.3.6.1.4.1.388.14.2.12.1.13.1.2
		wsSwNeighborType OBJECT-TYPE
			SYNTAX INTEGER
				{
				server(0),
				peer(1),
				broadcast(2)
				}
			MAX-ACCESS read-only
			STATUS current
			DESCRIPTION
				"The type can be server(0), peer(1) or broadcast(2)"
			::= { wsSwNTPNeighborEntry 2 }


--   -1 -> Autokey, 0 -> No authentication
-- > 0 -> Symmetric key value to be used for authentication.
-- 1.3.6.1.4.1.388.14.2.1.7.1.3
-- 1.3.6.1.4.1.388.14.2.12.1.7.1.3
		-- 1.3.6.1.4.1.388.14.2.12.1.13.1.3
		wsSwNeighborAuthKey OBJECT-TYPE
			SYNTAX INTEGER (-1..255)
			MAX-ACCESS read-create
			STATUS current
			DESCRIPTION
				"Valid key values are 1 to 65534. Value of -1 indicates Autokey option. Value 0 indicates removal of key."
			::= { wsSwNTPNeighborEntry 3 }


--   1.3.6.1.4.1.388.14.2.1.7.1.5
-- 1.3.6.1.4.1.388.14.2.12.1.7.1.5
		-- 1.3.6.1.4.1.388.14.2.12.1.13.1.4
		wsSwNeighborPrefPeer OBJECT-TYPE
			SYNTAX INTEGER
				{
				no(1),
				yes(2)
				}
			MAX-ACCESS read-create
			STATUS current
			DESCRIPTION
				"This object specifies whether this peer is the
				preferred one over the others. The valid value for this are no(1) and yes(2)"
			::= { wsSwNTPNeighborEntry 4 }


--   1.3.6.1.4.1.388.14.2.1.7.1.6
-- 1.3.6.1.4.1.388.14.2.12.1.7.1.6
		-- 1.3.6.1.4.1.388.14.2.12.1.13.1.5
		wsSwNeighborNtpVersion OBJECT-TYPE
			SYNTAX INTEGER
				{
				version1(1),
				version2(2),
				version3(3),
				version4(4)
				}
			MAX-ACCESS read-create
			STATUS current
			DESCRIPTION
				"The version values can range from 1 to 4. Value 0 indicates removal of version configuration"
			::= { wsSwNTPNeighborEntry 5 }


--   1.3.6.1.4.1.388.14.2.1.7.1.4
-- 1.3.6.1.4.1.388.14.2.12.1.7.1.4
		-- 1.3.6.1.4.1.388.14.2.12.1.13.1.6
		wsSwNeighborEntryStatus OBJECT-TYPE
			SYNTAX RowStatus
			MAX-ACCESS read-create
			STATUS current
			DESCRIPTION
				"The status object for this row. When a management
				station is creating a new row, it should set the
				value for cntpPeersPeerAddress at least, before the
				row can be made active(1)."
			::= { wsSwNTPNeighborEntry 6 }


--   1.3.6.1.4.1.388.14.2.1.8
-- 1.3.6.1.4.1.388.14.2.12.1.8
		-- 1.3.6.1.4.1.388.14.2.12.1.14
		wsSwPeersStatusTable OBJECT-TYPE
			SYNTAX SEQUENCE OF WsSwPeersStatusEntry
			MAX-ACCESS not-accessible
			STATUS current
			DESCRIPTION
				"Description."
			::= { wsSwNTPModule 14 }


--   1.3.6.1.4.1.388.14.2.1.8.1
-- 1.3.6.1.4.1.388.14.2.12.1.8.1
		-- 1.3.6.1.4.1.388.14.2.12.1.14.1
		wsSwPeersStatusEntry OBJECT-TYPE
			SYNTAX WsSwPeersStatusEntry
			MAX-ACCESS not-accessible
			STATUS current
			DESCRIPTION
				"Description."
			INDEX { wsSwPeersStatusIndex }
			::= { wsSwPeersStatusTable 1 }


		WsSwPeersStatusEntry ::=
			SEQUENCE {
				wsSwPeersStatusIndex
					Unsigned32,
				wsSwPeersStatusPeerAddress
					DisplayString,
				wsSwPeersWhen
					DisplayString,
				wsSwPeersStatusPort
					Integer32,
				wsSwPeersHostAddress
					DisplayString,
				wsSwPeersHostPort
					Integer32,
				wsSwPeersStratum
					NTPStratum,
				wsSwPeersPeerPoll
					NTPPollInterval,
				wsSwPeersHostPoll
					NTPPollInterval,
				wsSwPeersPrecision
					Integer32,
				wsSwPeersRootDelay
					DisplayString,
				wsSwPeersRootDispersion
					DisplayString,
				wsSwPeersRefId
					NTPRefId,
				wsSwPeersRefTime
					DisplayString,
				wsSwPeersOrgTime
					DisplayString,
				wsSwPeersReceiveTime
					DisplayString,
				wsSwPeersTransmitTime
					DisplayString,
				wsSwPeersReach
					Integer32,
				wsSwPeersOffset
					DisplayString,
				wsSwPeersDelay
					DisplayString,
				wsSwPeersDispersion
					DisplayString,
				wsSwPeersSanity
					INTEGER,
				wsSwPeersValidity
					TruthValue,
				wsSwPeersLocalMode
					DisplayString,
				wsSwPeersPeerMode
					DisplayString,
				wsSwPeersAssociationType
					INTEGER,
				wsSwPeersAuthority
					INTEGER,
				wsSwPeersLeapState
					INTEGER,
				wsSwPeersFiltDelay
					DisplayString,
				wsSwPeersFiltOffset
					DisplayString,
				wsSwPeersFiltError
					DisplayString,
				wsSwPeersRemotePollInterval
					Integer32
			 }

		-- 1.3.6.1.4.1.388.14.2.12.1.14.1.1
		wsSwPeersStatusIndex OBJECT-TYPE
			SYNTAX Unsigned32 (1..32768)
			MAX-ACCESS read-only
			STATUS current
			DESCRIPTION
				"Description."
			::= { wsSwPeersStatusEntry 1 }


--  1.3.6.1.4.1.388.14.2.12.1.8.1.1
		-- 1.3.6.1.4.1.388.14.2.12.1.14.1.2
		wsSwPeersStatusPeerAddress OBJECT-TYPE
			SYNTAX DisplayString
			MAX-ACCESS read-only
			STATUS current
			DESCRIPTION
				"Description."
			::= { wsSwPeersStatusEntry 2 }


--  1.3.6.1.4.1.388.14.2.12.1.8.1.2
		-- 1.3.6.1.4.1.388.14.2.12.1.14.1.3
		wsSwPeersWhen OBJECT-TYPE
			SYNTAX DisplayString
			MAX-ACCESS read-only
			STATUS current
			DESCRIPTION
				"Time of Last NTP packet received"
			::= { wsSwPeersStatusEntry 3 }


--  1.3.6.1.4.1.388.14.2.12.1.8.1.3
		-- 1.3.6.1.4.1.388.14.2.12.1.14.1.4
		wsSwPeersStatusPort OBJECT-TYPE
			SYNTAX Integer32
			MAX-ACCESS read-only
			STATUS current
			DESCRIPTION
				"Description."
			::= { wsSwPeersStatusEntry 4 }


--  1.3.6.1.4.1.388.14.2.12.1.8.1.4
		-- 1.3.6.1.4.1.388.14.2.12.1.14.1.5
		wsSwPeersHostAddress OBJECT-TYPE
			SYNTAX DisplayString
			MAX-ACCESS read-only
			STATUS current
			DESCRIPTION
				"The IP address of the local host.  Multi-homing can
				be supported using this object."
			::= { wsSwPeersStatusEntry 5 }


--  1.3.6.1.4.1.388.14.2.12.1.8.1.5
		-- 1.3.6.1.4.1.388.14.2.12.1.14.1.6
		wsSwPeersHostPort OBJECT-TYPE
			SYNTAX Integer32 (1..65535)
			MAX-ACCESS read-only
			STATUS current
			DESCRIPTION
				"The UDP port number on which the local host receives
				NTP messages."
			::= { wsSwPeersStatusEntry 6 }


--  1.3.6.1.4.1.388.14.2.12.1.8.1.7
		-- 1.3.6.1.4.1.388.14.2.12.1.14.1.7
		wsSwPeersStratum OBJECT-TYPE
			SYNTAX NTPStratum
			MAX-ACCESS read-only
			STATUS current
			DESCRIPTION
				"The stratum of the peer clock."
			::= { wsSwPeersStatusEntry 7 }


--  1.3.6.1.4.1.388.14.2.12.1.8.1.8
		-- 1.3.6.1.4.1.388.14.2.12.1.14.1.8
		wsSwPeersPeerPoll OBJECT-TYPE
			SYNTAX NTPPollInterval
			MAX-ACCESS read-only
			STATUS current
			DESCRIPTION
				"The interval at which the peer polls the local host."
			::= { wsSwPeersStatusEntry 8 }


--  1.3.6.1.4.1.388.14.2.12.1.8.1.9
		-- 1.3.6.1.4.1.388.14.2.12.1.14.1.9
		wsSwPeersHostPoll OBJECT-TYPE
			SYNTAX NTPPollInterval
			MAX-ACCESS read-only
			STATUS current
			DESCRIPTION
				"The interval at which the local host polls the peer."
			::= { wsSwPeersStatusEntry 9 }


--  1.3.6.1.4.1.388.14.2.12.1.8.1.10
		-- 1.3.6.1.4.1.388.14.2.12.1.14.1.10
		wsSwPeersPrecision OBJECT-TYPE
			SYNTAX Integer32 (-20..20)
			MAX-ACCESS read-only
			STATUS current
			DESCRIPTION
				"Signed integer indicating the precision of the peer
				clock, in seconds to the nearest power of two.  The
				value must be rounded to the next larger power of
				two; for instance, a 50-Hz (20 ms) or 60-Hz
				(16.67 ms) power-frequency clock would be assigned
				the value -5 (31.25 ms), while a 1000-Hz (1 ms)
				crystal-controlled clock would be assigned the value
				-9 (1.95 ms)."
			::= { wsSwPeersStatusEntry 10 }


--  1.3.6.1.4.1.388.14.2.12.1.8.1.11
		-- 1.3.6.1.4.1.388.14.2.12.1.14.1.11
		wsSwPeersRootDelay OBJECT-TYPE
			SYNTAX DisplayString
			UNITS "seconds"
			MAX-ACCESS read-only
			STATUS current
			DESCRIPTION
				"A signed fixed-point number indicating the total
				round-trip delay in seconds, from the peer to the
				primary reference source at the root of the
				synchronization subnet."
			::= { wsSwPeersStatusEntry 11 }


--  1.3.6.1.4.1.388.14.2.12.1.8.1.12
		-- 1.3.6.1.4.1.388.14.2.12.1.14.1.12
		wsSwPeersRootDispersion OBJECT-TYPE
			SYNTAX DisplayString
			UNITS "seconds"
			MAX-ACCESS read-only
			STATUS current
			DESCRIPTION
				"The maximum error in seconds, of the peer clock
				relative to the primary reference source at the root
				of the synchronization subnet.  Only positive values
				greater than zero are possible."
			::= { wsSwPeersStatusEntry 12 }


--  1.3.6.1.4.1.388.14.2.12.1.8.1.13
		-- 1.3.6.1.4.1.388.14.2.12.1.14.1.13
		wsSwPeersRefId OBJECT-TYPE
			SYNTAX NTPRefId
			MAX-ACCESS read-only
			STATUS current
			DESCRIPTION
				"The reference identifier of the peer."
			::= { wsSwPeersStatusEntry 13 }


--  1.3.6.1.4.1.388.14.2.12.1.8.1.14
		-- 1.3.6.1.4.1.388.14.2.12.1.14.1.14
		wsSwPeersRefTime OBJECT-TYPE
			SYNTAX DisplayString
			MAX-ACCESS read-only
			STATUS current
			DESCRIPTION
				"The local time at the peer when its clock was last
				updated.  If the peer clock has never been
				synchronized, the value is zero."
			::= { wsSwPeersStatusEntry 14 }


--  1.3.6.1.4.1.388.14.2.12.1.8.1.15
		-- 1.3.6.1.4.1.388.14.2.12.1.14.1.15
		wsSwPeersOrgTime OBJECT-TYPE
			SYNTAX DisplayString
			MAX-ACCESS read-only
			STATUS current
			DESCRIPTION
				"The local time at the peer, when its latest
				NTP message was sent.  If the peer becomes unreachable
				the value is set to zero."
			::= { wsSwPeersStatusEntry 15 }


--  1.3.6.1.4.1.388.14.2.12.1.8.1.16
		-- 1.3.6.1.4.1.388.14.2.12.1.14.1.16
		wsSwPeersReceiveTime OBJECT-TYPE
			SYNTAX DisplayString
			MAX-ACCESS read-only
			STATUS current
			DESCRIPTION
				"The local time, when the latest NTP message from
				the peer arrived.  If the peer becomes unreachable
				the value is set to zero."
			::= { wsSwPeersStatusEntry 16 }


--  1.3.6.1.4.1.388.14.2.12.1.8.1.17
		-- 1.3.6.1.4.1.388.14.2.12.1.14.1.17
		wsSwPeersTransmitTime OBJECT-TYPE
			SYNTAX DisplayString
			MAX-ACCESS read-only
			STATUS current
			DESCRIPTION
				"The local time at which the NTP message departed the
				sender."
			::= { wsSwPeersStatusEntry 17 }


--  1.3.6.1.4.1.388.14.2.12.1.8.1.19
		-- 1.3.6.1.4.1.388.14.2.12.1.14.1.18
		wsSwPeersReach OBJECT-TYPE
			SYNTAX Integer32 (0..255)
			MAX-ACCESS read-only
			STATUS current
			DESCRIPTION
				"A shift register of used to determine the
				reachability status of the peer, with bits entering
				from the least significant (rightmost) end.  A peer is
				considered reachable if at least one bit in this
				register is set to one i.e, if the value of this
				object is non-zero.
				The data in the shift register would be populated by
				the NTP protocol procedures."
			REFERENCE
				"D.L. Mills, 'Network Time Protocol (Version 3)',
				RFC-1305, March 1992, Section 3.2.3"
			::= { wsSwPeersStatusEntry 18 }


--  1.3.6.1.4.1.388.14.2.12.1.8.1.21
		-- 1.3.6.1.4.1.388.14.2.12.1.14.1.19
		wsSwPeersOffset OBJECT-TYPE
			SYNTAX DisplayString
			UNITS "seconds"
			MAX-ACCESS read-only
			STATUS current
			DESCRIPTION
				"The estimated offset of the peer clock relative to
				the local clock, in seconds.  The host determines the
				value of this object using the NTP clock-filter
				algorithm."
			REFERENCE
				"D.L. Mills, 'Network Time Protocol (Version 3)',
				RFC-1305, March 1992, Section 3.2.5"
			::= { wsSwPeersStatusEntry 19 }


--  1.3.6.1.4.1.388.14.2.12.1.8.1.22
		-- 1.3.6.1.4.1.388.14.2.12.1.14.1.20
		wsSwPeersDelay OBJECT-TYPE
			SYNTAX DisplayString
			UNITS "seconds"
			MAX-ACCESS read-only
			STATUS current
			DESCRIPTION
				"The estimated round-trip delay of the peer clock
				relative to the local clock over the network path
				between them, in seconds.  The host determines the
				value of this object using the NTP clock-filter
				algorithm."
			REFERENCE
				"D.L. Mills, 'Network Time Protocol (Version 3)',
				RFC-1305, March 1992, Section 3.2.5"
			::= { wsSwPeersStatusEntry 20 }


--  1.3.6.1.4.1.388.14.2.12.1.8.1.23
		-- 1.3.6.1.4.1.388.14.2.12.1.14.1.21
		wsSwPeersDispersion OBJECT-TYPE
			SYNTAX DisplayString
			UNITS "seconds"
			MAX-ACCESS read-only
			STATUS current
			DESCRIPTION
				"The estimated maximum error of the peer clock
				relative to the local clock over the network path
				between them, in seconds.  The host determines the
				value of this object using the NTP clock-filter
				algorithm."
			REFERENCE
				"D.L. Mills, 'Network Time Protocol (Version 3)',
				RFC-1305, March 1992, Section 3.2.5"
			::= { wsSwPeersStatusEntry 21 }


		-- 1.3.6.1.4.1.388.14.2.12.1.14.1.22
		wsSwPeersSanity OBJECT-TYPE
			SYNTAX INTEGER
				{
				insane(1),
				sane(2)
				}
			MAX-ACCESS read-only
			STATUS current
			DESCRIPTION
				"Description."
			::= { wsSwPeersStatusEntry 22 }


		-- 1.3.6.1.4.1.388.14.2.12.1.14.1.23
		wsSwPeersValidity OBJECT-TYPE
			SYNTAX TruthValue
			MAX-ACCESS read-only
			STATUS current
			DESCRIPTION
				"Description."
			::= { wsSwPeersStatusEntry 23 }


		-- 1.3.6.1.4.1.388.14.2.12.1.14.1.24
		wsSwPeersLocalMode OBJECT-TYPE
			SYNTAX DisplayString
			MAX-ACCESS read-only
			STATUS current
			DESCRIPTION
				"Description."
			::= { wsSwPeersStatusEntry 24 }


		-- 1.3.6.1.4.1.388.14.2.12.1.14.1.25
		wsSwPeersPeerMode OBJECT-TYPE
			SYNTAX DisplayString
			MAX-ACCESS read-only
			STATUS current
			DESCRIPTION
				"Description."
			::= { wsSwPeersStatusEntry 25 }


		-- 1.3.6.1.4.1.388.14.2.12.1.14.1.26
		wsSwPeersAssociationType OBJECT-TYPE
			SYNTAX INTEGER
				{
				configured(1),
				dynamic(2),
				unknown(3)
				}
			MAX-ACCESS read-only
			STATUS current
			DESCRIPTION
				"Description."
			::= { wsSwPeersStatusEntry 26 }


		-- 1.3.6.1.4.1.388.14.2.12.1.14.1.27
		wsSwPeersAuthority OBJECT-TYPE
			SYNTAX INTEGER
				{
				master(1),
				selected(2),
				candidate(3),
				unknown(4)
				}
			MAX-ACCESS read-only
			STATUS current
			DESCRIPTION
				"Description."
			::= { wsSwPeersStatusEntry 27 }


		-- 1.3.6.1.4.1.388.14.2.12.1.14.1.28
		wsSwPeersLeapState OBJECT-TYPE
			SYNTAX INTEGER
				{
				add(1),
				sub(2),
				unsynced(3),
				unknown(4)
				}
			MAX-ACCESS read-only
			STATUS current
			DESCRIPTION
				"Description."
			::= { wsSwPeersStatusEntry 28 }


		-- 1.3.6.1.4.1.388.14.2.12.1.14.1.29
		wsSwPeersFiltDelay OBJECT-TYPE
			SYNTAX DisplayString
			MAX-ACCESS read-only
			STATUS current
			DESCRIPTION
				"Description."
			::= { wsSwPeersStatusEntry 29 }


		-- 1.3.6.1.4.1.388.14.2.12.1.14.1.30
		wsSwPeersFiltOffset OBJECT-TYPE
			SYNTAX DisplayString
			MAX-ACCESS read-only
			STATUS current
			DESCRIPTION
				"Description."
			::= { wsSwPeersStatusEntry 30 }


		-- 1.3.6.1.4.1.388.14.2.12.1.14.1.31
		wsSwPeersFiltError OBJECT-TYPE
			SYNTAX DisplayString
			MAX-ACCESS read-only
			STATUS current
			DESCRIPTION
				"Description."
			::= { wsSwPeersStatusEntry 31 }


		-- 1.3.6.1.4.1.388.14.2.12.1.14.1.32
		wsSwPeersRemotePollInterval OBJECT-TYPE
			SYNTAX Integer32
			MAX-ACCESS read-only
			STATUS current
			DESCRIPTION
				"Remote Poll Interval"
			::= { wsSwPeersStatusEntry 32 }


--   1.3.6.1.4.1.388.14.2.1.9
-- 1.3.6.1.4.1.388.14.2.12.1.9
		-- 1.3.6.1.4.1.388.14.2.12.1.15
		wsSwNtpMIBConformance OBJECT IDENTIFIER ::= { wsSwNTPModule 15 }


--   1.3.6.1.4.1.388.14.2.1.9.1
-- this module
-- 1.3.6.1.4.1.388.14.2.12.1.9.1
-- this module
		-- 1.3.6.1.4.1.388.14.2.12.1.15.1
		wsSwNtpCompliance MODULE-COMPLIANCE
			STATUS current
			DESCRIPTION
				"Description."
--			MODULE wsSwNTPModule
--				MANDATORY-GROUPS { wsSwNtpGroupAll }
			MODULE -- this module
				MANDATORY-GROUPS { wsSwNtpGroupAll }
			::= { wsSwNtpMIBConformance 1 }


--   1.3.6.1.4.1.388.14.2.1.10
-- 1.3.6.1.4.1.388.14.2.12.1.10
		-- 1.3.6.1.4.1.388.14.2.12.1.16
		wsSWNtpGroups OBJECT IDENTIFIER ::= { wsSwNTPModule 16 }


--   1.3.6.1.4.1.388.14.2.1.10.1
-- 1.3.6.1.4.1.388.14.2.12.1.10.1
		-- 1.3.6.1.4.1.388.14.2.12.1.16.1
		wsSwNtpGroupAll OBJECT-GROUP
			OBJECTS { ntpBroadcastDelay, ntpMasterClockMode, ntpMasterClockStratum, ntpBroadcastClientMode, wsSwSysLeap,
				wsSwSysStratum, wsSwSysPrecision, wsSwSysRootDelay, wsSwSysRootDispersion, wsSwSysRefId,
				wsSwSysRefTime, wsSwSysPoll, wsSwSysClock, wsSwSysFrequency, wsSwSysJitter,
				wsSwSysStability, wsSwNtpKeyId, wsSwNtpKeyValue, wsSwNtpKeyIfTrusted, wsSwNtpKeyRowStatus,
				wsSwNeighborPeerName, wsSwNeighborType, wsSwNeighborAuthKey, wsSwNeighborEntryStatus, wsSwNeighborPrefPeer,
				wsSwNeighborNtpVersion, ntpaccessGroupPeer, ntpaccessGroupQueryOnly, ntpaccessGroupServe, ntpAutoKey,
				ntpaccessGroupServeOnly, ntpAuthenticate, wsSwPeersStatusPeerAddress, wsSwPeersStatusPort, wsSwPeersHostAddress,
				wsSwPeersHostPort, wsSwPeersStratum, wsSwPeersPeerPoll, wsSwPeersHostPoll, wsSwPeersPrecision,
				wsSwPeersRootDelay, wsSwPeersRootDispersion, wsSwPeersRefId, wsSwPeersRefTime, wsSwPeersOrgTime,
				wsSwPeersReceiveTime, wsSwPeersTransmitTime, wsSwPeersReach, wsSwPeersOffset, wsSwPeersDelay,
				wsSwPeersDispersion, wsSwPeersFiltError, wsSwPeersFiltOffset, wsSwPeersFiltDelay, wsSwPeersLeapState,
				wsSwPeersAuthority, wsSwPeersAssociationType, wsSwPeersPeerMode, wsSwPeersLocalMode, wsSwPeersValidity,
				wsSwPeersRemotePollInterval, wsSwPeersStatusIndex, wsSwPeersSanity, wsSwPeersWhen }
			STATUS current
			DESCRIPTION
				"Description."
			::= { wsSWNtpGroups 1 }



	END

--
-- WS-SW-AUTHENTICATEDNTP-MIB.my
--
