-- vim: syntax=mib
--
-- WS-INFRA-PM-MIB.my
-- MIB generated by MG-SOFT Visual MIB Builder Version 6.0  Build 88
-- Friday, May 26, 2006 at 16:37:06
--

	WS-INFRA-PM-MIB DEFINITIONS ::= BEGIN

		IMPORTS
			OBJECT-GROUP, MODULE-COMPLIANCE
				FROM SNMPv2-CONF
			Integer32, Unsigned32, OBJECT-TYPE, MODULE-IDENTITY
				FROM SNMPv2-SMI
			DisplayString, TruthValue, DateAndTime
				FROM SNMPv2-TC
			wsInfraPM
				FROM WS-INFRA-SMI-MIB
			DoActionNow
				FROM WS-TYPE-MIB;


		-- 1.3.6.1.4.1.388.14.1.5.1
		wsInfraProcessMonitor MODULE-IDENTITY
			LAST-UPDATED "200504191125Z"		-- April 19, 2005 at 11:25 GMT
			ORGANIZATION
				"Symbol Technologies"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"process monitor module"
			REVISION "200605241532Z"		-- May 24, 2006 at 15:32 GMT
			DESCRIPTION
				"01a06"
			REVISION "200605121426Z"		-- May 12, 2006 at 14:26 GMT
			DESCRIPTION
				"01a05"
			REVISION "200510271830Z"		-- October 27, 2005 at 18:30 GMT
			DESCRIPTION
				"01a04"
			REVISION "200509021622Z"		-- September 02, 2005 at 16:22 GMT
			DESCRIPTION
				"01a03"
			REVISION "200505191536Z"		-- May 19, 2005 at 15:36 GMT
			DESCRIPTION
				"01a02"
			REVISION "200505181711Z"		-- May 18, 2005 at 17:11 GMT
			DESCRIPTION
				"01a01"
			::= { wsInfraPM 1 }





--
-- Node definitions
--

		-- 1.3.6.1.4.1.388.14.1.5.1.1
		wsInfraProcMonSystemRestart OBJECT-TYPE
			SYNTAX TruthValue
			MAX-ACCESS read-write
			STATUS current
			DESCRIPTION
				"If set to true(1), the Process Monitor will restart
				the system if a failed process reached its max number of
				restarts.  If false(2), the Process Monitor will not
				restart the system."
			::= { wsInfraProcessMonitor 1 }


		-- 1.3.6.1.4.1.388.14.1.5.1.2
		wsInfraProcMonMaxSystemRestarts OBJECT-TYPE
			SYNTAX Unsigned32 (1..5)
			MAX-ACCESS read-write
			STATUS current
			DESCRIPTION
				"Maximum number of times the Process Monitor will restart
				the system because of failed processes."
			::= { wsInfraProcessMonitor 2 }


		-- 1.3.6.1.4.1.388.14.1.5.1.3
		wsInfraProcMonSystemRestartCnt OBJECT-TYPE
			SYNTAX Integer32
			MAX-ACCESS read-only
			STATUS current
			DESCRIPTION
				"System restart count."
			::= { wsInfraProcessMonitor 3 }


		-- 1.3.6.1.4.1.388.14.1.5.1.4
		wsInfraProcMonSystemRestartCntClear OBJECT-TYPE
			SYNTAX DoActionNow
			MAX-ACCESS read-write
			STATUS current
			DESCRIPTION
				"Clear the restart counter for the system."
			::= { wsInfraProcessMonitor 4 }


		-- 1.3.6.1.4.1.388.14.1.5.1.5
		wsInfraProcMonProcessTable OBJECT-TYPE
			SYNTAX SEQUENCE OF WsInfraProcMonProcessEntry
			MAX-ACCESS not-accessible
			STATUS current
			DESCRIPTION
				"List of processes that are monitored by Process
				Monitor."
			::= { wsInfraProcessMonitor 5 }


		-- 1.3.6.1.4.1.388.14.1.5.1.5.1
		wsInfraProcMonProcessEntry OBJECT-TYPE
			SYNTAX WsInfraProcMonProcessEntry
			MAX-ACCESS not-accessible
			STATUS current
			DESCRIPTION
				" "
			INDEX { wsInfraProcMonProcessIndex }
			::= { wsInfraProcMonProcessTable 1 }


		WsInfraProcMonProcessEntry ::=
			SEQUENCE {
				wsInfraProcMonProcessIndex
					Integer32,
				wsInfraProcMonProcessName
					DisplayString,
				wsInfraProcMonProcessPid
					Integer32,
				wsInfraProcMonProcessMaxRestart
					Integer32,
				wsInfraProcMonProcessStartCount
					Integer32,
				wsInfraProcMonProcessLastHeard
					DateAndTime,
				wsInfraProcMonProcessLastStarted
					DateAndTime
			 }

		-- 1.3.6.1.4.1.388.14.1.5.1.5.1.1
		wsInfraProcMonProcessIndex OBJECT-TYPE
			SYNTAX Integer32 (1..100)
			MAX-ACCESS accessible-for-notify
			STATUS current
			DESCRIPTION
				"Simple index."
			::= { wsInfraProcMonProcessEntry 1 }


		-- 1.3.6.1.4.1.388.14.1.5.1.5.1.2
		wsInfraProcMonProcessName OBJECT-TYPE
			SYNTAX DisplayString (SIZE (0..20))
			MAX-ACCESS read-only
			STATUS current
			DESCRIPTION
				"Process name."
			::= { wsInfraProcMonProcessEntry 2 }


		-- 1.3.6.1.4.1.388.14.1.5.1.5.1.3
		wsInfraProcMonProcessPid OBJECT-TYPE
			SYNTAX Integer32
			MAX-ACCESS read-only
			STATUS current
			DESCRIPTION
				"Process ID."
			::= { wsInfraProcMonProcessEntry 3 }


		-- 1.3.6.1.4.1.388.14.1.5.1.5.1.4
		wsInfraProcMonProcessMaxRestart OBJECT-TYPE
			SYNTAX Integer32 (0..10)
			MAX-ACCESS read-only
			STATUS current
			DESCRIPTION
				"Maximum number of times the Process Monitor will attempt
				to restart the process when it fails."
			::= { wsInfraProcMonProcessEntry 4 }


		-- 1.3.6.1.4.1.388.14.1.5.1.5.1.5
		wsInfraProcMonProcessStartCount OBJECT-TYPE
			SYNTAX Integer32
			MAX-ACCESS read-only
			STATUS current
			DESCRIPTION
				"Number of times the process was started by the Process
				Monitor."
			::= { wsInfraProcMonProcessEntry 5 }


		-- 1.3.6.1.4.1.388.14.1.5.1.5.1.6
		wsInfraProcMonProcessLastHeard OBJECT-TYPE
			SYNTAX DateAndTime
			MAX-ACCESS read-only
			STATUS current
			DESCRIPTION
				"The last time Process Monitor received a heartbeat
				message from the process."
			::= { wsInfraProcMonProcessEntry 6 }


		-- 1.3.6.1.4.1.388.14.1.5.1.5.1.7
		wsInfraProcMonProcessLastStarted OBJECT-TYPE
			SYNTAX DateAndTime
			MAX-ACCESS read-only
			STATUS current
			DESCRIPTION
				"The last time the Process Monitor started the process."
			::= { wsInfraProcMonProcessEntry 7 }


		-- 1.3.6.1.4.1.388.14.1.5.1.6
		wsInfraProcMonHistTable OBJECT-TYPE
			SYNTAX SEQUENCE OF WsInfraProcMonHistEntry
			MAX-ACCESS not-accessible
			STATUS current
			DESCRIPTION
				"List of history entries for monitored processes."
			::= { wsInfraProcessMonitor 6 }


		-- 1.3.6.1.4.1.388.14.1.5.1.6.1
		wsInfraProcMonHistEntry OBJECT-TYPE
			SYNTAX WsInfraProcMonHistEntry
			MAX-ACCESS not-accessible
			STATUS current
			DESCRIPTION
				" "
			INDEX { wsInfraProcMonProcessIndex, wsInfraProcMonHistIndex }
			::= { wsInfraProcMonHistTable 1 }


		WsInfraProcMonHistEntry ::=
			SEQUENCE {
				wsInfraProcMonHistIndex
					Integer32,
				wsInfraProcMonHistTimestamp
					DateAndTime,
				wsInfraProcMonHistEvent
					INTEGER,
				wsInfraProcMonHistState
					INTEGER
			 }

		-- 1.3.6.1.4.1.388.14.1.5.1.6.1.1
		wsInfraProcMonHistIndex OBJECT-TYPE
			SYNTAX Integer32 (1..1000)
			MAX-ACCESS accessible-for-notify
			STATUS current
			DESCRIPTION
				"Simple index."
			::= { wsInfraProcMonHistEntry 1 }


		-- 1.3.6.1.4.1.388.14.1.5.1.6.1.2
		wsInfraProcMonHistTimestamp OBJECT-TYPE
			SYNTAX DateAndTime
			MAX-ACCESS read-only
			STATUS current
			DESCRIPTION
				"Time when the process changed its state."
			::= { wsInfraProcMonHistEntry 2 }


		-- 1.3.6.1.4.1.388.14.1.5.1.6.1.3
		wsInfraProcMonHistEvent OBJECT-TYPE
			SYNTAX INTEGER
				{
				init(1),
				up(2),
				down(3),
				failed(4),
				heartbeat(5),
				shutdown(6),
				stopMonitoring(7),
				resumeMonitoring(8)
				}
			MAX-ACCESS read-only
			STATUS current
			DESCRIPTION
				"The event that caused the process to change its state."
			::= { wsInfraProcMonHistEntry 3 }


		-- 1.3.6.1.4.1.388.14.1.5.1.6.1.4
		wsInfraProcMonHistState OBJECT-TYPE
			SYNTAX INTEGER
				{
				unknown(1),
				running(2),
				notRunning(3),
				notResponding(4),
				kill(5),
				down(6),
				shutdown(7),
				notMonitoring(8),
				resumeMonitoring(9)
				}
			MAX-ACCESS read-only
			STATUS current
			DESCRIPTION
				"The new state the process moved to."
			::= { wsInfraProcMonHistEntry 4 }


		-- 1.3.6.1.4.1.388.14.1.5.1.100
		wsInfraPMMIBConformance OBJECT IDENTIFIER ::= { wsInfraProcessMonitor 100 }


		-- 1.3.6.1.4.1.388.14.1.5.1.100.1
		wsInfraPMMIBCompliances OBJECT IDENTIFIER ::= { wsInfraPMMIBConformance 1 }


		-- 1.3.6.1.4.1.388.14.1.5.1.100.1.1
		wsInfraPMMIBCompliance MODULE-COMPLIANCE
			STATUS current
			DESCRIPTION
				"PM mib compliance"
			MODULE -- this module
				MANDATORY-GROUPS { wsInfraMIBProcMonGroup }
			::= { wsInfraPMMIBCompliances 1 }


		-- 1.3.6.1.4.1.388.14.1.5.1.100.2
		wsInfraPMMIBGroups OBJECT IDENTIFIER ::= { wsInfraPMMIBConformance 2 }


		-- 1.3.6.1.4.1.388.14.1.5.1.100.2.1
		wsInfraMIBProcMonGroup OBJECT-GROUP
			OBJECTS { wsInfraProcMonProcessStartCount, wsInfraProcMonSystemRestartCntClear, wsInfraProcMonSystemRestartCnt, wsInfraProcMonProcessLastStarted, wsInfraProcMonSystemRestart,
				wsInfraProcMonMaxSystemRestarts, wsInfraProcMonProcessIndex, wsInfraProcMonProcessName, wsInfraProcMonProcessPid, wsInfraProcMonProcessMaxRestart,
				wsInfraProcMonProcessLastHeard, wsInfraProcMonHistIndex, wsInfraProcMonHistTimestamp, wsInfraProcMonHistEvent, wsInfraProcMonHistState
				 }
			STATUS current
			DESCRIPTION
				"proc mon mib group"
			::= { wsInfraPMMIBGroups 1 }



	END

--
-- WS-INFRA-PM-MIB.my
--
