-- vim: syntax=mib
--
-- WS-INFRA-AUTO-UPDATE-MIB.my
-- MIB generated by MG-SOFT Visual MIB Builder Version 6.0  Build 88
-- Saturday, October 07, 2006 at 15:45:04
--

	WS-INFRA-AUTO-UPDATE-MIB DEFINITIONS ::= BEGIN

		IMPORTS
			OBJECT-GROUP, MODULE-COMPLIANCE
				FROM SNMPv2-CONF
			IpAddress, Unsigned32, OBJECT-TYPE, MODULE-IDENTITY
				FROM SNMPv2-SMI
			DisplayString, TruthValue, RowStatus
				FROM SNMPv2-TC
			wsInfraAutoUpdate
				FROM WS-INFRA-SMI-MIB
			DoActionNow
				FROM WS-TYPE-MIB;


		-- 1.3.6.1.4.1.388.14.1.11.1
		wsInfraAutoUpdateModule MODULE-IDENTITY
			LAST-UPDATED "200608091334Z"		-- August 09, 2006 at 13:34 GMT
			ORGANIZATION
				"Symbol Technologies"
			CONTACT-INFO
				"Contact-info."
			DESCRIPTION
				"Description."
			REVISION "200610071517Z"		-- October 07, 2006 at 15:17 GMT
			DESCRIPTION
				"Added AutoUpdate start."
			REVISION "200608111634Z"		-- August 11, 2006 at 16:34 GMT
			DESCRIPTION
				"Changed Name to AutoUpdate"
			REVISION "200608091540Z"		-- August 09, 2006 at 15:40 GMT
			DESCRIPTION
				"Added Auto Update MIB for monarch"
			::= { wsInfraAutoUpdate 1 }



--
-- Type definitions
--

		DoActionState ::= INTEGER
			{
			success(1),
			failure(2),
			inProgress(3)
			}



--
-- Node definitions
--

		-- 1.3.6.1.4.1.388.14.1.11.1.1
		wsInfraAutoUpdateTable OBJECT-TYPE
			SYNTAX SEQUENCE OF WsInfraAutoUpdateEntry
			MAX-ACCESS not-accessible
			STATUS current
			DESCRIPTION
				"Description."
			::= { wsInfraAutoUpdateModule 1 }


		-- 1.3.6.1.4.1.388.14.1.11.1.1.1
		wsInfraAutoUpdateEntry OBJECT-TYPE
			SYNTAX WsInfraAutoUpdateEntry
			MAX-ACCESS not-accessible
			STATUS current
			DESCRIPTION
				"Description."
			INDEX { wsInfraAutoUpdateIndex }
			::= { wsInfraAutoUpdateTable 1 }


		WsInfraAutoUpdateEntry ::=
			SEQUENCE {
				wsInfraAutoUpdateIndex
					Unsigned32,
				wsInfraAutoUpdateEnableUpdate
					TruthValue,
				wsInfraAutoUpdateFileLoc
					DisplayString,
				wsInfraAutoUpdateSvrIpAddr
					IpAddress,
				wsInfraAutoUpdateSvrProtocol
					INTEGER,
				wsInfraAutoUpdateSvrUsername
					DisplayString,
				wsInfraAutoUpdateSvrPassword
					DisplayString,
				wsInfraAutoUpdateRowStatus
					RowStatus
			 }

		-- 1.3.6.1.4.1.388.14.1.11.1.1.1.1
		wsInfraAutoUpdateIndex OBJECT-TYPE
			SYNTAX Unsigned32 (1..3)
			MAX-ACCESS read-only
			STATUS current
			DESCRIPTION
				"Description."
			::= { wsInfraAutoUpdateEntry 1 }


		-- 1.3.6.1.4.1.388.14.1.11.1.1.1.2
		wsInfraAutoUpdateEnableUpdate OBJECT-TYPE
			SYNTAX TruthValue
			MAX-ACCESS read-write
			STATUS current
			DESCRIPTION
				"Description."
			::= { wsInfraAutoUpdateEntry 2 }


		-- 1.3.6.1.4.1.388.14.1.11.1.1.1.3
		wsInfraAutoUpdateFileLoc OBJECT-TYPE
			SYNTAX DisplayString (SIZE (0..128))
			MAX-ACCESS read-write
			STATUS current
			DESCRIPTION
				"Description."
			::= { wsInfraAutoUpdateEntry 3 }


		-- 1.3.6.1.4.1.388.14.1.11.1.1.1.4
		wsInfraAutoUpdateSvrIpAddr OBJECT-TYPE
			SYNTAX IpAddress
			MAX-ACCESS read-write
			STATUS current
			DESCRIPTION
				"Description."
			::= { wsInfraAutoUpdateEntry 4 }


		-- 1.3.6.1.4.1.388.14.1.11.1.1.1.5
		wsInfraAutoUpdateSvrProtocol OBJECT-TYPE
			SYNTAX INTEGER
				{
				none(0),
				stdinout(1),
				system(2),
				nvram(3),
				flash(4),
				slot0(5),
				scp(6),
				sftp(7),
				http(8),
				ftp(9),
				tftp(10)
				}
			MAX-ACCESS read-write
			STATUS current
			DESCRIPTION
				"Description."
			::= { wsInfraAutoUpdateEntry 5 }


		-- 1.3.6.1.4.1.388.14.1.11.1.1.1.6
		wsInfraAutoUpdateSvrUsername OBJECT-TYPE
			SYNTAX DisplayString (SIZE (0..49))
			MAX-ACCESS read-write
			STATUS current
			DESCRIPTION
				"Description."
			::= { wsInfraAutoUpdateEntry 6 }


		-- 1.3.6.1.4.1.388.14.1.11.1.1.1.7
		wsInfraAutoUpdateSvrPassword OBJECT-TYPE
			SYNTAX DisplayString (SIZE (0..49))
			MAX-ACCESS read-write
			STATUS current
			DESCRIPTION
				"Description."
			::= { wsInfraAutoUpdateEntry 7 }


		-- 1.3.6.1.4.1.388.14.1.11.1.1.1.8
		wsInfraAutoUpdateRowStatus OBJECT-TYPE
			SYNTAX RowStatus
			MAX-ACCESS read-write
			STATUS current
			DESCRIPTION
				"Description."
			::= { wsInfraAutoUpdateEntry 8 }


		-- 1.3.6.1.4.1.388.14.1.11.1.2
		wsInfraAutoUpdateImageFileVersion OBJECT-TYPE
			SYNTAX DisplayString (SIZE (0..29))
			MAX-ACCESS read-write
			STATUS current
			DESCRIPTION
				"Description."
			::= { wsInfraAutoUpdateModule 2 }


		-- 1.3.6.1.4.1.388.14.1.11.1.3
		wsInfraAutoUpdateStart OBJECT-TYPE
			SYNTAX DoActionNow
			MAX-ACCESS read-write
			STATUS current
			DESCRIPTION
				"Start Update Manually."
			::= { wsInfraAutoUpdateModule 3 }


		-- 1.3.6.1.4.1.388.14.1.11.1.100
		wsInfraAutoUpdateMIBConformance OBJECT IDENTIFIER ::= { wsInfraAutoUpdateModule 100 }


		-- 1.3.6.1.4.1.388.14.1.11.1.100.1
		wsInfraAutoUpdateMIBGroups OBJECT IDENTIFIER ::= { wsInfraAutoUpdateMIBConformance 1 }


		-- 1.3.6.1.4.1.388.14.1.11.1.100.1.1
		wsInfraAutoUpdateGroup OBJECT-GROUP
			OBJECTS { wsInfraAutoUpdateIndex, wsInfraAutoUpdateEnableUpdate, wsInfraAutoUpdateFileLoc, wsInfraAutoUpdateSvrIpAddr, wsInfraAutoUpdateSvrProtocol,
				wsInfraAutoUpdateSvrUsername, wsInfraAutoUpdateSvrPassword, wsInfraAutoUpdateStart, wsInfraAutoUpdateImageFileVersion, wsInfraAutoUpdateRowStatus
				 }
			STATUS current
			DESCRIPTION
				"Description."
			::= { wsInfraAutoUpdateMIBGroups 1 }


		-- 1.3.6.1.4.1.388.14.1.11.1.100.2
		wsInfraAutoUpdateMIBCompliances OBJECT IDENTIFIER ::= { wsInfraAutoUpdateMIBConformance 2 }


		-- 1.3.6.1.4.1.388.14.1.11.1.100.2.1
		wsInfraAutoUpdateMibCompliance MODULE-COMPLIANCE
			STATUS current
			DESCRIPTION
				"Description."
			MODULE -- this module
				MANDATORY-GROUPS { wsInfraAutoUpdateGroup }
			::= { wsInfraAutoUpdateMIBCompliances 1 }



	END

--
-- WS-INFRA-AUTO-UPDATE-MIB.my
--
