HP-ICF-8023-RPTR DEFINITIONS ::= BEGIN

       IMPORTS
           Integer32, Counter32,
           OBJECT-TYPE, MODULE-IDENTITY, NOTIFICATION-TYPE
               FROM SNMPv2-SMI
           DisplayString, TruthValue
               FROM SNMPv2-TC
           MODULE-COMPLIANCE, OBJECT-GROUP, NOTIFICATION-GROUP
               FROM SNMPv2-CONF
           rptrPortAutoPartitionState
               FROM SNMP-REPEATER-MIB  -- 802.3 Repeater MIB
           rpMauMediaAvailable, rpMauGroupIndex, rpMauPortIndex,
           rpMauIndex
               FROM MAU-MIB
           hpicfObjectModules, hpicfRepeater, hpicf8023RptrTrapsPrefix
               FROM HP-ICF-OID;

       hpicf8023RptrMib MODULE-IDENTITY
            LAST-UPDATED "200011032210Z"  -- November 3, 2000
            ORGANIZATION "Hewlett Packard Company,
                          Network Infrastructure Solutions"
            CONTACT-INFO
                    "Hewlett Packard Company
                     8000 Foothills Blvd.
                     Roseville, CA 95747"
            DESCRIPTION
                    "This MIB module contains objects that provide
                    HP-specific extensions to the 802.3 Repeater MIB."

            REVISION     "200011032210Z"  -- November 3, 2000
            DESCRIPTION  "Updated division name."

            REVISION     "9807162027Z"  -- July 16, 1998
            DESCRIPTION
                    "Added repeater port auto-negotiation objects."

            REVISION     "9609100219Z"  -- September 10, 1996
            DESCRIPTION
                    "Split this MIB module from the former monolithic
                    hp-icf MIB.  Added hpicf8023MultiRptr groups.
                    Deprecated objects that presumed a single repeater
                    segment."
            REVISION     "9402250000Z"  -- February 25, 1994
            DESCRIPTION
                    "Initial revision of this MIB module.  Released
                    with the AdvanceStack 10BaseT hubs: HPJ2600A,
                    HPJ2601A and HPJ2602A and agent module HPJ2603A."
            ::= { hpicfObjectModules 9 }


       hpRptrBasic        OBJECT IDENTIFIER ::= { hpicfRepeater 1 }
       hpRptrBasicGlobal  OBJECT IDENTIFIER ::= { hpRptrBasic 1 }


       hpRptrEntityName OBJECT-TYPE
           SYNTAX     DisplayString (SIZE (0..15))
           MAX-ACCESS read-only
           STATUS     deprecated
           DESCRIPTION
                   "********* THIS OBJECT IS DEPRECATED *********

                   The local name of this repeater.  This is the
                   same value as hpicfEntityName in the case where
                   there is Distributed Management Protocol to access
                   this device.

                   For SNMPv1, this name is appended to the agent
                   community name to obtain a community name to use
                   to specify that the agent should proxy to this
                   repeater.  For example, if this agent has a
                   community with a community name of 'public', and
                   the value of this object is 'repeater1', the
                   community 'public/repeater1' will specify that the
                   agent should proxy to the public community of the
                   repeater1 box to obtain management information
                   about this repeater.

                   If an agent receives a management request where
                   the localEntity is not specified, it will default
                   to the local repeater on which this agent is
                   executing.

                   This object has been deprecated.  Since it is a
                   scalar, it does not scale to systems containing
                   multiple repeater segments.  In addition, it is only
                   considered useful in systems supporting the
                   Distributed Management Chain, which has also been
                   deprecated."
           ::= { hpRptrBasicGlobal 1 }

       hpRptrThinlanFault OBJECT-TYPE
           SYNTAX     TruthValue
           MAX-ACCESS read-write
           STATUS     deprecated
           DESCRIPTION
                   "********* THIS OBJECT IS DEPRECATED *********

                   When set to 'true' this object causes the Fault
                   Led to blink if the ThinLan Port is segmented.

                   This object has been deprecated.  It only makes
                   sense in systems that support a single BNC port."
           ::= { hpRptrBasicGlobal 2 }

       hpRptrSqeEnabled OBJECT-TYPE
           SYNTAX     TruthValue
           MAX-ACCESS read-only
           STATUS     deprecated
           DESCRIPTION
                   "********* THIS OBJECT IS DEPRECATED *********

                   When 'true', this flag indicates that SQE has
                   been detected for the last ten agent transmits and
                   there is a high probability that the SQE switch on
                   the transceiver attached to the AUI port is set to
                   Enabled, when it should be Disabled.

                   This object has been deprecated, since it presumes
                   that the system will only have a single AUI port.
                   It has been replaced by the hpRptrPtSqeEnabled
                   object."
           ::= { hpRptrBasicGlobal 3 }

       hpRptrRobustHealing OBJECT-TYPE
           SYNTAX     TruthValue
           MAX-ACCESS read-write
           STATUS     deprecated
           DESCRIPTION
                   "********* THIS OBJECT IS DEPRECATED *********

                   When this flag is set to 'true', it enables
                   robust port healing mode.  The 802.3 specification
                   states that a segmented port is healed by
                   successfully transmitting or receiving a packet on
                   the port.  This mode disables port healing on
                   successful packet reception and requires that a
                   packet be successfully transmitted on a port in
                   order for a segmented port to be healed."
           ::= { hpRptrBasicGlobal 4 }

       hpRptrBasicGroup  OBJECT IDENTIFIER ::= { hpRptrBasic 2 }

       hpRptrBasicGroupTable OBJECT-TYPE
           SYNTAX     SEQUENCE OF HpRptrBasicGroupEntry
           MAX-ACCESS not-accessible
           STATUS     deprecated
           DESCRIPTION
                   "********* THIS OBJECT IS DEPRECATED *********

                   HP specific extensions to the rptrGroupTable."
           ::= { hpRptrBasicGroup 1 }

       hpRptrBasicGroupEntry OBJECT-TYPE
           SYNTAX     HpRptrBasicGroupEntry
           MAX-ACCESS not-accessible
           STATUS     deprecated
           DESCRIPTION
                   "********* THIS OBJECT IS DEPRECATED *********

                   An entry in the table, containing HP extensions
                   for a specific group."
           INDEX      { hpRptrGrpGroupIndex }
           ::= { hpRptrBasicGroupTable 1 }

       HpRptrBasicGroupEntry ::=
           SEQUENCE {
               hpRptrGrpGroupIndex             Integer32,
               hpRptrGrpPortsAdminStatus       OCTET STRING,
               hpRptrGrpPortsSegStatus         OCTET STRING,
               hpRptrGrpPortsMediaAvailable    OCTET STRING,
               hpRptrGrpPortsLinkbeatEnabled   OCTET STRING,
               hpRptrGrpPortsOperStatus        OCTET STRING
           }

       hpRptrGrpGroupIndex OBJECT-TYPE
           SYNTAX     Integer32 (1..2147483647)
           MAX-ACCESS read-only
           STATUS     deprecated
           DESCRIPTION
                   "********* THIS OBJECT IS DEPRECATED *********

                   The group within the repeater for which this
                   entry contains information.  This object has the
                   same value as the corresponding instance of
                   rptrGroupIndex."
           ::= {  hpRptrBasicGroupEntry 1 }

       hpRptrGrpPortsAdminStatus OBJECT-TYPE
           SYNTAX     OCTET STRING (SIZE (1..128))
           MAX-ACCESS read-only
           STATUS     deprecated
           DESCRIPTION
                   "********* THIS OBJECT IS DEPRECATED *********

                   The hpRptrGrpPortsAdminStatus is a bit map of the
                   state of the rptrPortAdminStatus object for all
                   of the ports in this group.  The object  has a one
                   bit for each port for which the value of
                   rptrPortAdminStatus is equal to 'enabled(1)' and
                   a zero bit for each port for which the value of
                   rptrPortAdminStatus is equal to 'disabled(2)'.

                   The bits are placed into the OCTET STRING in the
                   following order:

                       octet   0  octet    1  octet     2  ...
                       bits  7-0  bits   7-0  bits    7-0  ...
                       ports 1-8  ports 9-16  ports 17-24  ...

                   Values of unused bits in the last octet are
                   undefined."
           ::= { hpRptrBasicGroupEntry 2 }

       hpRptrGrpPortsSegStatus OBJECT-TYPE
           SYNTAX     OCTET STRING (SIZE (1..128))
           MAX-ACCESS read-only
           STATUS     deprecated
           DESCRIPTION
                   "********* THIS OBJECT IS DEPRECATED *********

                   The hpRptrGrpPortsSegStatus is a bit map of the
                   state of the rptrPortAutoPartitionState of all of
                   the ports in this group.  The object  has a one
                   bit for each port for which the value of
                   rptrPortAutoPartitionState is equal to
                   'notAutoPartitioned(1)' and a zero bit for each
                   port for which the value of
                   rptrPortAutoPartitionState is equal to
                   'autoPartitioned(2)'.

                   The bits are placed into the OCTET STRING in the
                   following order:

                       octet   0  octet    1  octet     2  ...
                       bits  7-0  bits   7-0  bits    7-0  ...
                       ports 1-8  ports 9-16  ports 17-24  ...

                   Values of unused bits in the last octet are
                   undefined."
           ::= { hpRptrBasicGroupEntry 3 }

       hpRptrGrpPortsMediaAvailable OBJECT-TYPE
           SYNTAX     OCTET STRING (SIZE (1..128))
           MAX-ACCESS read-only
           STATUS     deprecated
           DESCRIPTION
                   "********* THIS OBJECT IS DEPRECATED *********

                   The hpRptrGrpPortsMediaAvailable is a bit map of
                   the state of the rpMauMediaAvailable object for
                   all of the ports in this group.  The object has a
                   one bit for each port for which the value of
                   rpMauMediaAvailable is equal to 'available(3)'
                   and a zero bit for each port for which the value
                   of rpMauMediaAvailable is not equal to
                   'available(3)'.

                   The bits are placed into the OCTET STRING in the
                   following order:

                       octet   0  octet    1  octet     2  ...
                       bits  7-0  bits   7-0  bits    7-0  ...
                       ports 1-8  ports 9-16  ports 17-24  ...

                   Values of unused bits in the last octet are
                   undefined."
           ::= { hpRptrBasicGroupEntry 4 }

       hpRptrGrpPortsLinkbeatEnabled OBJECT-TYPE
           SYNTAX     OCTET STRING (SIZE (1..128))
           MAX-ACCESS read-only
           STATUS     deprecated
           DESCRIPTION
                   "********* THIS OBJECT IS DEPRECATED *********

                   The hpRptrGrpPortsLinkbeatEnabled is a bit map of
                   the state of the hpRptrPtLinkbeatEnable object for
                   all of the ports in this group.  The object  has a
                   one bit for each port for which the value of
                   hpRptrPtLinkbeatEnable is equal to 'true(1)' and
                   a zero bit for each port for which the value of
                   hpRptrPtLinkbeatEnable is equal to 'false(2)'.

                   The bits are placed into the OCTET STRING in the
                   following order:

                       octet   0  octet    1  octet     2  ...
                       bits  7-0  bits   7-0  bits    7-0  ...
                       ports 1-8  ports 9-16  ports 17-24  ...

                   Values of unused bits in the last octet are
                   undefined."
           ::= { hpRptrBasicGroupEntry 5 }

       hpRptrGrpPortsOperStatus OBJECT-TYPE
           SYNTAX     OCTET STRING (SIZE (1..128))
           MAX-ACCESS read-only
           STATUS     deprecated
           DESCRIPTION
                   "********* THIS OBJECT IS DEPRECATED *********

                   The hpRptrGrpPortsOperStatus is a bit map of the
                   state of all hub ports in the group.  The object
                   has a 1 bit for each port that is enabled, not
                   segmented, and the media is available.  Ports on
                   which these conditions are not true have a 0 bit.
                   The bits are placed into the OCTET STRING in the
                   following order:

                       octet   0  octet    1  octet     2  ...
                       bits  7-0  bits   7-0  bits    7-0  ...
                       ports 1-8  ports 9-16  ports 17-24  ...

                   Values of unused bits in the last octet are
                   undefined."
           ::= { hpRptrBasicGroupEntry 6 }


       hpRptrBasicPort   OBJECT IDENTIFIER ::= { hpRptrBasic 3 }

       hpRptrBasicPtTable OBJECT-TYPE
           SYNTAX     SEQUENCE OF HpRptrBasicPtEntry
           MAX-ACCESS not-accessible
           STATUS     current
           DESCRIPTION
                   "HP specific extensions to the rptrPortTable."
           ::= { hpRptrBasicPort 1 }

       hpRptrBasicPtEntry OBJECT-TYPE
           SYNTAX     HpRptrBasicPtEntry
           MAX-ACCESS not-accessible
           STATUS     current
           DESCRIPTION
                   "An entry in the table, containing HP extensions
                   for a specific port."
           INDEX      { hpRptrPtGroupIndex, hpRptrPtPortIndex }
           ::= { hpRptrBasicPtTable 1 }

       HpRptrBasicPtEntry ::=
           SEQUENCE {
               hpRptrPtGroupIndex              Integer32,
               hpRptrPtPortIndex               Integer32,
               hpRptrPtLinkbeatEnable          TruthValue,
               hpRptrPtPolarityReversed        TruthValue,
               hpRptrPtSqeEnabled              TruthValue,
               hpRptrPtMediaAvailTrapEnable    TruthValue,
               hpRptrPtLongCableEnable         TruthValue
           }

       hpRptrPtGroupIndex OBJECT-TYPE
           SYNTAX     Integer32 (1..2147483647)
           MAX-ACCESS read-only
           STATUS     current
           DESCRIPTION
                   "The group containing the port for which this
                   entry contains information.  This object has the
                   same value as the corresponding instance of
                   rptrPortGroupIndex."
           ::= { hpRptrBasicPtEntry 1 }

       hpRptrPtPortIndex OBJECT-TYPE
           SYNTAX     Integer32 (1..2147483647)
           MAX-ACCESS read-only
           STATUS     current
           DESCRIPTION
                   "The port within the group for which this entry
                   contains information.  This object has the same
                   value as the corresponding instance of
                   rptrPortIndex."
           ::= { hpRptrBasicPtEntry 2 }

       hpRptrPtLinkbeatEnable OBJECT-TYPE
           SYNTAX     TruthValue
           MAX-ACCESS read-write
           STATUS     current
           DESCRIPTION
                   "When this flag is set to 'true' the port's link
                   beat is enabled and when set to 'false' it is
                   disabled."
           ::= { hpRptrBasicPtEntry 3 }

       hpRptrPtPolarityReversed OBJECT-TYPE
           SYNTAX     TruthValue
           MAX-ACCESS read-only
           STATUS     current
           DESCRIPTION
                   "This object is used to indicate that the hub port
                   was wired with the positive/negative polarity of
                   its transmit and receive pairs reversed.  Note
                   that the port will continue to operate in this
                   state, with the hub inverting the polarity
                   internally."
           ::= { hpRptrBasicPtEntry 4 }

       hpRptrPtSqeEnabled OBJECT-TYPE
           SYNTAX     TruthValue
           MAX-ACCESS read-only
           STATUS     current
           DESCRIPTION
                   "When 'true', this flag indicates that SQE has
                   been detected for the last ten agent transmits and
                   there is a high probability that the SQE switch on
                   the transceiver attached to this port is set to
                   Enabled, when it should be Disabled.  This value
                   can only be 'true' on AUI ports."
           ::= { hpRptrBasicPtEntry 5 }

       hpRptrPtMediaAvailTrapEnable OBJECT-TYPE
           SYNTAX     TruthValue
           MAX-ACCESS read-write
           STATUS     current
           DESCRIPTION
                   "Indicates whether hpicfMediaAvailDetectTrap and
                   hpicfMediaAvailLostTrap events should be generated
                   for MAUs attached to this port.  This object has the
                   value of 'false' by default.  Setting the value of
                   this object to 'true' will cause a
                   hpicfMediaAvailDetectTrap event to be generated
                   whenever an instance of rpMauMediaAvailable object
                   associated with a MAU attached to this port enters
                   the 'available' state, and a hpicfMediaAvailLostTrap
                   to be generated whenever an instance of the
                   rpMauMediaAvailable object associated with a MAU
                   attached to this port exits the 'available' state.
                   Note that the disposition of these events is
                   controlled by the RMON eventTable.

                   We recommend that this object is only be set to
                   'true' on important ports, such as cascade ports and
                   ports attached to routers bridges, switches, or
                   servers.  Setting this object to 'true' on other
                   ports may cause irrelevant traps.  For example, it
                   is unlikely that an administrator would want to
                   receive a trap every time a user turns their PC off."
           ::= { hpRptrBasicPtEntry 6 }

       hpRptrPtLongCableEnable OBJECT-TYPE
           SYNTAX     TruthValue
           MAX-ACCESS read-write
           STATUS     current
           DESCRIPTION
                   "When this flag is set to 'true' the port's squelch
                   level will be reduced to account for extended
                   distance connections.  When set to 'false', this
                   port's squelch level will be normal.  We recommend
                   that this object only be set to 'true' for ports
                   that are actually connected to long cables."
           ::= { hpRptrBasicPtEntry 7 }

       hpRptrMonitor   OBJECT IDENTIFIER ::= { hpicfRepeater 2 }

       hpRptrMonitorGlobal OBJECT IDENTIFIER ::= { hpRptrMonitor 1 }

       -- Note: The hpRptrMonitorGlobal counters that are composed of
       -- other objects are provided to allow for event testing on
       -- global error conditions.
       --
       -- Note: the hpRptrMonitorGlobal counters have been deprecated.
       -- Since they are scalars, they do not scale to systems
       -- containing multiple repeater segments.  The standard repeater
       -- MIB is adding per-repeater counters for collisions, total
       -- frames, total octets and total errors.  Keeping per-repeater
       -- totals of the other counters included here was felt to be
       -- overkill.  Another factor is that it is quite expensive to
       -- maintain global counters in the presence of port mobility, so
       -- it made sense to limit the number of total counters to those
       -- that would be the most useful for network management.  Note
       -- that most of the information in these counters is available
       -- through other MIBs, such as the RMON etherStats group.

       hpRptrMonCounters
           OBJECT IDENTIFIER ::= { hpRptrMonitorGlobal 1 }

       hpRptrMonGlobalFrames OBJECT-TYPE
           SYNTAX     Counter32
           MAX-ACCESS read-only
           STATUS     deprecated
           DESCRIPTION
                   "********* THIS OBJECT IS DEPRECATED *********

                   The total number of frames of valid frame length
                   that have been received on all ports in this
                   repeater.  This counter is the summation  of the
                   values of the rptrMonitorPortReadableFrames
                   counter for all of the ports in this repeater.
                   Equivalently, this counter is the summation of the
                   values of the rptrMonitorGroupTotalFrames counter
                   for all of the port groups in this repeater."
           REFERENCE
                   "RFC 1516 rptrMonitorPortReadableFrames and
                   rptrMonitorGroupTotalFrames, and IEEE 802.3 Rptr Mgt,
                   19.2.6.2, aReadableFrames."
           ::= { hpRptrMonCounters 1 }

       hpRptrMonGlobalOctets OBJECT-TYPE
           SYNTAX     Counter32
           MAX-ACCESS read-only
           STATUS     deprecated
           DESCRIPTION
                   "********* THIS OBJECT IS DEPRECATED *********

                   The total number of octets contained in the valid
                   frames that have been received on the ports in
                   this repeater.  This counter is the summation of
                   the values of the rptrMonitorPortReadableOctets
                   counter for all of the ports in this repeater.
                   Equivalently, this counter is the summation of the
                   values of the rptrMonitorGroupTotalOctets counter
                   for all of the port groups in this repeater."
           REFERENCE
                   "RFC 1516 rptrMonitorPortReadableOctets and
                   rptrMonitorGroupTotalOctets, and IEEE 802.3 Rptr Mgt,
                   19.2.6.2, aReadableOctets."
           ::= { hpRptrMonCounters 2 }

       hpRptrMonGlobalFCSErrors OBJECT-TYPE
           SYNTAX     Counter32
           MAX-ACCESS read-only
           STATUS     deprecated
           DESCRIPTION
                   "********* THIS OBJECT IS DEPRECATED *********

                   This counter is incremented by one for each frame
                   received on any port with the FCSError signal
                   asserted and the FramingError and CollisionEvent
                   signals deasserted and whose OctetCount is greater
                   than or equal to minFrameSize and less than or
                   equal to maxFrameSize (Ref: 4.4.2.1, IEEE 802.3
                   Std).  This counter is the summation of the values
                   of the rptrMonitorPortFCSErrors counter for all of
                   the ports in this repeater."
           REFERENCE
                   "RFC 1516 rptrMonitorPortFCSErrors and IEEE 802.3
                   Rptr Mgt, 19.2.6.2, aFrameCheckSequenceErrors."
           ::= { hpRptrMonCounters 3 }

       hpRptrMonGlobalAlignmentErrors OBJECT-TYPE
           SYNTAX     Counter32
           MAX-ACCESS read-only
           STATUS     deprecated
           DESCRIPTION
                   "********* THIS OBJECT IS DEPRECATED *********

                   This counter is incremented by one for each frame
                   received on any port with the FCSError and
                   FramingError signals asserted and CollisonEvent
                   signal deasserted and whose OctetCount is greater
                   than or equal to minFrameSize and less than or
                   equal to maxFrameSize (Ref: 4.4.2.1, IEEE 802.3
                   Std).  If hpRptrMonGlobalAlignmentErrors is
                   incremented, then the hpRptrMonGlobalFCSErorrs
                   counter shall not be incremented for the same
                   frame.  This counter is the summation of the
                   values of the rptrMonitorPortAlignmentErrors
                   counter for all of the ports in this repeater."
           REFERENCE
                   "RFC 1516 rptrMonitorPortAlignmentErrors and IEEE
                   802.3 Rptr Mgt, 19.2.6.2, aAlignmentErrors."
           ::= { hpRptrMonCounters 4 }

       hpRptrMonGlobalFrameTooLongs OBJECT-TYPE
           SYNTAX     Counter32
           MAX-ACCESS read-only
           STATUS     deprecated
           DESCRIPTION
                   "********* THIS OBJECT IS DEPRECATED *********

                   This counter is incremented by one for each frame
                   received on any port whose OctetCount is greater
                   than maxFrameSize (Ref: 4.4.2.1, IEEE 802.3 Std).
                   If hpRptrMonGlobalFrameTooLongs is incremented,
                   then neither the hpRptrMonGlobalAlignmentErorrs
                   nor the hpRptrMonGlobalFCSErrors counter shall be
                   incremented for the frame.  This counter is the
                   summation of the values of the
                   rptrMonitorPortFrameTooLongs counter for all of
                   the ports in this repeater."
           REFERENCE
                   "RFC 1516 rptrMonitorPortFrameTooLongs and IEEE 802.3
                   Rptr Mgt, 19.2.6.2, aFramesTooLong"
           ::= { hpRptrMonCounters 5 }

       hpRptrMonGlobalShortEvents OBJECT-TYPE
           SYNTAX     Counter32
           MAX-ACCESS read-only
           STATUS     deprecated
           DESCRIPTION
                   "********* THIS OBJECT IS DEPRECATED *********

                   This counter is incremented by one for each
                   CarrierEvent on any port with ActivityDuration
                   less than ShortEventMaxTime.  ShortEventMaxTime is
                   greater than 74 bit times and less than 82 bit
                   times.  ShortEventMaxTime has tolerances included
                   to provide for circuit losses between a
                   conformance test point at the AUI and the
                   measurement point within the state machine.  This
                   counter is the summation of the values of the
                   rptrMonitorPortShortEvents counter for all of the
                   ports in this repeater."
           REFERENCE
                   "RFC 1516 rptrMonitorPortShortEvents and IEEE 802.3
                   Rptr Mgt, 19.2.6.2, aShortEvents."
           ::= { hpRptrMonCounters 6 }

       hpRptrMonGlobalRunts OBJECT-TYPE
           SYNTAX     Counter32
           MAX-ACCESS read-only
           STATUS     deprecated
           DESCRIPTION
                   "********* THIS OBJECT IS DEPRECATED *********

                   This counter is incremented by one for each
                   CarrierEvent on any port that meets one of the
                   following two conditions.  Only one test need be
                   made.  a) The ActivityDuration is greater than
                   ShortEventMaxTime and less than ValidPacketMinTime
                   and the CollisionEvent signal is deasserted.  b)
                   The OctetCount is less than 64, the
                   ActivityDuration is greater than ShortEventMaxTime
                   and the CollisionEvent signal is deasserted.
                   ValidPacketMinTime is greater than or equal to 552
                   bit times but less than 565 bit times.

                   An event whose length is greater than 74 bit times
                   but less than 82 bit times shall increment either
                   the hpRptrMonGlobalShortEvents counter or the
                   hpRptrMonGlobalRunts counter but not both.  A
                   CarrierEvent greater than or equal to 552 bit
                   times but less than 565 bit times may or may not
                   increment the hpRptrMonGlobalRunts counter.
                   ValidPacketMinTime has tolerances included to
                   provide for circuit losses between a conformance
                   test point at the AUI and the measurement point
                   within the state machine.

                   Runts usually indicate collision fragments, a
                   normal network event.  This counter is the
                   summation of the values of the
                   rptrMonitorPortRunts counter for all of the ports
                   in this repeater."
           REFERENCE
                   "RFC 1516 rptrMonitorPortRunts and IEEE 802.3 Rptr
                   Mgt, 19.2.6.2, aRunts."
           ::= { hpRptrMonCounters 7 }

       hpRptrMonGlobalCollisions OBJECT-TYPE
           SYNTAX     Counter32
           MAX-ACCESS read-only
           STATUS     deprecated
           DESCRIPTION
                   "********* THIS OBJECT IS DEPRECATED *********

                   This counter is incremented by one for any
                   CarrierEvent signal on any port for which the
                   CollisionEvent signal on any port is asserted.

                   This counter differs from
                   rptrMonitorTransmitCollisions in that it counts
                   all collisions seen by this repeater, even those
                   involving only a single port on this repeater,
                   whereas rptrMonitorTransmitCollisions counts only
                   collisions involving multiple ports on this
                   repeater."
           REFERENCE
                   "RFC 1516 rptrMonitorPortCollisions and IEEE 802.3
                   Rptr Mgt, 19.2.6.2, aCollisions."
           ::= { hpRptrMonCounters 8 }

       hpRptrMonGlobalLateEvents OBJECT-TYPE
           SYNTAX     Counter32
           MAX-ACCESS read-only
           STATUS     deprecated
           DESCRIPTION
                   "********* THIS OBJECT IS DEPRECATED *********

                   This counter is incremented by one for each
                   CarrierEvent on any port in which the CollIn(X)
                   variable transitions to the value SQE (Ref:
                   9.6.6.2, IEEE 802.3 Std) while the
                   ActivityDuration is greater than the
                   LateEventThreshold.  Such a CarrierEvent is
                   counted twice, as both hpRptrMonGlobalCollisions
                   and hpRptrMonGlobalLateEvents.  The
                   LateEventThreshold is greater than 480 bit times
                   and less than 565 bit times.  LateEventThreshold
                   has tolerances included to permit an
                   implementation to build a single threshold to
                   serve as both the LateEventThreshold and
                   ValidPacketMinTime threshold.  This counter is the
                   summation of the values of the
                   rptrMonitorPortLateEvents counter for all of the
                   ports in this repeater."
           REFERENCE
                   "RFC 1516 rptrMonitorPortLateEvents and IEEE 802.3
                   Rptr Mgt, 19.2.6.2, aLateEvents."
           ::= { hpRptrMonCounters 9 }

       hpRptrMonGlobalVeryLongEvents OBJECT-TYPE
           SYNTAX     Counter32
           MAX-ACCESS read-only
           STATUS     deprecated
           DESCRIPTION
                   "********* THIS OBJECT IS DEPRECATED *********

                   This counter is incremented by one for each
                   CarrierEvent on any port whose ActivityDuration is
                   greater than the MAU Jabber Lockup Protection
                   timer TW3 (Ref: 9.6.1 & 9.6.5, IEEE 802.3 Std).
                   Other counters may be incremented as appropriate.
                   This counter is the summation of the values of the
                   rptrMonitorPortVeryLongEvents counter for all of
                   the ports in this repeater."
           REFERENCE
                   "RFC 1516 rptrMonitorPortVeryLongEvents and IEEE
                   802.3 Rptr Mgt, 19.2.6.2, aVeryLongEvents."
           ::= { hpRptrMonCounters 10 }

       hpRptrMonGlobalDataRateMismatches OBJECT-TYPE
           SYNTAX     Counter32
           MAX-ACCESS read-only
           STATUS     deprecated
           DESCRIPTION
                   "********* THIS OBJECT IS DEPRECATED *********

                   This counter is incremented by one for each frame
                   received on any port that meets all of the
                   following conditions:  a) The CollisionEvent
                   signal is not asserted.  b) The ActivityDuration
                   is greater than ValidPacketMinTime.  c) The
                   frequency (data rate) is detectably mismatched
                   from the local transmit frequency.  The exact
                   degree of mismatch is vendor specific and is to be
                   defined by the vendor for conformance testing.
                   When this event occurs, other counters whose
                   increment conditions were satisfied may or may not
                   also be incremented.  This counter is the
                   summation of the values of the
                   rptrMonitorPortDatRateMismatches counter for all
                   of the ports in this repeater."
           REFERENCE
                   "RFC 1516 rptrMonitorPortDataRateMismatches and IEEE
                   802.3 Rptr Mgt, 19.2.6.2, aDataRateMismatches."
           ::= { hpRptrMonCounters 11 }

       hpRptrMonGlobalAutoPartitions OBJECT-TYPE
           SYNTAX     Counter32
           MAX-ACCESS read-only
           STATUS     deprecated
           DESCRIPTION
                   "********* THIS OBJECT IS DEPRECATED *********

                   This counter is incremented by one for each time
                   the repeater has automatically partitioned any
                   port.  The conditions that cause port partitioning
                   are specified in the partition state machine in
                   Section 9 of the IEEE 802.3 Std.  This counter is
                   the summation of the values of the
                   rptrMonitorPortAutoPartitions for all of the ports
                   in this repeater."
           REFERENCE
                   "RFC 1516 rptrMonitorPortAutoPartitions and IEEE
                   802.3 Rptr Mgt, 19.2.6.2, aAutoPartitions."
           ::= { hpRptrMonCounters 12 }

       hpRptrMonGlobalErrors OBJECT-TYPE
           SYNTAX     Counter32
           MAX-ACCESS read-only
           STATUS     deprecated
           DESCRIPTION
                   "********* THIS OBJECT IS DEPRECATED *********

                   The total number of errors which have occured
                   on any port in this repeater.  This counter is
                   the summation of the values of other error
                   counters, namely:

                       hpRptrMonGlobalFCSErrors,
                       hpRptrMonGlobalAlignmentErrors,
                       hpRptrMonGlobalFrameTooLongs,
                       hpRptrMonGlobalShortEvents,
                       hpRptrMonGlobalLateEvents,
                       hpRptrMonGlobalVeryLongEvents, and
                       hpRptrMonGlobalDataRateMismatches.

                   Equivalently, this counter is the summation of
                   the values of the rptrMonitorPortTotalErrors
                   counter for all of the ports in this repeater, or
                   it is the summation of the values of
                   rptrMonitorGroupTotalErrors for all of the port
                   groups in this repeater."
           REFERENCE
                   "RFC 1516, rptrMonitorGroupTotalErrors and
                   hpRptrMonitorPortTotalErrors."
           ::= { hpRptrMonCounters 13 }

       hpRptrMonGlobalUcastPackets OBJECT-TYPE
           SYNTAX     Counter32
           MAX-ACCESS read-only
           STATUS     deprecated
           DESCRIPTION
                   "********* THIS OBJECT IS DEPRECATED *********

                   This counter is incremented by one for each
                   unicast packet of valid frame length received on
                   any port.  This counter is the summation of
                   hpRptrMonPortUcastPackets for all of the ports
                   in this repeater.  This counter may not be
                   implemented for repeaters which do not have a
                   local network management agent."
           ::= { hpRptrMonCounters 14 }

       hpRptrMonGlobalBcastPackets OBJECT-TYPE
           SYNTAX     Counter32
           MAX-ACCESS read-only
           STATUS     deprecated
           DESCRIPTION
                   "********* THIS OBJECT IS DEPRECATED *********

                   This counter is incremented by one for each
                   broadcast packet of valid frame length received on
                   any port.  This counter is the summation of
                   hpRptrMonPortBcastPackets for all of the ports
                   in this repeater.  This counter may not be
                   implemented for repeaters which do not have a
                   local network management agent."
           ::= { hpRptrMonCounters 15 }

       hpRptrMonGlobalMcastPackets OBJECT-TYPE
           SYNTAX     Counter32
           MAX-ACCESS read-only
           STATUS     deprecated
           DESCRIPTION
                   "********* THIS OBJECT IS DEPRECATED *********

                   This counter is incremented by one for each
                   multicast packet of valid frame length received on
                   any port.  This counter is the summation of
                   hpRptrMonPortMcastPackets for all of the ports in
                   this repeater.  This counter may not be
                   implemented for repeaters which do not have a
                   local network management agent."
           ::= { hpRptrMonCounters 16 }

       hpRptrMonitorGroup
           OBJECT IDENTIFIER ::= { hpRptrMonitor 2 } -- unused

       hpRptrMonitorPort
           OBJECT IDENTIFIER ::= { hpRptrMonitor 3 }

       hpRptrMonPtTable OBJECT-TYPE
           SYNTAX     SEQUENCE OF HpRptrMonPtEntry
           MAX-ACCESS not-accessible
           STATUS     current
           DESCRIPTION
                   "Table of HP specific per port monitor objects."
           ::= { hpRptrMonitorPort 1 }

       hpRptrMonPtEntry OBJECT-TYPE
           SYNTAX     HpRptrMonPtEntry
           MAX-ACCESS not-accessible
           STATUS     current
           DESCRIPTION
                   "An entry in the table, containing per port
                   objects for a single port."
           INDEX     { hpRptrMonPtGroupIndex, hpRptrMonPtPortIndex }
           ::= { hpRptrMonPtTable 1 }

       HpRptrMonPtEntry ::=
           SEQUENCE {
               hpRptrMonPtGroupIndex           Integer32,
               hpRptrMonPtPortIndex            Integer32,
               hpRptrMonPtUcastPackets         Counter32,
               hpRptrMonPtBcastPackets         Counter32,
               hpRptrMonPtMcastPackets         Counter32
           }

       hpRptrMonPtGroupIndex OBJECT-TYPE
           SYNTAX     Integer32 (1..2147483647)
           MAX-ACCESS read-only
           STATUS     current
           DESCRIPTION
                   "The group containing the port for which this
                   entry contains information.  This object has the
                   same value as the corresponding instance of
                   rptrMonitorPortGroupIndex."
           ::= { hpRptrMonPtEntry 1 }

       hpRptrMonPtPortIndex OBJECT-TYPE
           SYNTAX     Integer32 (1..2147483647)
           MAX-ACCESS read-only
           STATUS     current
           DESCRIPTION
                   "The port within the group for which this entry
                   contains information.  This object has the same
                   value as the corresponding instance of
                   rptrMonitorPortIndex."
           ::= { hpRptrMonPtEntry 2 }

       hpRptrMonPtUcastPackets OBJECT-TYPE
           SYNTAX     Counter32
           MAX-ACCESS read-only
           STATUS     current
           DESCRIPTION
                   "This counter is incremented by one for each
                   unicast packet of valid frame length received on
                   this port.  This object may not be implemented for
                   repeaters which do not have a local network
                   management agent."
           ::= { hpRptrMonPtEntry 3 }

       hpRptrMonPtBcastPackets OBJECT-TYPE
           SYNTAX     Counter32
           MAX-ACCESS read-only
           STATUS     current
           DESCRIPTION
                   "This counter is incremented by one for each
                   broadcast packet of valid frame length received on
                   this port.  This object may not be implemented for
                   repeaters which do not have a local network
                   management agent."
           ::= { hpRptrMonPtEntry 4 }

       hpRptrMonPtMcastPackets OBJECT-TYPE
           SYNTAX     Counter32
           MAX-ACCESS read-only
           STATUS     current
           DESCRIPTION
                   "This counter is incremented by one for each
                   multicast packet of valid frame length received on
                   this port.  This object may not be implemented for
                   repeaters which do not have a local network
                   management agent."
           ::= { hpRptrMonPtEntry 5 }


       hpRpMauGroup   OBJECT IDENTIFIER ::= { hpicfRepeater 4 }

       hpRpMauTable OBJECT-TYPE
           SYNTAX     SEQUENCE OF HpRpMauEntry
           MAX-ACCESS not-accessible
           STATUS     current
           DESCRIPTION
                   "HP extensions to the rpMauTable."
           ::= { hpRpMauGroup 1 }

       hpRpMauEntry OBJECT-TYPE
           SYNTAX     HpRpMauEntry
           MAX-ACCESS not-accessible
           STATUS     current
           DESCRIPTION
                   "An entry in the table, containing HP extensions
                   for a single MAU."
           INDEX      { rpMauGroupIndex, rpMauPortIndex, rpMauIndex }
           ::= { hpRpMauTable 1 }

       HpRpMauEntry ::=
           SEQUENCE {
               hpRpMauTypeList                 BITS,
               hpRpMauAutoNegSupported         TruthValue,
               hpRpMauAutoNegAdminStatus       INTEGER,
               hpRpMauAutoNegRemoteSignaling   INTEGER,
               hpRpMauAutoNegConfig            INTEGER,
               hpRpMauAutoNegCapReceived       BITS,
               hpRpMauAutoNegRestart           INTEGER
           }

       hpRpMauTypeList OBJECT-TYPE
           SYNTAX      BITS {
               bOther(0),         -- other or unknown
               bAUI(1),           -- AUI
               b10base5(2),       -- 10BASE-5
               bFoirl(3),         -- FOIRL

               b10base2(4),       -- 10BASE-2
               b10baseT(5),       -- 10BASE-T duplex mode unknown
               b10baseFP(6),      -- 10BASE-FP
               b10baseFB(7),      -- 10BASE-FB
               b10baseFL(8),      -- 10BASE-FL duplex mode unknown
               b10broad36(9),     -- 10BROAD36
               b10baseTHD(10),    -- 10BASE-T  half duplex mode
               b10baseTFD(11),    -- 10BASE-T  full duplex mode
               b10baseFLHD(12),   -- 10BASE-FL half duplex mode
               b10baseFLFD(13),   -- 10BASE-FL full duplex mode

               b100baseT4(14),    -- 100BASE-T4
               b100baseTXHD(15),  -- 100BASE-TX half duplex mode
               b100baseTXFD(16),  -- 100BASE-TX full duplex mode
               b100baseFXHD(17),  -- 100BASE-FX half duplex mode
               b100baseFXFD(18),  -- 100BASE-FX full duplex mode
               b100baseT2HD(19),  -- 100BASE-T2 half duplex mode
               b100baseT2FD(20)   -- 100BASE-T2 full duplex mode
           }
           MAX-ACCESS read-only
           STATUS     current
           DESCRIPTION
                   "A value that uniquely identifies the set of
                   possible IEEE 802.3 types that the MAU could be.  If
                   auto-negotiation is present on this MAU, this object
                   will map to hpRpMauAutoNegCapability.

                   Note that a repeater can never actually support the
                   full-duplex MAU types.  The bits for them are
                   retained to keep the bit values consistent with
                   ifMauTypeListBits."
           ::= { hpRpMauEntry 1 }

       hpRpMauAutoNegSupported OBJECT-TYPE
           SYNTAX     TruthValue
           MAX-ACCESS read-only
           STATUS     current
           DESCRIPTION
                   "This object indicates whether or not
                   auto-negotiation is supported on this MAU."
           ::= { hpRpMauEntry 2 }

       hpRpMauAutoNegAdminStatus OBJECT-TYPE
           SYNTAX     INTEGER {
                          autoNegotiate(1),
                          forceTo100TXHD(2),
                          forceTo10THD(3)
                      }
           MAX-ACCESS read-write
           STATUS     current
           DESCRIPTION
                   "Setting this object to autoNegotiate(1) will cause
                   auto-negotiation to be enabled on this port.

                   Setting this object to forceTo100TXHD will cause
                   auto-negotiation to be disabled on this port, and
                   cause the operational type of the MAU on this port
                   (as reported by rpMauType) to transition to
                   dot3MauType100BaseTXHD.

                   Setting this object to forceTo10THD will cause
                   auto-negotiation to be disabled on this port, and
                   cause the operational type of the MAU on this port
                   (as reported by rpMauType) to transition to
                   dot3MauType10BaseTHD."
           ::= { hpRpMauEntry 3 }

       hpRpMauAutoNegRemoteSignaling OBJECT-TYPE
           SYNTAX     INTEGER {
                          detected(1),
                          notdetected(2)
                      }
           MAX-ACCESS read-only
           STATUS     current
           DESCRIPTION
                   "A value indicating whether the remote end of the
                   link is using auto-negotiation signaling. It takes
                   the value detected(1) if and only if, during the
                   previous link negotiation, FLP Bursts were received."
           REFERENCE  "[IEEE 802.3 Mgt], 30.6.1.1.3,
                      aAutoNegRemoteSignaling."
           ::= { hpRpMauEntry 4 }

       hpRpMauAutoNegConfig OBJECT-TYPE
           SYNTAX     INTEGER {
                          other(1),
                          configuring(2),
                          complete(3),
                          disabled(4),
                          parallelDetectFail(5)
                      }
           MAX-ACCESS read-only
           STATUS     current
           DESCRIPTION
                   "A value indicating the current status of the
                   auto-negotiation process.  The enumeration
                   parallelDetectFail(5) maps to a failure in parallel
                   detection as defined in 28.2.3.1 of
                   [IEEE 802.3 Std]."
           REFERENCE  "[IEEE 802.3 Mgt], 30.6.1.1.4,
                      aAutoNegAutoConfig."
           ::= { hpRpMauEntry 5 }

       hpRpMauAutoNegCapReceived OBJECT-TYPE
           SYNTAX     BITS {
                bOther(0),        -- other or unknown
                b10baseT(1),      -- 10BASE-T  half duplex mode
                b10baseTFD(2),    -- 10BASE-T  full duplex mode
                b100baseT4(3),    -- 100BASE-T4
                b100baseTX(4),    -- 100BASE-TX half duplex mode
                b100baseTXFD(5),  -- 100BASE-TX full duplex mode
                b100baseT2(6),    -- 100BASE-T2 half duplex mode
                b100baseT2FD(7)   -- 100BASE-T2 full duplex mode
           }
           MAX-ACCESS read-only
           STATUS     current
           DESCRIPTION
                   "A value that uniquely identifies the set of
                   capabilities received from the remote
                   auto-negotiation entity.

                   Note that ports that support this MIB may be
                   attached to remote auto-negotiation entities which
                   have capabilities beyond the scope of this MIB."
           REFERENCE  "[IEEE 802.3 Mgt], 30.6.1.1.7,
                      aAutoNegReceivedTechnologyAbility."
           ::= { hpRpMauEntry 6 }

       hpRpMauAutoNegRestart OBJECT-TYPE
           SYNTAX     INTEGER {
                          restart(1),
                          norestart(2)
                      }
           MAX-ACCESS read-write
           STATUS     current
           DESCRIPTION
                   "If the value of this object is set to restart(1)
                   then this will force auto-negotiation to begin link
                   renegotiation. If auto-negotiation signaling is
                   disabled, a write to this object has no effect.

                   Setting the value of this object to norestart(2) has
                   no effect."
           REFERENCE  "[IEEE 802.3 Mgt], 30.6.1.2.1,
                      acAutoNegRestartAutoConfig."
           ::= { hpRpMauEntry 7 }



       -- 802.3 Repeater Specific Traps


       hpicfLinkBeatTrap NOTIFICATION-TYPE
           OBJECTS    { rpMauMediaAvailable }
           STATUS     deprecated
           DESCRIPTION
                   "********* THIS NOTIFICATION IS DEPRECATED *********

                   A hpicfLinkBeatTrap is device type specific to ICF
                   hubs.  It signifies that the hub hardware has
                   detected a change of state in a port's link beat
                   status. The current value of the port's link beat
                   status is returned in the PDU.

                   This trap has been deprecated.  It is replaced by the
                   hpicfMediaAvailDetectTrap and the
                   hpicfMediaAvailLostTrap."
           ::=  { hpicf8023RptrTrapsPrefix 1 }

       hpicfPartitionTrap NOTIFICATION-TYPE
           OBJECTS    { rptrPortAutoPartitionState }
           STATUS     deprecated
           DESCRIPTION
                   "********* THIS NOTIFICATION IS DEPRECATED *********

                   A hpicfPartitionTrap is device type specific to ICF
                   hubs.  It signifies that the hub hardware has
                   detected a change of state in a port's partition
                   status.  The current value of the port's partition
                   status is returned in the PDU.

                   This trap has been deprecated.  It is replaced by the
                   hpicfPortPartitionTrap and the hpicfPortHealTrap."
           ::= { hpicf8023RptrTrapsPrefix 2 }

       hpicfMediaAvailDetectTrap NOTIFICATION-TYPE
           OBJECTS    { rpMauMediaAvailable }
           STATUS     current
           DESCRIPTION
                   "A hpicfMediaAvailDetectTraps is device type specific
                   to ICF hubs.  It signifies that the hub hardware has
                   detected an instance of rpMauMediaAvailable for one
                   of the repeater's ports has entered the 'available'
                   state from some other state.  Note that this trap is
                   only generated for instances of rpMauMediaAvailable
                   associated with MAUs attached to repeater ports for
                   which the corresponding instance of the
                   hpRptrPtMediaAvailTrapEnable object is equal to
                   'true'.

                   The previous value of the instance of the
                   rpMauMediaAvailable object that entered the 'active'
                   state is returned in the PDU."
           ::= { hpicf8023RptrTrapsPrefix 3 }

       hpicfMediaAvailLostTrap NOTIFICATION-TYPE
           OBJECTS    { rpMauMediaAvailable }
           STATUS     current
           DESCRIPTION
                   "A hpicfMediaAvailLostTraps is device type specific
                   to ICF hubs.  It signifies that the hub hardware has
                   detected an instance of rpMauMediaAvailable for one
                   of the repeater's ports that had been in the
                   'available' state has exited that state.  Note that
                   this trap is only generated for instances of
                   rpMauMediaAvailable associated with MAUs attached to
                   repeater ports for which the corresponding instance
                   of the hpRptrPtMediaAvailTrapEnable object is equal
                   to 'true'.

                   The new value of the instance of the
                   rpMauMediaAvailable object that exited the 'active'
                   state is returned in the PDU."
           ::= { hpicf8023RptrTrapsPrefix 4 }

       hpicfPortPartitionTrap NOTIFICATION-TYPE
           OBJECTS    { rptrPortAutoPartitionState }
           STATUS     current
           DESCRIPTION
                   "A hpicfPortPartitionTrap is device type specific
                   to ICF hubs.  It signifies that the hub hardware has
                   detected that an instance of
                   rptrPortAutoPartitionState for one of the repeater's
                   ports has changed from the 'notAutoPartitioned' state
                   to the 'autoPartitioned' state.  The current value of
                   the instance of the rptrPortAutoPartitionState for
                   the port that auto-partitioned is returned in the
                   PDU."
           ::= { hpicf8023RptrTrapsPrefix 5 }

       hpicfPortHealTrap NOTIFICATION-TYPE
           OBJECTS    { rptrPortAutoPartitionState }
           STATUS     current
           DESCRIPTION
                   "A hpicfPortHealTrap is device type specific to ICF
                   hubs.  It signifies that the hub hardware has
                   detected that an instance of
                   rptrPortAutoPartitionState for one of the repeater's
                   ports has changed from the 'autoPartitioned' state
                   to the 'notAutoPartitioned' state.  The current value
                   of the instance of the rptrPortAutoPartitionState for
                   the port that healed is returned in the PDU."
           ::= { hpicf8023RptrTrapsPrefix 6 }


       -- Conformance information

       hpicf8023RptrConformance
           OBJECT IDENTIFIER ::= { hpicf8023RptrMib 1 }

       hpicf8023RptrCompliances
           OBJECT IDENTIFIER ::= { hpicf8023RptrConformance 1 }
       hpicf8023RptrGroups
           OBJECT IDENTIFIER ::= { hpicf8023RptrConformance 2 }


       -- Compliance statements

       hpicf8023RptrCompliance MODULE-COMPLIANCE
           STATUS     deprecated
           DESCRIPTION
                   "********* THIS COMPLIANCE IS DEPRECATED *********

                   The compliance statement for HP extensions to the
                   802.3 Repeater MIB for HP AdvanceStack 802.3
                   repeaters."
           MODULE
               MANDATORY-GROUPS { hpicf8023RptrBasicGroup,
                                  hpicf8023RptrMonitorGroup,
                                  hpicf8023RptrNotifyGroup }

       ::= { hpicf8023RptrCompliances 1 }

       hpicf8023RptrSlaveCompliance MODULE-COMPLIANCE
           STATUS     deprecated
           DESCRIPTION
                   "********* THIS COMPLIANCE IS DEPRECATED *********

                   The compliance statement for HP extensions to the
                   802.3 Repeater MIB for HP AdvanceStack 802.3
                   slave repeaters."
           MODULE
               MANDATORY-GROUPS { hpicf8023RptrBasicSlaveGroup,
                                  hpicf8023RptrMonitorSlaveGroup,
                                  hpicf8023RptrNotifyGroup }

       ::= { hpicf8023RptrCompliances 2 }

       hpicf8023MultiRptrCompliance MODULE-COMPLIANCE
           STATUS     current
           DESCRIPTION
                   "The compliance statement for HP extensions to the
                   802.3 Repeater MIB for HP AdvanceStack 802.3
                   repeaters.  This compliance supports devices
                   with multiple repeater segments, as well as
                   devices with a single repeater segment."
           MODULE
               MANDATORY-GROUPS { hpicf8023MultiRptrBasicGroup,
                                  hpicf8023MultiRptrMonitorGroup,
                                  hpicf8023MultiRptrNotifyGroup }

       ::= { hpicf8023RptrCompliances 3 }

       hpicf8023RptrAutoNegCompliance MODULE-COMPLIANCE
           STATUS     current
           DESCRIPTION
                   "The compliance statement for HP extensions to the
                   802.3 Repeater MIB for HP AdvanceStack 802.3
                   repeaters.  This compliance supports devices
                   with multiple repeater segments, as well as
                   devices with a single repeater segment.  It also
                   supports repeater devices with auto-negotiation."
           MODULE
               MANDATORY-GROUPS { hpicf8023MultiRptrBasicGroup,
                                  hpicf8023MultiRptrMonitorGroup,
                                  hpicf8023MultiRptrNotifyGroup }

               GROUP       hpicf8023RpMauAutoNegGroup
               DESCRIPTION "Implementation of this group is required for
                           MAUs that support auto-negotiation."

       ::= { hpicf8023RptrCompliances 4 }


       -- Units of conformance

       hpicf8023RptrBasicGroup OBJECT-GROUP
           OBJECTS    { hpRptrEntityName,
                        hpRptrThinlanFault,
                        hpRptrSqeEnabled,
                        hpRptrRobustHealing,
                        hpRptrGrpGroupIndex,
                        hpRptrGrpPortsAdminStatus,
                        hpRptrGrpPortsSegStatus,
                        hpRptrGrpPortsMediaAvailable,
                        hpRptrGrpPortsLinkbeatEnabled,
                        hpRptrGrpPortsOperStatus,
                        hpRptrPtGroupIndex,
                        hpRptrPtPortIndex,
                        hpRptrPtLinkbeatEnable,
                        hpRptrPtPolarityReversed
                      }
           STATUS     deprecated
           DESCRIPTION
                   "********* THIS GROUP IS DEPRECATED *********

                   A collection of HP specific extensions to the
                   802.3 Repeater MIB for the HP AdvanceStack product
                   line."
           ::= { hpicf8023RptrGroups 1 }

       hpicf8023RptrBasicSlaveGroup OBJECT-GROUP
           OBJECTS    { hpRptrEntityName,
                        hpRptrThinlanFault,
                        hpRptrSqeEnabled,
                        hpRptrGrpGroupIndex,
                        hpRptrGrpPortsAdminStatus,
                        hpRptrGrpPortsSegStatus,
                        hpRptrGrpPortsMediaAvailable,
                        hpRptrGrpPortsLinkbeatEnabled,
                        hpRptrGrpPortsOperStatus,
                        hpRptrPtGroupIndex,
                        hpRptrPtPortIndex,
                        hpRptrPtLinkbeatEnable,
                        hpRptrPtPolarityReversed
                      }
           STATUS     deprecated
           DESCRIPTION
                   "********* THIS GROUP IS DEPRECATED *********

                   A collection of HP specific extensions to the
                   802.3 Repeater MIB for HP AdvanceStack slaves."
           ::= { hpicf8023RptrGroups 2 }

       hpicf8023RptrMonitorGroup OBJECT-GROUP
           OBJECTS    { hpRptrMonGlobalFrames,
                        hpRptrMonGlobalOctets,
                        hpRptrMonGlobalFCSErrors,
                        hpRptrMonGlobalAlignmentErrors,
                        hpRptrMonGlobalFrameTooLongs,
                        hpRptrMonGlobalShortEvents,
                        hpRptrMonGlobalRunts,
                        hpRptrMonGlobalCollisions,
                        hpRptrMonGlobalLateEvents,
                        hpRptrMonGlobalVeryLongEvents,
                        hpRptrMonGlobalDataRateMismatches,
                        hpRptrMonGlobalAutoPartitions,
                        hpRptrMonGlobalErrors,
                        hpRptrMonGlobalUcastPackets,
                        hpRptrMonGlobalBcastPackets,
                        hpRptrMonGlobalMcastPackets,
                        hpRptrMonPtGroupIndex,
                        hpRptrMonPtPortIndex,
                        hpRptrMonPtUcastPackets,
                        hpRptrMonPtBcastPackets,
                        hpRptrMonPtMcastPackets
                      }
           STATUS     deprecated
           DESCRIPTION
                   "********* THIS GROUP IS DEPRECATED *********

                   A collection of extended counters for 802.3
                   repeaters in the HP AdvanceStack product line."
           ::= { hpicf8023RptrGroups 3 }

       hpicf8023RptrMonitorSlaveGroup OBJECT-GROUP
           OBJECTS    { hpRptrMonGlobalFrames,
                        hpRptrMonGlobalOctets,
                        hpRptrMonGlobalFCSErrors,
                        hpRptrMonGlobalAlignmentErrors,
                        hpRptrMonGlobalFrameTooLongs,
                        hpRptrMonGlobalShortEvents,
                        hpRptrMonGlobalRunts,
                        hpRptrMonGlobalCollisions,
                        hpRptrMonGlobalLateEvents,
                        hpRptrMonGlobalVeryLongEvents,
                        hpRptrMonGlobalDataRateMismatches,
                        hpRptrMonGlobalAutoPartitions,
                        hpRptrMonGlobalErrors
                      }
           STATUS     deprecated
           DESCRIPTION
                   "********* THIS GROUP IS DEPRECATED *********

                   A collection of extended counters for HP
                   AdvanceStack 802.3 slave repeaters."
           ::= { hpicf8023RptrGroups 4 }

       hpicf8023MultiRptrBasicGroup OBJECT-GROUP
           OBJECTS    { hpRptrPtGroupIndex,
                        hpRptrPtPortIndex,
                        hpRptrPtLinkbeatEnable,
                        hpRptrPtPolarityReversed,
                        hpRptrPtSqeEnabled,
                        hpRptrPtMediaAvailTrapEnable,
                        hpRptrPtLongCableEnable
                      }
           STATUS     current
           DESCRIPTION
                   "A collection of HP specific extensions to the
                   802.3 Repeater MIB for products in the HP
                   AdvanceStack product line.  This group supports
                   devices with multiple repeater segments as well
                   as devices with a single repeater segment."
           ::= { hpicf8023RptrGroups 5 }

       hpicf8023MultiRptrMonitorGroup OBJECT-GROUP
           OBJECTS    { hpRptrMonPtGroupIndex,
                        hpRptrMonPtPortIndex,
                        hpRptrMonPtUcastPackets,
                        hpRptrMonPtBcastPackets,
                        hpRptrMonPtMcastPackets
                      }
           STATUS     current
           DESCRIPTION
                   "A collection of extended counters for 802.3
                   repeaters in the HP AdvanceStack product line.
                   This group supports devices with multiple
                   repeater segments as well as devices with a
                   single repeater segment."
           ::= { hpicf8023RptrGroups 6 }

       hpicf8023RptrNotifyGroup NOTIFICATION-GROUP
           NOTIFICATIONS { hpicfLinkBeatTrap,
                           hpicfPartitionTrap
                         }
           STATUS     deprecated
           DESCRIPTION
                   "********* THIS GROUP IS DEPRECATED *********

                   A collection of notifications used to indicate
                   changes in port status for 802.3 repeaters in the
                   HP AdvanceStack product line."
           ::= { hpicf8023RptrGroups 7 }

       hpicf8023MultiRptrNotifyGroup NOTIFICATION-GROUP
           NOTIFICATIONS { hpicfMediaAvailDetectTrap,
                           hpicfMediaAvailLostTrap,
                           hpicfPortPartitionTrap,
                           hpicfPortHealTrap
                         }
           STATUS     current
           DESCRIPTION
                   "A collection of notifications used to indicate
                   changes in port status for 802.3 repeaters in the
                   HP AdvanceStack product line.  Notifications in
                   this group use different traps for good->bad than
                   are used for bad->good (similar to linkUp/linkDown)."
           ::= { hpicf8023RptrGroups 8 }

       hpicf8023RpMauAutoNegGroup OBJECT-GROUP
           OBJECTS    { hpRpMauTypeList,
                        hpRpMauAutoNegSupported,
                        hpRpMauAutoNegAdminStatus,
                        hpRpMauAutoNegRemoteSignaling,
                        hpRpMauAutoNegConfig,
                        hpRpMauAutoNegCapReceived,
                        hpRpMauAutoNegRestart
                      }
           STATUS     current
           DESCRIPTION
                   "A collection of objects for managing MAUs attached
                   to repeater ports with managed auto-negotiation."
           ::= { hpicf8023RptrGroups 9 }

       hpicf8023Rptr100BasicGroup OBJECT-GROUP
           OBJECTS    { hpRptrPtGroupIndex,
                        hpRptrPtPortIndex,
                        hpRptrPtPolarityReversed,
                        hpRptrPtMediaAvailTrapEnable
                      }
           STATUS     current
           DESCRIPTION
                   "A collection of HP specific extensions to the
                   802.3 Repeater MIB for products in the HP
                   AdvanceStack product line.  This group supports
                   devices with multiple repeater segments as well
                   as devices with a single repeater segment.  This
                   group supports devices with 100BaseT repeater
                   segments."
           ::= { hpicf8023RptrGroups 10 }

       END
