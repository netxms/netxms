MOSTCOM-MIB DEFINITIONS ::= BEGIN


-- This file describes the MIB supported by the
-- Mostcom Communications devices
-- Recommended application : SNMPc V7.0
--
-- Current MIB Version : 1.00
-- Targer firmware : ????????????
--
-- revision history:
--
-- 2014/05/21 1.00	Created - M1-xGE FSO Artolink.
--


IMPORTS
	experimental,
        enterprises, IpAddress, TimeTicks, Counter32     	FROM SNMPv2-SMI
        OBJECT-TYPE       FROM RFC-1212
        DisplayString     FROM RFC1213-MIB;


-- managed device root object ID

mostcom   		OBJECT IDENTIFIER ::= { enterprises 33691 }

-- tree structure
fsoTerminal   		OBJECT IDENTIFIER ::= { mostcom 2}
                
-- head group.  This is a table of heads

 Type OBJECT-TYPE
    	SYNTAX	DisplayString (SIZE (0..255))
	ACCESS	read-only
	STATUS	mandatory
	DESCRIPTION
	"FSO equipment type"
	::= { fsoTerminal 1}

 Status  OBJECT-TYPE
    	SYNTAX	DisplayString (SIZE (0..255))
	ACCESS	read-only
	STATUS	mandatory
	DESCRIPTION
	"FSO equipment status"
	::= { fsoTerminal 2}

 localOU OBJECT IDENTIFIER ::= { fsoTerminal 3 }
  LOU_SerialNumber	OBJECT-TYPE
    	SYNTAX	DisplayString (SIZE (0..255))
	ACCESS	read-only
	STATUS	mandatory
	DESCRIPTION
	"Local OU serial number"
	::= { localOU 1}
  LOU_License	OBJECT-TYPE
    	SYNTAX	DisplayString (SIZE (0..255))
	ACCESS	read-only
	STATUS	mandatory
	DESCRIPTION
	"Local OU license parameters"
	::= { localOU 2}
  LOU_Coordinates	OBJECT-TYPE
    	SYNTAX	DisplayString (SIZE (0..255))
	ACCESS	read-only
	STATUS	mandatory
	DESCRIPTION
	"OU installation geo coordinates"
	::= { localOU 3}
  LOU_Temperature	OBJECT-TYPE
    	SYNTAX	DisplayString (SIZE (0..255))
	ACCESS	read-only
	STATUS	mandatory
	DESCRIPTION
	"Local OU internal temperature"
	::= { localOU 4}
  louState OBJECT IDENTIFIER ::= { localOU 5 }
   LOU_InputFiber  OBJECT-TYPE
    	SYNTAX	DisplayString (SIZE (0..255))
	ACCESS	read-only
	STATUS	mandatory
	DESCRIPTION
	"OU input fiber connection status"
	::= { louState 1}
   LOU_Autotracking OBJECT-TYPE
    	SYNTAX	DisplayString (SIZE (0..255))
	ACCESS	read-only
	STATUS	mandatory
	DESCRIPTION
	"OU autotracking status"
	::= { louState 2}
   LOU_ServiceChannel OBJECT-TYPE
    	SYNTAX	DisplayString (SIZE (0..255))
	ACCESS	read-only
	STATUS	mandatory
	DESCRIPTION
	"OU service channel status"
	::= { louState 3}


 localIU OBJECT IDENTIFIER ::= { fsoTerminal 4 }
  LIU_FSOsignal OBJECT-TYPE
    	SYNTAX	DisplayString (SIZE (0..255))
	ACCESS	read-only
	STATUS	mandatory
	DESCRIPTION
	"Local IU input FSO signal from OU"
	::= { localIU 1}  
  liuIPconfig OBJECT IDENTIFIER ::= { localIU 2 }
   LIU_IPaddress  OBJECT-TYPE
    	SYNTAX	DisplayString (SIZE (0..255))
	ACCESS	read-only
	STATUS	mandatory
	DESCRIPTION
	"Local IU IP address"
	::= { liuIPconfig 1}
   LIU_NetMask  OBJECT-TYPE
    	SYNTAX	DisplayString (SIZE (0..255))
	ACCESS	read-only
	STATUS	mandatory
	DESCRIPTION
	"Local IU Network mask"
	::= { liuIPconfig 2}
   LIU_IPgw  OBJECT-TYPE
    	SYNTAX	DisplayString (SIZE (0..255))
	ACCESS	read-only
	STATUS	mandatory
	DESCRIPTION
	"Local IU gateway IP"
	::= { liuIPconfig 3}
   LIU_MACaddress  OBJECT-TYPE
    	SYNTAX	DisplayString (SIZE (0..255))
	ACCESS	read-only
	STATUS	mandatory
	DESCRIPTION
	"Local IU MAC address"
	::= { liuIPconfig 4}
   LIU_SNMPagent  OBJECT-TYPE
    	SYNTAX	DisplayString (SIZE (0..255))
	ACCESS	read-only
	STATUS	mandatory
	DESCRIPTION
	"Local IU SNMP agent IP"
	::= { liuIPconfig 5}
   LIU_Ports  OBJECT-TYPE
    	SYNTAX	DisplayString (SIZE (0..255))
	ACCESS	read-only
	STATUS	mandatory
	DESCRIPTION
	"Local IU telemetry ports"
	::= { liuIPconfig 6}

  liuBackup OBJECT IDENTIFIER ::= { localIU 3 }
   LIU_BckSwmode  OBJECT-TYPE
    	SYNTAX	DisplayString (SIZE (0..255))
	ACCESS	read-only
	STATUS	mandatory
	DESCRIPTION
	"Local IU backup switch mode"
	::= { liuBackup 1}
   LIU_BckMain  OBJECT-TYPE
    	SYNTAX	DisplayString (SIZE (0..255))
	ACCESS	read-only
	STATUS	mandatory
	DESCRIPTION
	"Local IU backup main channel"
	::= { liuBackup 2}
   LIU_BckChn  OBJECT-TYPE
    	SYNTAX	DisplayString (SIZE (0..255))
	ACCESS	read-only
	STATUS	mandatory
	DESCRIPTION
	"Local IU backup channel"
	::= { liuBackup 3}
   LIU_BckSwLevel  OBJECT-TYPE
    	SYNTAX	DisplayString (SIZE (0..255))
	ACCESS	read-only
	STATUS	mandatory
	DESCRIPTION
	"Local IU losses backup channel switch level"
	::= { liuBackup 4}
   LIU_BckFSOReturnTime  OBJECT-TYPE
    	SYNTAX	DisplayString (SIZE (0..255))
	ACCESS	read-only
	STATUS	mandatory
	DESCRIPTION
	"Local IU time for return to FSO from backup"
	::= { liuBackup 5}
   LIU_BckPOEConfig  OBJECT-TYPE
    	SYNTAX	DisplayString (SIZE (0..255))
	ACCESS	read-only
	STATUS	mandatory
	DESCRIPTION
	"Local IU PoE backup config"
	::= { liuBackup 6}
   LIU_BckALLF  OBJECT-TYPE
    	SYNTAX	DisplayString (SIZE (0..255))
	ACCESS	read-only
	STATUS	mandatory
	DESCRIPTION
	"Local IU PoE ALLFconfig"
	::= { liuBackup 7}
  
  liuChnStat OBJECT IDENTIFIER ::= { localIU 4 }
   liuFSOStat OBJECT IDENTIFIER ::= { liuChnStat 1 }
    LIU_FSOnoerr  OBJECT-TYPE
    	SYNTAX	DisplayString (SIZE (0..255))
	ACCESS	read-only
	STATUS	mandatory
	DESCRIPTION
	"Local IU FSO channel no errors received Mbytes"
	::= { liuFSOStat 1}
    LIU_FSOerr  OBJECT-TYPE
    	SYNTAX	DisplayString (SIZE (0..255))
	ACCESS	read-only
	STATUS	mandatory
	DESCRIPTION
	"Local IU FSO channel errored received Mbytes"
	::= { liuFSOStat 2}
    LIU_FSOsent OBJECT-TYPE
    	SYNTAX	DisplayString (SIZE (0..255))
	ACCESS	read-only
	STATUS	mandatory
	DESCRIPTION
	"Local IU FSO channel sent Mbytes"
	::= { liuFSOStat 3}
    LIU_FSOoutput OBJECT-TYPE
    	SYNTAX	DisplayString (SIZE (0..255))
	ACCESS	read-only
	STATUS	mandatory
	DESCRIPTION
	"Local IU FSO channel output data rate Mbyte/s"
	::= { liuFSOStat 4}
    LIU_FSOinput OBJECT-TYPE
    	SYNTAX	DisplayString (SIZE (0..255))
	ACCESS	read-only
	STATUS	mandatory
	DESCRIPTION
	"Local IU FSO channel input data rate Mbyte/s"
	::= { liuFSOStat 5}
    LIU_FSOinperr OBJECT-TYPE
    	SYNTAX	DisplayString (SIZE (0..255))
	ACCESS	read-only
	STATUS	mandatory
	DESCRIPTION
	"Local IU FSO channel input data error, %"
	::= { liuFSOStat 6}

   liuEth1Stat OBJECT IDENTIFIER ::= { liuChnStat 2 }
    LIU_Eth1noerr  OBJECT-TYPE
    	SYNTAX	DisplayString (SIZE (0..255))
	ACCESS	read-only
	STATUS	mandatory
	DESCRIPTION
	"Local IU ETHERNET1 channel no errors received Mbytes"
	::= { liuEth1Stat 1}
    LIU_Eth1err  OBJECT-TYPE
    	SYNTAX	DisplayString (SIZE (0..255))
	ACCESS	read-only
	STATUS	mandatory
	DESCRIPTION
	"Local IU ETHERNET1 channel errored received Mbytes"
	::= { liuEth1Stat 2}
    LIU_Eth1sent OBJECT-TYPE
    	SYNTAX	DisplayString (SIZE (0..255))
	ACCESS	read-only
	STATUS	mandatory
	DESCRIPTION
	"Local IU ETHERNET1 channel sent Mbytes"
	::= { liuEth1Stat 3}
    LIU_Eth1output OBJECT-TYPE
    	SYNTAX	DisplayString (SIZE (0..255))
	ACCESS	read-only
	STATUS	mandatory
	DESCRIPTION
	"Local IU ETHERNET1 channel output data rate Mbyte/s"
	::= { liuEth1Stat 4}
    LIU_Eth1input OBJECT-TYPE
    	SYNTAX	DisplayString (SIZE (0..255))
	ACCESS	read-only
	STATUS	mandatory
	DESCRIPTION
	"Local IU ETHERNET1 channel input data rate Mbyte/s"
	::= { liuEth1Stat 5}
    LIU_Eth1inperr OBJECT-TYPE
    	SYNTAX	DisplayString (SIZE (0..255))
	ACCESS	read-only
	STATUS	mandatory
	DESCRIPTION
	"Local IU ETHERNET1 channel input data error, %"
	::= { liuEth1Stat 6}

   liuEth2Stat OBJECT IDENTIFIER ::= { liuChnStat 3 }
    LIU_Eth2noerr  OBJECT-TYPE
    	SYNTAX	DisplayString (SIZE (0..255))
	ACCESS	read-only
	STATUS	mandatory
	DESCRIPTION
	"Local IU ETHERNET2 channel no errors received Mbytes"
	::= { liuEth2Stat 1}
    LIU_Eth2err  OBJECT-TYPE
    	SYNTAX	DisplayString (SIZE (0..255))
	ACCESS	read-only
	STATUS	mandatory
	DESCRIPTION
	"Local IU ETHERNET2 channel errored received Mbytes"
	::= { liuEth2Stat 2}
    LIU_Eth2sent OBJECT-TYPE
    	SYNTAX	DisplayString (SIZE (0..255))
	ACCESS	read-only
	STATUS	mandatory
	DESCRIPTION
	"Local IU ETHERNET2 channel sent Mbytes"
	::= { liuEth2Stat 3}
    LIU_Eth2output OBJECT-TYPE
    	SYNTAX	DisplayString (SIZE (0..255))
	ACCESS	read-only
	STATUS	mandatory
	DESCRIPTION
	"Local IU ETHERNET2 channel output data rate Mbyte/s"
	::= { liuEth2Stat 4}
    LIU_Eth2input OBJECT-TYPE
    	SYNTAX	DisplayString (SIZE (0..255))
	ACCESS	read-only
	STATUS	mandatory
	DESCRIPTION
	"Local IU ETHERNET2 channel input data rate Mbyte/s"
	::= { liuEth2Stat 5}
    LIU_Eth2inperr OBJECT-TYPE
    	SYNTAX	DisplayString (SIZE (0..255))
	ACCESS	read-only
	STATUS	mandatory
	DESCRIPTION
	"Local IU ETHERNET2 channel input data error, %"
	::= { liuEth2Stat 6}

   liuEth3Stat OBJECT IDENTIFIER ::= { liuChnStat 4 }
    LIU_Eth3noerr  OBJECT-TYPE
    	SYNTAX	DisplayString (SIZE (0..255))
	ACCESS	read-only
	STATUS	mandatory
	DESCRIPTION
	"Local IU ETHERNET3 channel no errors received Mbytes"
	::= { liuEth3Stat 1}
    LIU_Eth3err  OBJECT-TYPE
    	SYNTAX	DisplayString (SIZE (0..255))
	ACCESS	read-only
	STATUS	mandatory
	DESCRIPTION
	"Local IU ETHERNET3 channel errored received Mbytes"
	::= { liuEth3Stat 2}
    LIU_Eth3sent OBJECT-TYPE
    	SYNTAX	DisplayString (SIZE (0..255))
	ACCESS	read-only
	STATUS	mandatory
	DESCRIPTION
	"Local IU ETHERNET3 channel sent Mbytes"
	::= { liuEth3Stat 3}
    LIU_Eth3output OBJECT-TYPE
    	SYNTAX	DisplayString (SIZE (0..255))
	ACCESS	read-only
	STATUS	mandatory
	DESCRIPTION
	"Local IU ETHERNET3 channel output data rate Mbyte/s"
	::= { liuEth3Stat 4}
    LIU_Eth3input OBJECT-TYPE
    	SYNTAX	DisplayString (SIZE (0..255))
	ACCESS	read-only
	STATUS	mandatory
	DESCRIPTION
	"Local IU ETHERNET3 channel input data rate Mbyte/s"
	::= { liuEth3Stat 5}
    LIU_Eth3inperr OBJECT-TYPE
    	SYNTAX	DisplayString (SIZE (0..255))
	ACCESS	read-only
	STATUS	mandatory
	DESCRIPTION
	"Local IU ETHERNET3 channel input data error, %"
	::= { liuEth3Stat 6}

   liuBCKStat OBJECT IDENTIFIER ::= { liuChnStat 5 }
    LIU_BCKnoerr  OBJECT-TYPE
    	SYNTAX	DisplayString (SIZE (0..255))
	ACCESS	read-only
	STATUS	mandatory
	DESCRIPTION
	"Local IU Backup channel no errors received Mbytes"
	::= { liuBCKStat 1}
    LIU_BCKerr  OBJECT-TYPE
    	SYNTAX	DisplayString (SIZE (0..255))
	ACCESS	read-only
	STATUS	mandatory
	DESCRIPTION
	"Local IU Backup channel errored received Mbytes"
	::= { liuBCKStat 2}
    LIU_BCKsent OBJECT-TYPE
    	SYNTAX	DisplayString (SIZE (0..255))
	ACCESS	read-only
	STATUS	mandatory
	DESCRIPTION
	"Local IU Backup channel sent Mbytes"
	::= { liuBCKStat 3}
    LIU_BCKoutput OBJECT-TYPE
    	SYNTAX	DisplayString (SIZE (0..255))
	ACCESS	read-only
	STATUS	mandatory
	DESCRIPTION
	"Local IU Backup channel output data rate Mbyte/s"
	::= { liuBCKStat 4}
    LIU_BCKinput OBJECT-TYPE
    	SYNTAX	DisplayString (SIZE (0..255))
	ACCESS	read-only
	STATUS	mandatory
	DESCRIPTION
	"Local IU Backup channel input data rate Mbyte/s"
	::= { liuBCKStat 5}
    LIU_BCKinperr OBJECT-TYPE
    	SYNTAX	DisplayString (SIZE (0..255))
	ACCESS	read-only
	STATUS	mandatory
	DESCRIPTION
	"Local IU Backup channel input data error, %"
	::= { liuBCKStat 6}


 remoteOU OBJECT IDENTIFIER ::= { fsoTerminal 5 }
  ROU_SerialNumber	OBJECT-TYPE
    	SYNTAX	DisplayString (SIZE (0..255))
	ACCESS	read-only
	STATUS	mandatory
	DESCRIPTION
	"Local OU serial number"
	::= { remoteOU 1}
  ROU_License	OBJECT-TYPE
    	SYNTAX	DisplayString (SIZE (0..255))
	ACCESS	read-only
	STATUS	mandatory
	DESCRIPTION
	"Local OU license parameters"
	::= { remoteOU 2}
  ROU_Coordinates	OBJECT-TYPE
    	SYNTAX	DisplayString (SIZE (0..255))
	ACCESS	read-only
	STATUS	mandatory
	DESCRIPTION
	"OU installation geo coordinates"
	::= { remoteOU 3}
  ROU_Temperature	OBJECT-TYPE
    	SYNTAX	DisplayString (SIZE (0..255))
	ACCESS	read-only
	STATUS	mandatory
	DESCRIPTION
	"Local OU internal temperature"
	::= { remoteOU 4}
  rouState OBJECT IDENTIFIER ::= { remoteOU 5 }
   ROU_InputFiber  OBJECT-TYPE
    	SYNTAX	DisplayString (SIZE (0..255))
	ACCESS	read-only
	STATUS	mandatory
	DESCRIPTION
	"OU input fiber connection status"
	::= { rouState 1}
   ROU_Autotracking OBJECT-TYPE
    	SYNTAX	DisplayString (SIZE (0..255))
	ACCESS	read-only
	STATUS	mandatory
	DESCRIPTION
	"OU autotracking status"
	::= { rouState 2}
   ROU_ServiceChannel OBJECT-TYPE
    	SYNTAX	DisplayString (SIZE (0..255))
	ACCESS	read-only
	STATUS	mandatory
	DESCRIPTION
	"OU service channel status"
	::= { rouState 3}

 remoteIU OBJECT IDENTIFIER ::= { fsoTerminal 6 }
  RIU_FSOsignal OBJECT-TYPE
    	SYNTAX	DisplayString (SIZE (0..255))
	ACCESS	read-only
	STATUS	mandatory
	DESCRIPTION
	"Remote IU input FSO signal from OU"
	::= { remoteIU 1}  
  riuIPconfig OBJECT IDENTIFIER ::= { remoteIU 2 }
   RIU_IPaddress  OBJECT-TYPE
    	SYNTAX	DisplayString (SIZE (0..255))
	ACCESS	read-only
	STATUS	mandatory
	DESCRIPTION
	"Remote IU IP address"
	::= { riuIPconfig 1}
   RIU_NetMask  OBJECT-TYPE
    	SYNTAX	DisplayString (SIZE (0..255))
	ACCESS	read-only
	STATUS	mandatory
	DESCRIPTION
	"Remote IU Network mask"
	::= { riuIPconfig 2}
   RIU_IPgw  OBJECT-TYPE
    	SYNTAX	DisplayString (SIZE (0..255))
	ACCESS	read-only
	STATUS	mandatory
	DESCRIPTION
	"Remote IU gateway IP"
	::= { riuIPconfig 3}
   RIU_MACaddress  OBJECT-TYPE
    	SYNTAX	DisplayString (SIZE (0..255))
	ACCESS	read-only
	STATUS	mandatory
	DESCRIPTION
	"Remote IU MAC address"
	::= { riuIPconfig 4}
   RIU_SNMPagent  OBJECT-TYPE
    	SYNTAX	DisplayString (SIZE (0..255))
	ACCESS	read-only
	STATUS	mandatory
	DESCRIPTION
	"Remote IU SNMP agent IP"
	::= { riuIPconfig 5}
   RIU_Ports  OBJECT-TYPE
    	SYNTAX	DisplayString (SIZE (0..255))
	ACCESS	read-only
	STATUS	mandatory
	DESCRIPTION
	"Remote IU telemetry ports"
	::= { riuIPconfig 6}

  riuBackup OBJECT IDENTIFIER ::= { remoteIU 3 }
   RIU_BckSwmode  OBJECT-TYPE
    	SYNTAX	DisplayString (SIZE (0..255))
	ACCESS	read-only
	STATUS	mandatory
	DESCRIPTION
	"Remote IU backup switch mode"
	::= { riuBackup 1}
   RIU_BckMain  OBJECT-TYPE
    	SYNTAX	DisplayString (SIZE (0..255))
	ACCESS	read-only
	STATUS	mandatory
	DESCRIPTION
	"Remote IU backup main channel"
	::= { riuBackup 2}
   RIU_BckChn  OBJECT-TYPE
    	SYNTAX	DisplayString (SIZE (0..255))
	ACCESS	read-only
	STATUS	mandatory
	DESCRIPTION
	"Remote IU backup channel"
	::= { riuBackup 3}
   RIU_BckSwLevel  OBJECT-TYPE
    	SYNTAX	DisplayString (SIZE (0..255))
	ACCESS	read-only
	STATUS	mandatory
	DESCRIPTION
	"Remote IU losses backup channel switch level"
	::= { riuBackup 4}
   RIU_BckFSOReturnTime  OBJECT-TYPE
    	SYNTAX	DisplayString (SIZE (0..255))
	ACCESS	read-only
	STATUS	mandatory
	DESCRIPTION
	"Remote IU time for return to FSO from backup"
	::= { riuBackup 5}
   RIU_BckPOEConfig  OBJECT-TYPE
    	SYNTAX	DisplayString (SIZE (0..255))
	ACCESS	read-only
	STATUS	mandatory
	DESCRIPTION
	"Remote IU PoE backup config"
	::= { riuBackup 6}
   RIU_BckALLF  OBJECT-TYPE
    	SYNTAX	DisplayString (SIZE (0..255))
	ACCESS	read-only
	STATUS	mandatory
	DESCRIPTION
	"Remote IU PoE ALLFconfig"
	::= { riuBackup 7}
  
  riuChnStat OBJECT IDENTIFIER ::= { remoteIU 4 }
   riuFSOStat OBJECT IDENTIFIER ::= { riuChnStat 1 }
    RLIU_FSOnoerr  OBJECT-TYPE
    	SYNTAX	DisplayString (SIZE (0..255))
	ACCESS	read-only
	STATUS	mandatory
	DESCRIPTION
	"Remote IU FSO channel no errors received Mbytes"
	::= { riuFSOStat 1}
    RIU_FSOerr  OBJECT-TYPE
    	SYNTAX	DisplayString (SIZE (0..255))
	ACCESS	read-only
	STATUS	mandatory
	DESCRIPTION
	"Remote IU FSO channel errored received Mbytes"
	::= { riuFSOStat 2}
    RIU_FSOsent OBJECT-TYPE
    	SYNTAX	DisplayString (SIZE (0..255))
	ACCESS	read-only
	STATUS	mandatory
	DESCRIPTION
	"Remote IU FSO channel sent Mbytes"
	::= { riuFSOStat 3}
    RIU_FSOoutput OBJECT-TYPE
    	SYNTAX	DisplayString (SIZE (0..255))
	ACCESS	read-only
	STATUS	mandatory
	DESCRIPTION
	"Remote IU FSO channel output data rate Mbyte/s"
	::= { riuFSOStat 4}
    RIU_FSOinput OBJECT-TYPE
    	SYNTAX	DisplayString (SIZE (0..255))
	ACCESS	read-only
	STATUS	mandatory
	DESCRIPTION
	"Remote IU FSO channel input data rate Mbyte/s"
	::= { riuFSOStat 5}
    RIU_FSOinperr OBJECT-TYPE
    	SYNTAX	DisplayString (SIZE (0..255))
	ACCESS	read-only
	STATUS	mandatory
	DESCRIPTION
	"Remote IU FSO channel input data error, %"
	::= { riuFSOStat 6}

   riuEth1Stat OBJECT IDENTIFIER ::= { riuChnStat 2 }
    RIU_Eth1noerr  OBJECT-TYPE
    	SYNTAX	DisplayString (SIZE (0..255))
	ACCESS	read-only
	STATUS	mandatory
	DESCRIPTION
	"Remote IU ETHERNET1 channel no errors received Mbytes"
	::= { riuEth1Stat 1}
    RIU_Eth1err  OBJECT-TYPE
    	SYNTAX	DisplayString (SIZE (0..255))
	ACCESS	read-only
	STATUS	mandatory
	DESCRIPTION
	"Remote IU ETHERNET1 channel errored received Mbytes"
	::= { riuEth1Stat 2}
    RIU_Eth1sent OBJECT-TYPE
    	SYNTAX	DisplayString (SIZE (0..255))
	ACCESS	read-only
	STATUS	mandatory
	DESCRIPTION
	"Remote IU ETHERNET1 channel sent Mbytes"
	::= { riuEth1Stat 3}
    RIU_Eth1output OBJECT-TYPE
    	SYNTAX	DisplayString (SIZE (0..255))
	ACCESS	read-only
	STATUS	mandatory
	DESCRIPTION
	"Remote IU ETHERNET1 channel output data rate Mbyte/s"
	::= { riuEth1Stat 4}
    RIU_Eth1input OBJECT-TYPE
    	SYNTAX	DisplayString (SIZE (0..255))
	ACCESS	read-only
	STATUS	mandatory
	DESCRIPTION
	"Remote IU ETHERNET1 channel input data rate Mbyte/s"
	::= { riuEth1Stat 5}
    RIU_Eth1inperr OBJECT-TYPE
    	SYNTAX	DisplayString (SIZE (0..255))
	ACCESS	read-only
	STATUS	mandatory
	DESCRIPTION
	"Remote IU ETHERNET1 channel input data error, %"
	::= { riuEth1Stat 6}

   riuEth2Stat OBJECT IDENTIFIER ::= { riuChnStat 3 }
    RIU_Eth2noerr  OBJECT-TYPE
    	SYNTAX	DisplayString (SIZE (0..255))
	ACCESS	read-only
	STATUS	mandatory
	DESCRIPTION
	"Remote IU ETHERNET2 channel no errors received Mbytes"
	::= { riuEth2Stat 1}
    RIU_Eth2err  OBJECT-TYPE
    	SYNTAX	DisplayString (SIZE (0..255))
	ACCESS	read-only
	STATUS	mandatory
	DESCRIPTION
	"Remote IU ETHERNET2 channel errored received Mbytes"
	::= { riuEth2Stat 2}
    RIU_Eth2sent OBJECT-TYPE
    	SYNTAX	DisplayString (SIZE (0..255))
	ACCESS	read-only
	STATUS	mandatory
	DESCRIPTION
	"Remote IU ETHERNET2 channel sent Mbytes"
	::= { riuEth2Stat 3}
    RIU_Eth2output OBJECT-TYPE
    	SYNTAX	DisplayString (SIZE (0..255))
	ACCESS	read-only
	STATUS	mandatory
	DESCRIPTION
	"Remote IU ETHERNET2 channel output data rate Mbyte/s"
	::= { riuEth2Stat 4}
    RIU_Eth2input OBJECT-TYPE
    	SYNTAX	DisplayString (SIZE (0..255))
	ACCESS	read-only
	STATUS	mandatory
	DESCRIPTION
	"Remote IU ETHERNET2 channel input data rate Mbyte/s"
	::= { riuEth2Stat 5}
    RIU_Eth2inperr OBJECT-TYPE
    	SYNTAX	DisplayString (SIZE (0..255))
	ACCESS	read-only
	STATUS	mandatory
	DESCRIPTION
	"Remote IU ETHERNET2 channel input data error, %"
	::= { riuEth2Stat 6}

   riuEth3Stat OBJECT IDENTIFIER ::= { riuChnStat 4 }
    RIU_Eth3noerr  OBJECT-TYPE
    	SYNTAX	DisplayString (SIZE (0..255))
	ACCESS	read-only
	STATUS	mandatory
	DESCRIPTION
	"Remote IU ETHERNET3 channel no errors received Mbytes"
	::= { riuEth3Stat 1}
    RIU_Eth3err  OBJECT-TYPE
    	SYNTAX	DisplayString (SIZE (0..255))
	ACCESS	read-only
	STATUS	mandatory
	DESCRIPTION
	"Remote IU ETHERNET3 channel errored received Mbytes"
	::= { riuEth3Stat 2}
    RIU_Eth3sent OBJECT-TYPE
    	SYNTAX	DisplayString (SIZE (0..255))
	ACCESS	read-only
	STATUS	mandatory
	DESCRIPTION
	"Remote IU ETHERNET3 channel sent Mbytes"
	::= { riuEth3Stat 3}
    RIU_Eth3output OBJECT-TYPE
    	SYNTAX	DisplayString (SIZE (0..255))
	ACCESS	read-only
	STATUS	mandatory
	DESCRIPTION
	"Remote IU ETHERNET3 channel output data rate Mbyte/s"
	::= { riuEth3Stat 4}
    RIU_Eth3input OBJECT-TYPE
    	SYNTAX	DisplayString (SIZE (0..255))
	ACCESS	read-only
	STATUS	mandatory
	DESCRIPTION
	"Remote IU ETHERNET3 channel input data rate Mbyte/s"
	::= { riuEth3Stat 5}
    RIU_Eth3inperr OBJECT-TYPE
    	SYNTAX	DisplayString (SIZE (0..255))
	ACCESS	read-only
	STATUS	mandatory
	DESCRIPTION
	"Remote IU ETHERNET3 channel input data error, %"
	::= { riuEth3Stat 6}

   riuBCKStat OBJECT IDENTIFIER ::= { riuChnStat 5 }
    RIU_BCKnoerr  OBJECT-TYPE
    	SYNTAX	DisplayString (SIZE (0..255))
	ACCESS	read-only
	STATUS	mandatory
	DESCRIPTION
	"Remote IU Backup channel no errors received Mbytes"
	::= { riuBCKStat 1}
    RIU_BCKerr  OBJECT-TYPE
    	SYNTAX	DisplayString (SIZE (0..255))
	ACCESS	read-only
	STATUS	mandatory
	DESCRIPTION
	"Remote IU Backup channel errored received Mbytes"
	::= { riuBCKStat 2}
    RIU_BCKsent OBJECT-TYPE
    	SYNTAX	DisplayString (SIZE (0..255))
	ACCESS	read-only
	STATUS	mandatory
	DESCRIPTION
	"Remote IU Backup channel sent Mbytes"
	::= { riuBCKStat 3}
    RIU_BCKoutput OBJECT-TYPE
    	SYNTAX	DisplayString (SIZE (0..255))
	ACCESS	read-only
	STATUS	mandatory
	DESCRIPTION
	"Remote IU Backup channel output data rate Mbyte/s"
	::= { riuBCKStat 4}
    RIU_BCKinput OBJECT-TYPE
    	SYNTAX	DisplayString (SIZE (0..255))
	ACCESS	read-only
	STATUS	mandatory
	DESCRIPTION
	"Remote IU Backup channel input data rate Mbyte/s"
	::= { riuBCKStat 5}
    RIU_BCKinperr OBJECT-TYPE
    	SYNTAX	DisplayString (SIZE (0..255))
	ACCESS	read-only
	STATUS	mandatory
	DESCRIPTION
	"Remote IU Backup channel input data error, %"
	::= { riuBCKStat 6}

 localIUSFP OBJECT IDENTIFIER ::= { fsoTerminal 7 }
  LIU_LOS	OBJECT-TYPE
    	SYNTAX	DisplayString (SIZE (0..255))
	ACCESS	read-only
	STATUS	mandatory
	DESCRIPTION
	"Local IU SFP LOS"
	::= { localIUSFP 1}
  LIU_Tx	OBJECT-TYPE
    	SYNTAX	DisplayString (SIZE (0..255))
	ACCESS	read-only
	STATUS	mandatory
	DESCRIPTION
	"Local IU SFP Transmitter"
	::= { localIUSFP 2}
  LIU_SFP	OBJECT-TYPE
    	SYNTAX	DisplayString (SIZE (0..255))
	ACCESS	read-only
	STATUS	mandatory
	DESCRIPTION
	"Local IU SFP presence"
	::= { localIUSFP 3}

 remoteIUSFP OBJECT IDENTIFIER ::= { fsoTerminal 8 }
  RIU_LOS	OBJECT-TYPE
    	SYNTAX	DisplayString (SIZE (0..255))
	ACCESS	read-only
	STATUS	mandatory
	DESCRIPTION
	"Remote IU SFP LOS"
	::= { remoteIUSFP 1}
  RIU_Tx	OBJECT-TYPE
    	SYNTAX	DisplayString (SIZE (0..255))
	ACCESS	read-only
	STATUS	mandatory
	DESCRIPTION
	"Remote IU SFP Transmitter"
	::= { remoteIUSFP 2}
  RIU_SFP	OBJECT-TYPE
    	SYNTAX	DisplayString (SIZE (0..255))
	ACCESS	read-only
	STATUS	mandatory
	DESCRIPTION
	"Remote IU SFP presence"
	::= { remoteIUSFP 3}
END
