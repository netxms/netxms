--
-- Kelvin-IT-Chiller.mib
-- MIB generated by Rittal
-- Friday, 17 January 2014
--

Rittal-IT-Chiller DEFINITIONS ::= BEGIN

	IMPORTS
		NOTIFICATION-GROUP, OBJECT-GROUP
		FROM SNMPv2-CONF
		sysContact, sysName, sysDescr, sysLocation
		FROM SNMPv2-MIB
		enterprises, MODULE-IDENTITY, OBJECT-TYPE, NOTIFICATION-TYPE, Integer32
		FROM SNMPv2-SMI
		DisplayString
		FROM SNMPv2-TC;



rittal-IT-Chiller MODULE-IDENTITY

	LAST-UPDATED	"201401171730Z" -- January 17, 2014 at 17:30 GMT
	ORGANIZATION	"Rittal GmbH"
	CONTACT-INFO	"
			KELVIN srl / Rittal Gmbh
			Via degli Imprenditori, 15
			37067 Valeggio sul Mincio (VR) Italy
			Tel: +39 045 6372711
			E-mail: info@kelvinitaly.it
			"
	DESCRIPTION	"This is the MIB module for the Rittal's IT Chiller."
	REVISION	"201401171730Z" -- January 17, 2014 at 17:00 GMT
	DESCRIPTION	"
			The numbering of traps has been changed to avoid conflicts with similar
			devices that mounts onboard the Carel's pCOWeb adapter. Traps of IT
			Chillers should be generated with OID 1.3.6.1.4.1.2606.20.2.1.120.x
			"
	REVISION	"201309221200Z" -- September 22, 2013 at 12:00 GMT
	DESCRIPTION	"
			A new Rittal sysObjectID 1.3.6.1.4.1.2606.20 has been associated to IT Chillers
			sysObjectID defined by Daniel Rosenthal, Research and Development - Technology & Support, Rosenthal.D@rittal.de
			MIB file modified by Giuseppe Leto, Product Manager IT, Leto.G@rittal.it
			MIB file validated up to severity level 3 by simpleweb, http://www.simpleweb.org/ietf/mibs/validate/
			"
	REVISION	"201309131602Z"	-- September 13, 2013 at 16:02 GMT
	DESCRIPTION	"New MIB ChillerIT"

	::= { instruments 1 }


--
-- Node definitions
--

	-- 1.3.6.1.4.1.2606
	rittal OBJECT IDENTIFIER	::= { enterprises 2606 }

	-- 1.3.6.1.4.1.2606.20
	itChillers OBJECT IDENTIFIER	::= { rittal 20 }

	-- 1.3.6.1.4.1.2606.20.1
	system OBJECT IDENTIFIER	::= { itChillers 1 }

	-- 1.3.6.1.4.1.2606.20.1.1
	agentRelease OBJECT-TYPE
		SYNTAX Integer32
		UNITS "N/A"
		MAX-ACCESS read-only
		STATUS current
		DESCRIPTION "Release of the Agent."
		::= { system 1 }

	-- 1.3.6.1.4.1.2606.20.1.2
	agentCode OBJECT-TYPE
		SYNTAX Integer32
		UNITS "N/A"
		MAX-ACCESS read-only
		STATUS current
		DESCRIPTION "Code of the Agent. 2=pCOWeb."
		::= { system 2 }

	-- 1.3.6.1.4.1.2606.20.2
	instruments OBJECT IDENTIFIER	::= { itChillers 2 }

	-- 1.3.6.1.4.1.2606.20.2.0
	pCOWebInfo OBJECT IDENTIFIER	::= { instruments 0 }


	-- 1.3.6.1.4.1.2606.20.2.0.10
	pCOStatusgroup OBJECT IDENTIFIER ::= { pCOWebInfo 10 }

	-- 1.3.6.1.4.1.2606.20.2.0.10.1
	pCOId1-Status OBJECT-TYPE
		SYNTAX Integer32
		UNITS "N/A"
		MAX-ACCESS read-only
		STATUS current
		DESCRIPTION "Status of pCOId1. 0=Offline, 1=Init, 2=Online"
		::= { pCOStatusgroup 1 }

	-- ... You will have how many pCOIdX-Status objects as the pCOs connected to pCOWeb.

	-- 1.3.6.1.4.1.2606.20.2.0.11
	pCOErrorsNumbergroup OBJECT IDENTIFIER ::= { pCOWebInfo 11 }

	-- 1.3.6.1.4.1.2606.20.2.0.11.1
	pCOId1-ErrorsNumber OBJECT-TYPE
		SYNTAX Integer32
		UNITS "N/A"
		MAX-ACCESS read-only
		STATUS current
		DESCRIPTION "Number of Communication Errors from pCOId1 to pCOWeb."
		::= { pCOErrorsNumbergroup 1 }

	-- ... You will have how many pCOIdX-ErrorsNumber objects as the pCOs connected to pCOWeb.



--
-- DIGITAL VARIABLES
--

	-- 1.3.6.1.4.1.2606.20.2.1.1
	digitalObjects OBJECT IDENTIFIER	::= { rittal-IT-Chiller 1 }

	-- 1.3.6.1.4.1.2606.20.2.1.1.1
	al-pa1 OBJECT-TYPE
		SYNTAX Integer32 (0..1)
		UNITS "N/A"
		MAX-ACCESS read-only
		STATUS current
		DESCRIPTION "High pressure switch 1 alarm"
		::= { digitalObjects 1 }

	-- 1.3.6.1.4.1.2606.20.2.1.1.2
	al-pa2 OBJECT-TYPE
		SYNTAX Integer32 (0..1)
		UNITS "N/A"
		MAX-ACCESS read-only
		STATUS current
		DESCRIPTION "High pressure switch 2 alarm"
		::= { digitalObjects 2 }

	-- 1.3.6.1.4.1.2606.20.2.1.1.3
	al-pb1 OBJECT-TYPE
		SYNTAX Integer32 (0..1)
		UNITS "N/A"
		MAX-ACCESS read-only
		STATUS current
		DESCRIPTION "Low pressure switch 1 alarm"
		::= { digitalObjects 3 }

	-- 1.3.6.1.4.1.2606.20.2.1.1.4
	al-pb2 OBJECT-TYPE
		SYNTAX Integer32 (0..1)
		UNITS "N/A"
		MAX-ACCESS read-only
		STATUS current
		DESCRIPTION "Low pressure switch 2 alarm"
		::= { digitalObjects 4 }

	-- 1.3.6.1.4.1.2606.20.2.1.1.5
	--al-ta OBJECT-TYPE
	--	SYNTAX Integer32 (0..1)
	--	UNITS "N/A"
	--	MAX-ACCESS read-only
	--	STATUS current
	--	DESCRIPTION "Antifreeze alarm"
	--	::= { digitalObjects 5 }

	-- 1.3.6.1.4.1.2606.20.2.1.1.6
	al-le OBJECT-TYPE
		SYNTAX Integer32 (0..1)
		UNITS "N/A"
		MAX-ACCESS read-only
		STATUS current
		DESCRIPTION "Water level alarm"
		::= { digitalObjects 6 }

	-- 1.3.6.1.4.1.2606.20.2.1.1.7
	--din-7 OBJECT-TYPE
	--	SYNTAX Integer32 (0..1)
	--	UNITS "N/A"
	--	MAX-ACCESS read-only
	--	STATUS current
	--	DESCRIPTION "Digital input 7"
	--	::= { digitalObjects 7 }

	-- 1.3.6.1.4.1.2606.20.2.1.1.8
	al-idrofrigo-fl1 OBJECT-TYPE
		SYNTAX Integer32 (0..1)
		UNITS "N/A"
		MAX-ACCESS read-only
		STATUS current
		DESCRIPTION "Flow switch alarm"
		::= { digitalObjects 8 }

	-- 1.3.6.1.4.1.2606.20.2.1.1.9
	static-press-alarm OBJECT-TYPE
		SYNTAX Integer32 (0..1)
		UNITS "N/A"
		MAX-ACCESS read-only
		STATUS current
		DESCRIPTION "Water static pressure alarm"
		::= { digitalObjects 9 }

	-- 1.3.6.1.4.1.2606.20.2.1.1.10
	w-static-press-alarm OBJECT-TYPE
		SYNTAX Integer32 (0..1)
		UNITS "N/A"
		MAX-ACCESS read-only
		STATUS current
		DESCRIPTION "Water static pressure warning"
		::= { digitalObjects 10 }

	-- 1.3.6.1.4.1.2606.20.2.1.1.11
	flow-value-alarm OBJECT-TYPE
		SYNTAX Integer32 (0..1)
		UNITS "N/A"
		MAX-ACCESS read-only
		STATUS current
		DESCRIPTION "Flow rate alarm"
		::= { digitalObjects 11 }

	-- 1.3.6.1.4.1.2606.20.2.1.1.12
	al-q-comp1 OBJECT-TYPE
		SYNTAX Integer32 (0..1)
		UNITS "N/A"
		MAX-ACCESS read-only
		STATUS current
		DESCRIPTION "Overload compressor 1 circuit 1 alarm"
		::= { digitalObjects 12 }

	-- 1.3.6.1.4.1.2606.20.2.1.1.13
	al-q-comp2 OBJECT-TYPE
		SYNTAX Integer32 (0..1)
		UNITS "N/A"
		MAX-ACCESS read-only
		STATUS current
		DESCRIPTION "Overload compressor 2 circuit 1 alarm"
		::= { digitalObjects 13 }

	-- 1.3.6.1.4.1.2606.20.2.1.1.14
	al-q-comp3 OBJECT-TYPE
		SYNTAX Integer32 (0..1)
		UNITS "N/A"
		MAX-ACCESS read-only
		STATUS current
		DESCRIPTION "Overload compressor 3 circuit 1 alarm"
		::= { digitalObjects 14 }

	-- 1.3.6.1.4.1.2606.20.2.1.1.15
	al-q-comp4 OBJECT-TYPE
		SYNTAX Integer32 (0..1)
		UNITS "N/A"
		MAX-ACCESS read-only
		STATUS current
		DESCRIPTION "Overload compressor 1 circuit 2 alarm"
		::= { digitalObjects 15 }

	-- 1.3.6.1.4.1.2606.20.2.1.1.16
	al-q-comp5 OBJECT-TYPE
		SYNTAX Integer32 (0..1)
		UNITS "N/A"
		MAX-ACCESS read-only
		STATUS current
		DESCRIPTION "Overload compressor 2 circuit 2 alarm"
		::= { digitalObjects 16 }

	-- 1.3.6.1.4.1.2606.20.2.1.1.17
	al-q-comp6 OBJECT-TYPE
		SYNTAX Integer32 (0..1)
		UNITS "N/A"
		MAX-ACCESS read-only
		STATUS current
		DESCRIPTION "Overload compressor 3 circuit 2 alarm"
		::= { digitalObjects 17 }

	-- 1.3.6.1.4.1.2606.20.2.1.1.18
	al-q-fan-1 OBJECT-TYPE
		SYNTAX Integer32 (0..1)
		UNITS "N/A"
		MAX-ACCESS read-only
		STATUS current
		DESCRIPTION "Overload fans circuit 1"
		::= { digitalObjects 18 }

	-- 1.3.6.1.4.1.2606.20.2.1.1.19
	al-q-fan-2 OBJECT-TYPE
		SYNTAX Integer32 (0..1)
		UNITS "N/A"
		MAX-ACCESS read-only
		STATUS current
		DESCRIPTION "Overload fans circuit 2"
		::= { digitalObjects 19 }

	-- 1.3.6.1.4.1.2606.20.2.1.1.20
	al-q-fan11 OBJECT-TYPE
		SYNTAX Integer32 (0..1)
		UNITS "N/A"
		MAX-ACCESS read-only
		STATUS current
		DESCRIPTION "Overload fan 1 circuit 1 alarm"
		::= { digitalObjects 20 }

	-- 1.3.6.1.4.1.2606.20.2.1.1.21
	al-q-fan12 OBJECT-TYPE
		SYNTAX Integer32 (0..1)
		UNITS "N/A"
		MAX-ACCESS read-only
		STATUS current
		DESCRIPTION "Overload fan 2 circuit 1 alarm"
		::= { digitalObjects 21 }

	-- 1.3.6.1.4.1.2606.20.2.1.1.22
	al-q-fan13 OBJECT-TYPE
		SYNTAX Integer32 (0..1)
		UNITS "N/A"
		MAX-ACCESS read-only
		STATUS current
		DESCRIPTION "Overload fan 3 circuit 1 alarm"
		::= { digitalObjects 22 }

	-- 1.3.6.1.4.1.2606.20.2.1.1.23
	al-q-fan14 OBJECT-TYPE
		SYNTAX Integer32 (0..1)
		UNITS "N/A"
		MAX-ACCESS read-only
		STATUS current
		DESCRIPTION "Overload fan 4 circuit 1 alarm"
		::= { digitalObjects 23 }

	-- 1.3.6.1.4.1.2606.20.2.1.1.24
	al-q-fan21 OBJECT-TYPE
		SYNTAX Integer32 (0..1)
		UNITS "N/A"
		MAX-ACCESS read-only
		STATUS current
		DESCRIPTION "Overload fan 1 circuit 2 alarm"
		::= { digitalObjects 24 }

	-- 1.3.6.1.4.1.2606.20.2.1.1.25
	al-q-fan22 OBJECT-TYPE
		SYNTAX Integer32 (0..1)
		UNITS "N/A"
		MAX-ACCESS read-only
		STATUS current
		DESCRIPTION "Overload fan 2 circuit 2 alarm"
		::= { digitalObjects 25 }

	-- 1.3.6.1.4.1.2606.20.2.1.1.26
	al-q-fan23 OBJECT-TYPE
		SYNTAX Integer32 (0..1)
		UNITS "N/A"
		MAX-ACCESS read-only
		STATUS current
		DESCRIPTION "Overload fan 3 circuit 2 alarm"
		::= { digitalObjects 26 }

	-- 1.3.6.1.4.1.2606.20.2.1.1.27
	al-q-fan24 OBJECT-TYPE
		SYNTAX Integer32 (0..1)
		UNITS "N/A"
		MAX-ACCESS read-only
		STATUS current
		DESCRIPTION "Overload fan 4 circuit 2 alarm"
		::= { digitalObjects 27 }

	-- 1.3.6.1.4.1.2606.20.2.1.1.28
	al-idrofrigo-pump1 OBJECT-TYPE
		SYNTAX Integer32 (0..1)
		UNITS "N/A"
		MAX-ACCESS read-only
		STATUS current
		DESCRIPTION "Overload pump 1 alarm"
		::= { digitalObjects 28 }

	-- 1.3.6.1.4.1.2606.20.2.1.1.29
	al-idrofrigo-pump2 OBJECT-TYPE
		SYNTAX Integer32 (0..1)
		UNITS "N/A"
		MAX-ACCESS read-only
		STATUS current
		DESCRIPTION "Overload pump 2 alarm"
		::= { digitalObjects 29 }

	-- 1.3.6.1.4.1.2606.20.2.1.1.30
	al-phase-cont OBJECT-TYPE
		SYNTAX Integer32 (0..1)
		UNITS "N/A"
		MAX-ACCESS read-only
		STATUS current
		DESCRIPTION "Wrong phase rotation alarm"
		::= { digitalObjects 30 }

	-- 1.3.6.1.4.1.2606.20.2.1.1.31
	al-door-sw OBJECT-TYPE
		SYNTAX Integer32 (0..1)
		UNITS "N/A"
		MAX-ACCESS read-only
		STATUS current
		DESCRIPTION "Back Door open alarm"
		::= { digitalObjects 31 }

	-- 1.3.6.1.4.1.2606.20.2.1.1.32
	compressor-FlowRate OBJECT-TYPE
		SYNTAX Integer32 (0..1)
		UNITS "N/A"
		MAX-ACCESS read-write
		STATUS current
		DESCRIPTION "Compressor FlowRate Management"
		::= { digitalObjects 32 }

	-- 1.3.6.1.4.1.2606.20.2.1.1.33
	setpoint-inv-pumps OBJECT-TYPE
		SYNTAX Integer32 (0..1)
		UNITS "N/A"
		MAX-ACCESS read-write
		STATUS current
		DESCRIPTION "Setpoint Type for Inverter pumps"
		::= { digitalObjects 33 }

	-- 1.3.6.1.4.1.2606.20.2.1.1.34
	enable-pumps-redundance OBJECT-TYPE
		SYNTAX Integer32 (0..1)
		UNITS "N/A"
		MAX-ACCESS read-write
		STATUS current
		DESCRIPTION "Enable Pumps redundance"
		::= { digitalObjects 34 }

	-- 1.3.6.1.4.1.2606.20.2.1.1.35
	enable-chiller-redundance OBJECT-TYPE
		SYNTAX Integer32 (0..1)
		UNITS "N/A"
		MAX-ACCESS read-write
		STATUS current
		DESCRIPTION "Enable Chiller redundance"
		::= { digitalObjects 35 }

	-- 1.3.6.1.4.1.2606.20.2.1.1.36
	status-in-alarm OBJECT-TYPE
		SYNTAX Integer32 (0..1)
		UNITS "N/A"
		MAX-ACCESS read-write
		STATUS current
		DESCRIPTION "Status in alarm"
		::= { digitalObjects 36 }

	-- 1.3.6.1.4.1.2606.20.2.1.1.37
	compressor-recovery OBJECT-TYPE
		SYNTAX Integer32 (0..1)
		UNITS "N/A"
		MAX-ACCESS read-write
		STATUS current
		DESCRIPTION "Compressor Recovery"
		::= { digitalObjects 37 }

	-- 1.3.6.1.4.1.2606.20.2.1.1.38
	enable-thermal-redundance OBJECT-TYPE
		SYNTAX Integer32 (0..1)
		UNITS "N/A"
		MAX-ACCESS read-write
		STATUS current
		DESCRIPTION "Enable Thermal redundance"
		::= { digitalObjects 38 }

	-- 1.3.6.1.4.1.2606.20.2.1.1.39
	enable-multi-pumps-function OBJECT-TYPE
		SYNTAX Integer32 (0..1)
		UNITS "N/A"
		MAX-ACCESS read-write
		STATUS current
		DESCRIPTION "Enable multi-pumps function"
		::= { digitalObjects 39 }

	-- 1.3.6.1.4.1.2606.20.2.1.1.40
	enable-pumps-offline OBJECT-TYPE
		SYNTAX Integer32 (0..1)
		UNITS "N/A"
		MAX-ACCESS read-write
		STATUS current
		DESCRIPTION "Enable function pumps-Offline"
		::= { digitalObjects 40 }

	-- 1.3.6.1.4.1.2606.20.2.1.1.41
	enable-3way-valve OBJECT-TYPE
		SYNTAX Integer32 (0..1)
		UNITS "N/A"
		MAX-ACCESS read-write
		STATUS current
		DESCRIPTION "Enable 3way valve"
		::= { digitalObjects 41 }

	-- 1.3.6.1.4.1.2606.20.2.1.1.42
	enable-speed-up-FCM OBJECT-TYPE
		SYNTAX Integer32 (0..1)
		UNITS "N/A"
		MAX-ACCESS read-write
		STATUS current
		DESCRIPTION "Enable speed-up FCM"
		::= { digitalObjects 42 }

	-- 1.3.6.1.4.1.2606.20.2.1.1.43
	enable-soft-start-FCM OBJECT-TYPE
		SYNTAX Integer32 (0..1)
		UNITS "N/A"
		MAX-ACCESS read-write
		STATUS current
		DESCRIPTION "Enable soft-start FCM"
		::= { digitalObjects 43 }

	-- 1.3.6.1.4.1.2606.20.2.1.1.44
	enable-freecooling OBJECT-TYPE
		SYNTAX Integer32 (0..1)
		UNITS "N/A"
		MAX-ACCESS read-write
		STATUS current
		DESCRIPTION "Enable Freecooling"
		::= { digitalObjects 44}

	-- 1.3.6.1.4.1.2606.20.2.1.1.45
	enable-rot-FIFO-FC OBJECT-TYPE
		SYNTAX Integer32 (0..1)
		UNITS "N/A"
		MAX-ACCESS read-write
		STATUS current
		DESCRIPTION "Enable rotation FIFO Freecooling"
		::= { digitalObjects 45}

	-- 1.3.6.1.4.1.2606.20.2.1.1.46
	enable-HT-function OBJECT-TYPE
		SYNTAX Integer32 (0..1)
		UNITS "N/A"
		MAX-ACCESS read-write
		STATUS current
		DESCRIPTION "Enable HT-function"
		::= { digitalObjects 46 }

	-- 1.3.6.1.4.1.2606.20.2.1.1.47
	enable-PID-Fc-valve OBJECT-TYPE
		SYNTAX Integer32 (0..1)
		UNITS "N/A"
		MAX-ACCESS read-write
		STATUS current
		DESCRIPTION "Enable PID-regulation for Freecooling valve"
		::= { digitalObjects 47 }

	-- 1.3.6.1.4.1.2606.20.2.1.1.48
	enable-Fc-Thermal-Exclusion OBJECT-TYPE
		SYNTAX Integer32 (0..1)
		UNITS "N/A"
		MAX-ACCESS read-write
		STATUS current
		DESCRIPTION "Enable Freecooling Thermal Exclusion"
		::= { digitalObjects 48 }

	-- 1.3.6.1.4.1.2606.20.2.1.1.49
	manual-Reset-Ext-Drycooler-Alarm OBJECT-TYPE
		SYNTAX Integer32 (0..1)
		UNITS "N/A"
		MAX-ACCESS read-write
		STATUS current
		DESCRIPTION "Manual Reset External Dry-cooler Alarm"
		::= { digitalObjects 49 }

	-- 1.3.6.1.4.1.2606.20.2.1.1.50
	enable-static-press-Alarm OBJECT-TYPE
		SYNTAX Integer32 (0..1)
		UNITS "N/A"
		MAX-ACCESS read-write
		STATUS current
		DESCRIPTION "Enable static pressure Alarm"
		::= { digitalObjects 50 }

	-- 1.3.6.1.4.1.2606.20.2.1.1.51
	manual-reset-static-press-Alarm OBJECT-TYPE
		SYNTAX Integer32 (0..1)
		UNITS "N/A"
		MAX-ACCESS read-write
		STATUS current
		DESCRIPTION "Manual reset static pressure Alarm"
		::= { digitalObjects 51 }

	-- 1.3.6.1.4.1.2606.20.2.1.1.52
	enable-static-press-Warning OBJECT-TYPE
		SYNTAX Integer32 (0..1)
		UNITS "N/A"
		MAX-ACCESS read-write
		STATUS current
		DESCRIPTION "Enable static pressure Warning"
		::= { digitalObjects 52 }

	-- 1.3.6.1.4.1.2606.20.2.1.1.53
	manual-reset-static-press-Warning OBJECT-TYPE
		SYNTAX Integer32 (0..1)
		UNITS "N/A"
		MAX-ACCESS read-write
		STATUS current
		DESCRIPTION "Manual reset static pressure Warning"
		::= { digitalObjects 53 }

	-- 1.3.6.1.4.1.2606.20.2.1.1.54
	enable-diff-press-Alarm OBJECT-TYPE
		SYNTAX Integer32 (0..1)
		UNITS "N/A"
		MAX-ACCESS read-write
		STATUS current
		DESCRIPTION "Enable differential pressure Alarm"
		::= { digitalObjects 54 }

	-- 1.3.6.1.4.1.2606.20.2.1.1.55
	manual-reset-diff-press-Alarm OBJECT-TYPE
		SYNTAX Integer32 (0..1)
		UNITS "N/A"
		MAX-ACCESS read-write
		STATUS current
		DESCRIPTION "Manual reset differential pressure Alarm"
		::= { digitalObjects 55 }

	-- 1.3.6.1.4.1.2606.20.2.1.1.56
	enable-pressure-recovery OBJECT-TYPE
		SYNTAX Integer32 (0..1)
		UNITS "N/A"
		MAX-ACCESS read-write
		STATUS current
		DESCRIPTION "Enable pressure recovery"
		::= { digitalObjects 56 }

	-- 1.3.6.1.4.1.2606.20.2.1.1.57
	enable-Flow-Rate-Alarm OBJECT-TYPE
		SYNTAX Integer32 (0..1)
		UNITS "N/A"
		MAX-ACCESS read-write
		STATUS current
		DESCRIPTION "Enable Flow-Rate Alarm"
		::= { digitalObjects 57 }

	-- 1.3.6.1.4.1.2606.20.2.1.1.58
	manual-reset-Flow-Rate-Alarm OBJECT-TYPE
		SYNTAX Integer32 (0..1)
		UNITS "N/A"
		MAX-ACCESS read-write
		STATUS current
		DESCRIPTION "Manual reset Flow-Rate Alarm"
		::= { digitalObjects 58 }

	-- 1.3.6.1.4.1.2606.20.2.1.1.59
	enable-Flow-Rate-recovery OBJECT-TYPE
		SYNTAX Integer32 (0..1)
		UNITS "N/A"
		MAX-ACCESS read-write
		STATUS current
		DESCRIPTION "Enable Flow-Rate recovery"
		::= { digitalObjects 59 }

	-- 1.3.6.1.4.1.2606.20.2.1.1.60
	enable-pCOWeb OBJECT-TYPE
		SYNTAX Integer32 (0..1)
		UNITS "N/A"
		MAX-ACCESS read-write
		STATUS current
		DESCRIPTION "Enable pCOWeb"
		::= { digitalObjects 60 }

	-- 1.3.6.1.4.1.2606.20.2.1.1.61
	fc-single-chiller OBJECT-TYPE
		SYNTAX Integer32 (0..1)
		UNITS "N/A"
		MAX-ACCESS read-write
		STATUS current
		DESCRIPTION "Freecooling single chiller function"
		::= { digitalObjects 61 }

	-- 1.3.6.1.4.1.2606.20.2.1.1.75
	al-idrofrigo-pump-c-1 OBJECT-TYPE
		SYNTAX Integer32 (0..1)
		UNITS "N/A"
		MAX-ACCESS read-only
		STATUS current
		DESCRIPTION "Condensation pump 1 breaker switch alarm"
		::= { digitalObjects 75 }

	-- 1.3.6.1.4.1.2606.20.2.1.1.76
	al-idrofrigo-pump-c-2 OBJECT-TYPE
		SYNTAX Integer32 (0..1)
		UNITS "N/A"
		MAX-ACCESS read-only
		STATUS current
		DESCRIPTION "Condensation pump 2 breaker switch alarm"
		::= { digitalObjects 76 }

	-- 1.3.6.1.4.1.2606.20.2.1.1.80
	al-idrofrigo-fl-C OBJECT-TYPE
		SYNTAX Integer32 (0..1)
		UNITS "N/A"
		MAX-ACCESS read-only
		STATUS current
		DESCRIPTION "Condensation flow switch alarm"
		::= { digitalObjects 80 }

	-- 1.3.6.1.4.1.2606.20.2.1.1.100
	c11-on OBJECT-TYPE
		SYNTAX Integer32 (0..1)
		UNITS "N/A"
		MAX-ACCESS read-only
		STATUS current
		DESCRIPTION "Compressor 1 circuit 1 ON"
		::= { digitalObjects 100 }

	-- 1.3.6.1.4.1.2606.20.2.1.1.101
	c12-on OBJECT-TYPE
		SYNTAX Integer32 (0..1)
		UNITS "N/A"
		MAX-ACCESS read-only
		STATUS current
		DESCRIPTION "Compressor 2 circuit 1 ON"
		::= { digitalObjects 101 }

	-- 1.3.6.1.4.1.2606.20.2.1.1.102
	c13-on OBJECT-TYPE
		SYNTAX Integer32 (0..1)
		UNITS "N/A"
		MAX-ACCESS read-only
		STATUS current
		DESCRIPTION "Compressor 3 circuit 1 ON"
		::= { digitalObjects 102 }

	-- 1.3.6.1.4.1.2606.20.2.1.1.103
	c21-on OBJECT-TYPE
		SYNTAX Integer32 (0..1)
		UNITS "N/A"
		MAX-ACCESS read-only
		STATUS current
		DESCRIPTION "Compressor 1 circuit 2 ON"
		::= { digitalObjects 103 }

	-- 1.3.6.1.4.1.2606.20.2.1.1.104
	c22-on OBJECT-TYPE
		SYNTAX Integer32 (0..1)
		UNITS "N/A"
		MAX-ACCESS read-only
		STATUS current
		DESCRIPTION "Compressor 2 circuit 2 ON"
		::= { digitalObjects 104 }

	-- 1.3.6.1.4.1.2606.20.2.1.1.105
	c23-on OBJECT-TYPE
		SYNTAX Integer32 (0..1)
		UNITS "N/A"
		MAX-ACCESS read-only
		STATUS current
		DESCRIPTION "Compressor 3 circuit 2 ON"
		::= { digitalObjects 105 }

	-- 1.3.6.1.4.1.2606.20.2.1.1.106
	pump1-on OBJECT-TYPE
		SYNTAX Integer32 (0..1)
		UNITS "N/A"
		MAX-ACCESS read-only
		STATUS current
		DESCRIPTION "Pump 1 ON"
		::= { digitalObjects 106 }

	-- 1.3.6.1.4.1.2606.20.2.1.1.107
	pump2-on OBJECT-TYPE
		SYNTAX Integer32 (0..1)
		UNITS "N/A"
		MAX-ACCESS read-only
		STATUS current
		DESCRIPTION "Pump 2 ON"
		::= { digitalObjects 107 }

	-- 1.3.6.1.4.1.2606.20.2.1.1.108
	on-fan-gr1 OBJECT-TYPE
		SYNTAX Integer32 (0..1)
		UNITS "N/A"
		MAX-ACCESS read-only
		STATUS current
		DESCRIPTION "Fans group 1 ON"
		::= { digitalObjects 108 }

	-- 1.3.6.1.4.1.2606.20.2.1.1.109
	on-fan-gr2 OBJECT-TYPE
		SYNTAX Integer32 (0..1)
		UNITS "N/A"
		MAX-ACCESS read-only
		STATUS current
		DESCRIPTION "Fans group 2 ON"
		::= { digitalObjects 109 }

	-- 1.3.6.1.4.1.2606.20.2.1.1.110
	fc-on OBJECT-TYPE
		SYNTAX Integer32 (0..1)
		UNITS "N/A"
		MAX-ACCESS read-only
		STATUS current
		DESCRIPTION "Freecooling or external dry-cooler 1 ON"
		::= { digitalObjects 110 }

	-- 1.3.6.1.4.1.2606.20.2.1.1.130
	en-on-off-rem OBJECT-TYPE
		SYNTAX Integer32 (0..1)
		UNITS "N/A"
		MAX-ACCESS read-write
		STATUS current
		DESCRIPTION "Remote on-off"
		::= { digitalObjects 130 }

	-- 1.3.6.1.4.1.2606.20.2.1.1.131
	unit-on OBJECT-TYPE
		SYNTAX Integer32 (0..1)
		UNITS "N/A"
		MAX-ACCESS read-write
		STATUS current
		DESCRIPTION "Chiller ON"
		::= { digitalObjects 131 }

	-- 1.3.6.1.4.1.2606.20.2.1.1.148
	disch-alarm-scw-1 OBJECT-TYPE
		SYNTAX Integer32 (0..1)
		UNITS "N/A"
		MAX-ACCESS read-only
		STATUS current
		DESCRIPTION "Discharge screw compressor 1 alarm"
		::= { digitalObjects 148 }

	-- 1.3.6.1.4.1.2606.20.2.1.1.149
	disch-alarm-scw-2 OBJECT-TYPE
		SYNTAX Integer32 (0..1)
		UNITS "N/A"
		MAX-ACCESS read-only
		STATUS current
		DESCRIPTION "Discharge screw compressor 2 alarm"
		::= { digitalObjects 149 }

	-- 1.3.6.1.4.1.2606.20.2.1.1.150
	al-probe-inlet OBJECT-TYPE
		SYNTAX Integer32 (0..1)
		UNITS "N/A"
		MAX-ACCESS read-only
		STATUS current
		DESCRIPTION "Inlet probe alarm (broken or disconnected)"
		::= { digitalObjects 150 }

	-- 1.3.6.1.4.1.2606.20.2.1.1.151
	al-probe-amb OBJECT-TYPE
		SYNTAX Integer32 (0..1)
		UNITS "N/A"
		MAX-ACCESS read-only
		STATUS current
		DESCRIPTION "Ambient probe alarm (broken or disconnected)"
		::= { digitalObjects 151 }

	-- 1.3.6.1.4.1.2606.20.2.1.1.152
	al-frigo-fl1 OBJECT-TYPE
		SYNTAX Integer32 (0..1)
		UNITS "N/A"
		MAX-ACCESS read-only
		STATUS current
		DESCRIPTION "Flow switch alarm (cooling alarm)"
		::= { digitalObjects 152 }

	-- 1.3.6.1.4.1.2606.20.2.1.1.153
	al-idro-pump1 OBJECT-TYPE
		SYNTAX Integer32 (0..1)
		UNITS "N/A"
		MAX-ACCESS read-only
		STATUS current
		DESCRIPTION "Pump 1 hydraulic alarm"
		::= { digitalObjects 153 }

	-- 1.3.6.1.4.1.2606.20.2.1.1.154
	al-idro-pump2 OBJECT-TYPE
		SYNTAX Integer32 (0..1)
		UNITS "N/A"
		MAX-ACCESS read-only
		STATUS current
		DESCRIPTION "Pump 2 hydraulic alarm"
		::= { digitalObjects 154 }

	-- 1.3.6.1.4.1.2606.20.2.1.1.155
	al-idro-fl1 OBJECT-TYPE
		SYNTAX Integer32 (0..1)
		UNITS "N/A"
		MAX-ACCESS read-only
		STATUS current
		DESCRIPTION "Flow switch alarm (hydraulic alarm)"
		::= { digitalObjects 155 }

	-- 1.3.6.1.4.1.2606.20.2.1.1.156
	al-warning-fl1 OBJECT-TYPE
		SYNTAX Integer32 (0..1)
		UNITS "N/A"
		MAX-ACCESS read-only
		STATUS current
		DESCRIPTION "Flow switch alarm (warning alarm)"
		::= { digitalObjects 156 }

	-- 1.3.6.1.4.1.2606.20.2.1.1.157
	al-hi-water-temp OBJECT-TYPE
		SYNTAX Integer32 (0..1)
		UNITS "N/A"
		MAX-ACCESS read-only
		STATUS current
		DESCRIPTION "High Temperature alarm"
		::= { digitalObjects 157 }

	-- 1.3.6.1.4.1.2606.20.2.1.1.158
	al-lo-water-temp OBJECT-TYPE
		SYNTAX Integer32 (0..1)
		UNITS "N/A"
		MAX-ACCESS read-only
		STATUS current
		DESCRIPTION "Low Temperature alarm"
		::= { digitalObjects 158 }

	-- 1.3.6.1.4.1.2606.20.2.1.1.159
	al-ta-probe1 OBJECT-TYPE
		SYNTAX Integer32 (0..1)
		UNITS "N/A"
		MAX-ACCESS read-only
		STATUS current
		DESCRIPTION "Antifreeze/evaporator probe 1 alarm"
		::= { digitalObjects 159 }

	-- 1.3.6.1.4.1.2606.20.2.1.1.160
	al-hi-press OBJECT-TYPE
		SYNTAX Integer32 (0..1)
		UNITS "N/A"
		MAX-ACCESS read-only
		STATUS current
		DESCRIPTION "High condensation pressure alarm"
		::= { digitalObjects 160 }

	-- 1.3.6.1.4.1.2606.20.2.1.1.161
	al-lo-press OBJECT-TYPE
		SYNTAX Integer32 (0..1)
		UNITS "N/A"
		MAX-ACCESS read-only
		STATUS current
		DESCRIPTION "Low condensation pressure alarm"
		::= { digitalObjects 161 }

	-- 1.3.6.1.4.1.2606.20.2.1.1.162
	al-probe-evap-1 OBJECT-TYPE
		SYNTAX Integer32 (0..1)
		UNITS "N/A"
		MAX-ACCESS read-only
		STATUS current
		DESCRIPTION "Antifreeze/evaporator probe 1 alarm (broken or disconnected)"
		::= { digitalObjects 162 }

	-- 1.3.6.1.4.1.2606.20.2.1.1.163
	al-probe-evap-2 OBJECT-TYPE
		SYNTAX Integer32 (0..1)
		UNITS "N/A"
		MAX-ACCESS read-only
		STATUS current
		DESCRIPTION "Antifreeze/evaporator probe 2 alarm (broken or disconnected)"
		::= { digitalObjects 163 }

	-- 1.3.6.1.4.1.2606.20.2.1.1.164
	al-hi-press-1 OBJECT-TYPE
		SYNTAX Integer32 (0..1)
		UNITS "N/A"
		MAX-ACCESS read-only
		STATUS current
		DESCRIPTION "High condensation pressure 1 alarm"
		::= { digitalObjects 164 }

	-- 1.3.6.1.4.1.2606.20.2.1.1.165
	al-hi-press-2 OBJECT-TYPE
		SYNTAX Integer32 (0..1)
		UNITS "N/A"
		MAX-ACCESS read-only
		STATUS current
		DESCRIPTION "High condensation pressure 2 alarm"
		::= { digitalObjects 165 }

	-- 1.3.6.1.4.1.2606.20.2.1.1.166
	al-lo-press-1 OBJECT-TYPE
		SYNTAX Integer32 (0..1)
		UNITS "N/A"
		MAX-ACCESS read-only
		STATUS current
		DESCRIPTION "Low condensation pressure 1 alarm"
		::= { digitalObjects 166 }

	-- 1.3.6.1.4.1.2606.20.2.1.1.167
	al-lo-press-2 OBJECT-TYPE
		SYNTAX Integer32 (0..1)
		UNITS "N/A"
		MAX-ACCESS read-only
		STATUS current
		DESCRIPTION "Low condensation pressure 2 alarm"
		::= { digitalObjects 167 }

	-- 1.3.6.1.4.1.2606.20.2.1.1.168
	al-probe-tank OBJECT-TYPE
		SYNTAX Integer32 (0..1)
		UNITS "N/A"
		MAX-ACCESS read-only
		STATUS current
		DESCRIPTION "Tank/Out probe alarm (broken or disconnected)"
		::= { digitalObjects 168 }

	-- 1.3.6.1.4.1.2606.20.2.1.1.169
	off-line-1 OBJECT-TYPE
		SYNTAX Integer32 (0..1)
		UNITS "N/A"
		MAX-ACCESS read-only
		STATUS current
		DESCRIPTION "Chiller 1 offline"
		::= { digitalObjects 169 }

	-- 1.3.6.1.4.1.2606.20.2.1.1.170
	off-line-2 OBJECT-TYPE
		SYNTAX Integer32 (0..1)
		UNITS "N/A"
		MAX-ACCESS read-only
		STATUS current
		DESCRIPTION "Chiller 2 offline"
		::= { digitalObjects 170 }

	-- 1.3.6.1.4.1.2606.20.2.1.1.171
	off-line-3 OBJECT-TYPE
		SYNTAX Integer32 (0..1)
		UNITS "N/A"
		MAX-ACCESS read-only
		STATUS current
		DESCRIPTION "Chiller 3 offline"
		::= { digitalObjects 171 }

	-- 1.3.6.1.4.1.2606.20.2.1.1.172
	off-line-4 OBJECT-TYPE
		SYNTAX Integer32 (0..1)
		UNITS "N/A"
		MAX-ACCESS read-only
		STATUS current
		DESCRIPTION "Chiller 4 offline"
		::= { digitalObjects 172 }

	-- 1.3.6.1.4.1.2606.20.2.1.1.173
	off-line-5 OBJECT-TYPE
		SYNTAX Integer32 (0..1)
		UNITS "N/A"
		MAX-ACCESS read-only
		STATUS current
		DESCRIPTION "Chiller 5 offline"
		::= { digitalObjects 173 }

	-- 1.3.6.1.4.1.2606.20.2.1.1.174
	off-line-6 OBJECT-TYPE
		SYNTAX Integer32 (0..1)
		UNITS "N/A"
		MAX-ACCESS read-only
		STATUS current
		DESCRIPTION "Chiller 6 offline"
		::= { digitalObjects 174 }

	-- 1.3.6.1.4.1.2606.20.2.1.1.175
	off-line-7 OBJECT-TYPE
		SYNTAX Integer32 (0..1)
		UNITS "N/A"
		MAX-ACCESS read-only
		STATUS current
		DESCRIPTION "Chiller 7 offline"
		::= { digitalObjects 175 }

	-- 1.3.6.1.4.1.2606.20.2.1.1.176
	off-line-8 OBJECT-TYPE
		SYNTAX Integer32 (0..1)
		UNITS "N/A"
		MAX-ACCESS read-only
		STATUS current
		DESCRIPTION "Chiller 8 offline"
		::= { digitalObjects 176 }

	-- 1.3.6.1.4.1.2606.20.2.1.1.177
	al-ta-probe2 OBJECT-TYPE
		SYNTAX Integer32 (0..1)
		UNITS "N/A"
		MAX-ACCESS read-only
		STATUS current
		DESCRIPTION "Antifreeze/evaporator probe 2 alarm"
		::= { digitalObjects 177 }

	-- 1.3.6.1.4.1.2606.20.2.1.1.178
	al-sms OBJECT-TYPE
		SYNTAX Integer32 (0..1)
		UNITS "N/A"
		MAX-ACCESS read-only
		STATUS current
		DESCRIPTION "SMS alarm"
		::= { digitalObjects 178 }

	-- 1.3.6.1.4.1.2606.20.2.1.1.179
	al-modem OBJECT-TYPE
		SYNTAX Integer32 (0..1)
		UNITS "N/A"
		MAX-ACCESS read-only
		STATUS current
		DESCRIPTION "Modem alarm"
		::= { digitalObjects 179 }

	-- 1.3.6.1.4.1.2606.20.2.1.1.180
	sms-coda-alarm OBJECT-TYPE
		SYNTAX Integer32 (0..1)
		UNITS "N/A"
		MAX-ACCESS read-only
		STATUS current
		DESCRIPTION "SMS coda alarm"
		::= { digitalObjects 180 }

	-- 1.3.6.1.4.1.2606.20.2.1.1.181
	al-probe-fc OBJECT-TYPE
		SYNTAX Integer32 (0..1)
		UNITS "N/A"
		MAX-ACCESS read-only
		STATUS current
		DESCRIPTION "Freecooling probe alarm (broken or disconnected)"
		::= { digitalObjects 181 }

	-- 1.3.6.1.4.1.2606.20.2.1.1.182
	al-maint-pw1 OBJECT-TYPE
		SYNTAX Integer32 (0..1)
		UNITS "N/A"
		MAX-ACCESS read-only
		STATUS current
		DESCRIPTION "Maintenance pump 1 alarm)"
		::= { digitalObjects 182 }

	-- 1.3.6.1.4.1.2606.20.2.1.1.183
	al-maint-pw2 OBJECT-TYPE
		SYNTAX Integer32 (0..1)
		UNITS "N/A"
		MAX-ACCESS read-only
		STATUS current
		DESCRIPTION "Maintenance pump 2 alarm)"
		::= { digitalObjects 183 }

	-- 1.3.6.1.4.1.2606.20.2.1.1.184
	al-hi-temp-rid OBJECT-TYPE
		SYNTAX Integer32 (0..1)
		UNITS "N/A"
		MAX-ACCESS read-only
		STATUS current
		DESCRIPTION "High temperature alarm (redundance)"
		::= { digitalObjects 184 }

	-- 1.3.6.1.4.1.2606.20.2.1.1.185
	al-q-fc-sep OBJECT-TYPE
		SYNTAX Integer32 (0..1)
		UNITS "N/A"
		MAX-ACCESS read-only
		STATUS current
		DESCRIPTION "DryCooler breaker switch alarm"
		::= { digitalObjects 185 }

	-- 1.3.6.1.4.1.2606.20.2.1.1.186
	al-p-wat2 OBJECT-TYPE
		SYNTAX Integer32 (0..1)
		UNITS "N/A"
		MAX-ACCESS read-only
		STATUS current
		DESCRIPTION "Water pressure 2 alarm"
		::= { digitalObjects 186 }

	-- 1.3.6.1.4.1.2606.20.2.1.1.187
	al-p-wat1 OBJECT-TYPE
		SYNTAX Integer32 (0..1)
		UNITS "N/A"
		MAX-ACCESS read-only
		STATUS current
		DESCRIPTION "Water pressure 1 alarm"
		::= { digitalObjects 187 }

	-- 1.3.6.1.4.1.2606.20.2.1.1.188
	al-fault-flow-p1 OBJECT-TYPE
		SYNTAX Integer32 (0..1)
		UNITS "N/A"
		MAX-ACCESS read-only
		STATUS current
		DESCRIPTION "Pump 1 flow alarm"
		::= { digitalObjects 188 }

	-- 1.3.6.1.4.1.2606.20.2.1.1.189
	al-fault-flow-p2 OBJECT-TYPE
		SYNTAX Integer32 (0..1)
		UNITS "N/A"
		MAX-ACCESS read-only
		STATUS current
		DESCRIPTION "Pump 2 flow alarm"
		::= { digitalObjects 189 }

	-- 1.3.6.1.4.1.2606.20.2.1.1.190
	al-fault-fl1-p1 OBJECT-TYPE
		SYNTAX Integer32 (0..1)
		UNITS "N/A"
		MAX-ACCESS read-only
		STATUS current
		DESCRIPTION "Pump 1 flow-switch alarm"
		::= { digitalObjects 190 }

	-- 1.3.6.1.4.1.2606.20.2.1.1.191
	al-fault-fl1-p2 OBJECT-TYPE
		SYNTAX Integer32 (0..1)
		UNITS "N/A"
		MAX-ACCESS read-only
		STATUS current
		DESCRIPTION "Pump 2 flow-switch alarm"
		::= { digitalObjects 191 }

	-- 1.3.6.1.4.1.2606.20.2.1.1.192
	al-warning-le OBJECT-TYPE
		SYNTAX Integer32 (0..1)
		UNITS "N/A"
		MAX-ACCESS read-only
		STATUS current
		DESCRIPTION "Water level warning"
		::= { digitalObjects 192 }

	-- 1.3.6.1.4.1.2606.20.2.1.1.193
	al-frigo-fl-C OBJECT-TYPE
		SYNTAX Integer32 (0..1)
		UNITS "N/A"
		MAX-ACCESS read-only
		STATUS current
		DESCRIPTION "Flow switch condensation alarm (cooling alarm)"
		::= { digitalObjects 193 }

	-- 1.3.6.1.4.1.2606.20.2.1.1.194
	al-idro-pump-c-1 OBJECT-TYPE
		SYNTAX Integer32 (0..1)
		UNITS "N/A"
		MAX-ACCESS read-only
		STATUS current
		DESCRIPTION "Pump 1 condensation hydraulic alarm"
		::= { digitalObjects 194 }

	-- 1.3.6.1.4.1.2606.20.2.1.1.195
	al-idro-pump-c-2 OBJECT-TYPE
		SYNTAX Integer32 (0..1)
		UNITS "N/A"
		MAX-ACCESS read-only
		STATUS current
		DESCRIPTION "Pump 2 condensation hydraulic alarm"
		::= { digitalObjects 195 }


	-- 1.3.6.1.4.1.2606.20.2.1.1.196
	al-idro-fl-C OBJECT-TYPE
		SYNTAX Integer32 (0..1)
		UNITS "N/A"
		MAX-ACCESS read-only
		STATUS current
		DESCRIPTION "Flow switch condensation alarm (hydraulic alarm)"
		::= { digitalObjects 196 }

	-- 1.3.6.1.4.1.2606.20.2.1.1.197
	al-warning-fl-C OBJECT-TYPE
		SYNTAX Integer32 (0..1)
		UNITS "N/A"
		MAX-ACCESS read-only
		STATUS current
		DESCRIPTION "Flow switch condensation alarm (warning alarm)"
		::= { digitalObjects 197 }

	-- 1.3.6.1.4.1.2606.20.2.1.1.198
	al-foul-fl-C-p1 OBJECT-TYPE
		SYNTAX Integer32 (0..1)
		UNITS "N/A"
		MAX-ACCESS read-only
		STATUS current
		DESCRIPTION "Pump 1 condensation flow-switch alarm"
		::= { digitalObjects 198 }

	-- 1.3.6.1.4.1.2606.20.2.1.1.199
	al-foul-fl-C-p2 OBJECT-TYPE
		SYNTAX Integer32 (0..1)
		UNITS "N/A"
		MAX-ACCESS read-only
		STATUS current
		DESCRIPTION "Pump 2 condensation flow-switch alarm"
		::= { digitalObjects 199 }



--
-- ANALOG VARIABLES
--

	-- 1.3.6.1.4.1.2606.20.2.1.2
	analogObjects OBJECT IDENTIFIER		::= { rittal-IT-Chiller 2 }

	-- 1.3.6.1.4.1.2606.20.2.1.2.1
	setpoint-antifreeze1 OBJECT-TYPE
		SYNTAX Integer32 (-999..999)
		UNITS "N/A"
		MAX-ACCESS read-write
		STATUS current
		DESCRIPTION "Setpoint Antifreeze 1"
		::= { analogObjects 1 }

	-- 1.3.6.1.4.1.2606.20.2.1.2.2
	setpoint-antifreeze2 OBJECT-TYPE
		SYNTAX Integer32 (-999..999)
		UNITS "N/A"
		MAX-ACCESS read-write
		STATUS current
		DESCRIPTION "Setpoint Antifreeze 2"
		::= { analogObjects 2 }

	-- 1.3.6.1.4.1.2606.20.2.1.2.3
	setpoint-Compensation OBJECT-TYPE
		SYNTAX Integer32 (-999..999)
		UNITS "N/A"
		MAX-ACCESS read-write
		STATUS current
		DESCRIPTION "Setpoint Compensation"
		::= { analogObjects 3 }

	-- 1.3.6.1.4.1.2606.20.2.1.2.4
	hysteresis-Compensation OBJECT-TYPE
		SYNTAX Integer32 (-999..999)
		UNITS "N/A"
		MAX-ACCESS read-write
		STATUS current
		DESCRIPTION "Hysteresis Compensation"
		::= { analogObjects 4 }

	-- 1.3.6.1.4.1.2606.20.2.1.2.5
	max-Compensation OBJECT-TYPE
		SYNTAX Integer32 (-999..999)
		UNITS "N/A"
		MAX-ACCESS read-write
		STATUS current
		DESCRIPTION "Max. Compensation"
		::= { analogObjects 5 }

	-- 1.3.6.1.4.1.2606.20.2.1.2.6
	setpoint-Differential OBJECT-TYPE
		SYNTAX Integer32 (-999..999)
		UNITS "N/A"
		MAX-ACCESS read-write
		STATUS current
		DESCRIPTION "Setpoint Differential"
		::= { analogObjects 6 }

	-- 1.3.6.1.4.1.2606.20.2.1.2.7
	high-Limit OBJECT-TYPE
		SYNTAX Integer32 (-999..999)
		UNITS "N/A"
		MAX-ACCESS read-write
		STATUS current
		DESCRIPTION "High Limit"
		::= { analogObjects 7 }

	-- 1.3.6.1.4.1.2606.20.2.1.2.8
	low-Limit OBJECT-TYPE
		SYNTAX Integer32 (-999..999)
		UNITS "N/A"
		MAX-ACCESS read-write
		STATUS current
		DESCRIPTION "Low Limit"
		::= { analogObjects 8 }

	-- 1.3.6.1.4.1.2606.20.2.1.2.9
	max-Setpoint-Differential OBJECT-TYPE
		SYNTAX Integer32 (-999..999)
		UNITS "N/A"
		MAX-ACCESS read-write
		STATUS current
		DESCRIPTION "Max. Setpoint Differential"
		::= { analogObjects 9 }

	-- 1.3.6.1.4.1.2606.20.2.1.2.10
	min-Setpoint-Differential OBJECT-TYPE
		SYNTAX Integer32 (-999..999)
		UNITS "N/A"
		MAX-ACCESS read-write
		STATUS current
		DESCRIPTION "Min. Setpoint Differential"
		::= { analogObjects 10 }

	-- 1.3.6.1.4.1.2606.20.2.1.2.11
	setpoint-ASB-Inverter-pumps OBJECT-TYPE
		SYNTAX Integer32 (-999..999)
		UNITS "N/A"
		MAX-ACCESS read-write
		STATUS current
		DESCRIPTION "Setpoint ASB Inverter pumps"
		::= { analogObjects 11 }

	-- 1.3.6.1.4.1.2606.20.2.1.2.12
	setpoint-DIFF-Inverter-pumps OBJECT-TYPE
		SYNTAX Integer32 (-999..999)
		UNITS "N/A"
		MAX-ACCESS read-write
		STATUS current
		DESCRIPTION "Setpoint DIFF Inverter pumps"
		::= { analogObjects 12 }

	-- 1.3.6.1.4.1.2606.20.2.1.2.13
	pressure-Out OBJECT-TYPE
		SYNTAX Integer32 (-999..999)
		UNITS "N/A"
		MAX-ACCESS read-only
		STATUS current
		DESCRIPTION "Pressure Out"
		::= { analogObjects 13 }

	-- 1.3.6.1.4.1.2606.20.2.1.2.14
	proportional-Band-Inverter-Pumps-PID OBJECT-TYPE
		SYNTAX Integer32 (-999..999)
		UNITS "N/A"
		MAX-ACCESS read-write
		STATUS current
		DESCRIPTION "Proportional Band Inverter Pumps PID"
		::= { analogObjects 14 }

	-- 1.3.6.1.4.1.2606.20.2.1.2.15
	integral-Time-Inverter-Pumps-PID OBJECT-TYPE
		SYNTAX Integer32 (-999..999)
		UNITS "N/A"
		MAX-ACCESS read-write
		STATUS current
		DESCRIPTION "Integral Time Inverter Pumps PID"
		::= { analogObjects 15 }

	-- 1.3.6.1.4.1.2606.20.2.1.2.16
	derivative-Time-Inverter-Pumps-PID OBJECT-TYPE
		SYNTAX Integer32 (-999..999)
		UNITS "N/A"
		MAX-ACCESS read-write
		STATUS current
		DESCRIPTION "Derivative Time Inverter Pumps PID"
		::= { analogObjects 16 }

	-- 1.3.6.1.4.1.2606.20.2.1.2.17
	hysteresis-Thermal-redundance OBJECT-TYPE
		SYNTAX Integer32 (-999..999)
		UNITS "N/A"
		MAX-ACCESS read-write
		STATUS current
		DESCRIPTION "Hysteresis Thermal redundance"
		::= { analogObjects 17 }

	-- 1.3.6.1.4.1.2606.20.2.1.2.18
	min-Opening-3Way-Valve-Hydraulic OBJECT-TYPE
		SYNTAX Integer32 (-999..999)
		UNITS "N/A"
		MAX-ACCESS read-write
		STATUS current
		DESCRIPTION "Min. Opening 3Way Valve Hydraulic"
		::= { analogObjects 18 }

	-- 1.3.6.1.4.1.2606.20.2.1.2.19
	max-Opening-3Way-Valve-Hydraulic OBJECT-TYPE
		SYNTAX Integer32 (-999..999)
		UNITS "N/A"
		MAX-ACCESS read-write
		STATUS current
		DESCRIPTION "Max. Opening 3Way Valve Hydraulic"
		::= { analogObjects 19 }

	-- 1.3.6.1.4.1.2606.20.2.1.2.20
	proportional-Band-3Way-Valve-Hydrauli-PID OBJECT-TYPE
		SYNTAX Integer32 (-999..999)
		UNITS "N/A"
		MAX-ACCESS read-write
		STATUS current
		DESCRIPTION "Proportional Band 3Way Valve Hydraulic PID"
		::= { analogObjects 20 }

	-- 1.3.6.1.4.1.2606.20.2.1.2.21
	setpoint-FCM OBJECT-TYPE
		SYNTAX Integer32 (-999..999)
		UNITS "N/A"
		MAX-ACCESS read-write
		STATUS current
		DESCRIPTION "Setpoint FCM"
		::= { analogObjects 21 }

	-- 1.3.6.1.4.1.2606.20.2.1.2.22
	hysteresis-FCM OBJECT-TYPE
		SYNTAX Integer32 (-999..999)
		UNITS "N/A"
		MAX-ACCESS read-write
		STATUS current
		DESCRIPTION "Hysteresis FCM"
		::= { analogObjects 22 }

	-- 1.3.6.1.4.1.2606.20.2.1.2.23
	max-Out-Speed-FCM OBJECT-TYPE
		SYNTAX Integer32 (-999..999)
		UNITS "N/A"
		MAX-ACCESS read-write
		STATUS current
		DESCRIPTION "Max. Out Speed FCM"
		::= { analogObjects 23 }

	-- 1.3.6.1.4.1.2606.20.2.1.2.24
	min-Out-Speed-FCM OBJECT-TYPE
		SYNTAX Integer32 (-999..999)
		UNITS "N/A"
		MAX-ACCESS read-write
		STATUS current
		DESCRIPTION "Min. Out Speed FCM"
		::= { analogObjects 24 }

	-- 1.3.6.1.4.1.2606.20.2.1.2.25
	hysteresis-Cut-off-FCM OBJECT-TYPE
		SYNTAX Integer32 (-999..999)
		UNITS "N/A"
		MAX-ACCESS read-write
		STATUS current
		DESCRIPTION "Hysteresis Cut-off FCM"
		::= { analogObjects 25 }

	-- 1.3.6.1.4.1.2606.20.2.1.2.26
	max-Pressure-Alarm-FCM OBJECT-TYPE
		SYNTAX Integer32 (-999..999)
		UNITS "N/A"
		MAX-ACCESS read-write
		STATUS current
		DESCRIPTION "Max. Pressure Alarm FCM"
		::= { analogObjects 26 }

	-- 1.3.6.1.4.1.2606.20.2.1.2.27
	hysteresis-Max-Pressure-Alarm-FCM OBJECT-TYPE
		SYNTAX Integer32 (-999..999)
		UNITS "N/A"
		MAX-ACCESS read-write
		STATUS current
		DESCRIPTION "Hysteresis Max.Pressure Alarm FCM"
		::= { analogObjects 27 }

	-- 1.3.6.1.4.1.2606.20.2.1.2.28
	max-Out-FCM OBJECT-TYPE
		SYNTAX Integer32 (-999..999)
		UNITS "N/A"
		MAX-ACCESS read-write
		STATUS current
		DESCRIPTION "Max. Out FCM"
		::= { analogObjects 28 }

	-- 1.3.6.1.4.1.2606.20.2.1.2.29
	min-Pressure-Alarm-FCM OBJECT-TYPE
		SYNTAX Integer32 (-999..999)
		UNITS "N/A"
		MAX-ACCESS read-write
		STATUS current
		DESCRIPTION "Min. Pressure Alarm FCM"
		::= { analogObjects 29 }

	-- 1.3.6.1.4.1.2606.20.2.1.2.30
	hysteresis-Min-Pressure-Alarm-FCM OBJECT-TYPE
		SYNTAX Integer32 (-999..999)
		UNITS "N/A"
		MAX-ACCESS read-write
		STATUS current
		DESCRIPTION "Hysteresis Min.Pressure Alarm FCM"
		::= { analogObjects 30 }

	-- 1.3.6.1.4.1.2606.20.2.1.2.31
	min-Out-FCM OBJECT-TYPE
		SYNTAX Integer32 (-999..999)
		UNITS "N/A"
		MAX-ACCESS read-write
		STATUS current
		DESCRIPTION "Min. Out FCM"
		::= { analogObjects 31 }

	-- 1.3.6.1.4.1.2606.20.2.1.2.32
	delta-Freecooling OBJECT-TYPE
		SYNTAX Integer32 (-999..999)
		UNITS "N/A"
		MAX-ACCESS read-write
		STATUS current
		DESCRIPTION "Delta Freecooling"
		::= { analogObjects 32 }

	-- 1.3.6.1.4.1.2606.20.2.1.2.33
	hysteresis-Freecooling OBJECT-TYPE
		SYNTAX Integer32 (-999..999)
		UNITS "N/A"
		MAX-ACCESS read-write
		STATUS current
		DESCRIPTION "Hysteresis Freecooling"
		::= { analogObjects 33 }

	-- 1.3.6.1.4.1.2606.20.2.1.2.34
	proportional-Band-Freecooling-PID OBJECT-TYPE
		SYNTAX Integer32 (-999..999)
		UNITS "N/A"
		MAX-ACCESS read-write
		STATUS current
		DESCRIPTION "Proportional Band Freecooling PID"
		::= { analogObjects 34 }

	-- 1.3.6.1.4.1.2606.20.2.1.2.35
	offset-Freecooling-PID OBJECT-TYPE
		SYNTAX Integer32 (-999..999)
		UNITS "N/A"
		MAX-ACCESS read-write
		STATUS current
		DESCRIPTION "Offset Freecooling PID"
		::= { analogObjects 35 }

	-- 1.3.6.1.4.1.2606.20.2.1.2.36
	temperature-Overlap-Freecooling OBJECT-TYPE
		SYNTAX Integer32 (-999..999)
		UNITS "N/A"
		MAX-ACCESS read-write
		STATUS current
		DESCRIPTION "Temperature Overlap Freecooling"
		::= { analogObjects 36 }

	-- 1.3.6.1.4.1.2606.20.2.1.2.37
	min-out-freecooling OBJECT-TYPE
		SYNTAX Integer32 (-999..999)
		UNITS "N/A"
		MAX-ACCESS read-write
		STATUS current
		DESCRIPTION "Min. out freecooling"
		::= { analogObjects 37 }

	-- 1.3.6.1.4.1.2606.20.2.1.2.38
	neutral-zone-K-costant OBJECT-TYPE
		SYNTAX Integer32 (-999..999)
		UNITS "N/A"
		MAX-ACCESS read-write
		STATUS current
		DESCRIPTION "Neutral zone K costant"
		::= { analogObjects 38 }

	-- 1.3.6.1.4.1.2606.20.2.1.2.39
	neutral-zone-V-variable OBJECT-TYPE
		SYNTAX Integer32 (-999..999)
		UNITS "N/A"
		MAX-ACCESS read-write
		STATUS current
		DESCRIPTION "Neutral zone V variable"
		::= { analogObjects 39 }

	-- 1.3.6.1.4.1.2606.20.2.1.2.40
	proportional-Band-freecooling-Valve-PID OBJECT-TYPE
		SYNTAX Integer32 (-999..999)
		UNITS "N/A"
		MAX-ACCESS read-write
		STATUS current
		DESCRIPTION "Proportional Band freecooling Valve PID"
		::= { analogObjects 40 }

	-- 1.3.6.1.4.1.2606.20.2.1.2.41
	offset-Freecooling-Valve-PID OBJECT-TYPE
		SYNTAX Integer32 (-999..999)
		UNITS "N/A"
		MAX-ACCESS read-write
		STATUS current
		DESCRIPTION "Offset Freecooling Valve PID"
		::= { analogObjects 41 }

	-- 1.3.6.1.4.1.2606.20.2.1.2.42
	temperature-A-B OBJECT-TYPE
		SYNTAX Integer32 (-999..999)
		UNITS "N/A"
		MAX-ACCESS read-only
		STATUS current
		DESCRIPTION "Temperature A-B"
		::= { analogObjects 42 }

	-- 1.3.6.1.4.1.2606.20.2.1.2.43
	delta-Thermal-Excusion-Freecoling OBJECT-TYPE
		SYNTAX Integer32 (-999..999)
		UNITS "N/A"
		MAX-ACCESS read-write
		STATUS current
		DESCRIPTION "Delta Thermal Excusion Freecoling"
		::= { analogObjects 43 }

	-- 1.3.6.1.4.1.2606.20.2.1.2.44
	hysteresis-Thermal-Excusion-Freecoling OBJECT-TYPE
		SYNTAX Integer32 (-999..999)
		UNITS "N/A"
		MAX-ACCESS read-write
		STATUS current
		DESCRIPTION "hysteresis Thermal Excusion Freecoling"
		::= { analogObjects 44 }

	-- 1.3.6.1.4.1.2606.20.2.1.2.45
	alarm-Setpoint-Static-Pressure-Hydraulic-circuit OBJECT-TYPE
		SYNTAX Integer32 (-999..999)
		UNITS "N/A"
		MAX-ACCESS read-write
		STATUS current
		DESCRIPTION "Alarm Setpoint Static Pressure Hydraulic circuit"
		::= { analogObjects 45 }

	-- 1.3.6.1.4.1.2606.20.2.1.2.46
	warnig-Setpoint-Static-Pressure-Hydraulic-circuit OBJECT-TYPE
		SYNTAX Integer32 (-999..999)
		UNITS "N/A"
		MAX-ACCESS read-write
		STATUS current
		DESCRIPTION "Warnig Setpoint Static Pressure Hydraulic circuit"
		::= { analogObjects 46 }

	-- 1.3.6.1.4.1.2606.20.2.1.2.47
	alarm-Setpoint-Differential-Pressure-Hydraulic-circuit OBJECT-TYPE
		SYNTAX Integer32 (-999..999)
		UNITS "N/A"
		MAX-ACCESS read-write
		STATUS current
		DESCRIPTION "Alarm Setpoint Differential Pressure Hydraulic circuit"
		::= { analogObjects 47 }

	-- 1.3.6.1.4.1.2606.20.2.1.2.48
	alarm-Setpoint-Flow-Rate-Hydraulic-circuit OBJECT-TYPE
		SYNTAX Integer32 (-999..999)
		UNITS "N/A"
		MAX-ACCESS read-write
		STATUS current
		DESCRIPTION "Alarm Setpoint Flow-Rate Hydraulic circuit"
		::= { analogObjects 48 }

	-- 1.3.6.1.4.1.2606.20.2.1.2.50
	tempertaure-Cut-off-FCM OBJECT-TYPE
		SYNTAX Integer32 (-999..999)
		UNITS "N/A"
		MAX-ACCESS read-write
		STATUS current
		DESCRIPTION "Tempertaure Cut-off FCM"
		::= { analogObjects 50 }

	-- 1.3.6.1.4.1.2606.20.2.1.2.59
	set-effective OBJECT-TYPE
		SYNTAX Integer32 (-999..999)
		UNITS "N/A"
		MAX-ACCESS read-only
		STATUS current
		DESCRIPTION "Set-effective"
		::= { analogObjects 59 }

	-- 1.3.6.1.4.1.2606.20.2.1.2.60
	set-fc OBJECT-TYPE
		SYNTAX Integer32 (-999..999)
		UNITS "N/A"
		MAX-ACCESS read-only
		STATUS current
		DESCRIPTION "Freecooling or drycooler Set-point"
		::= { analogObjects 60 }

	-- 1.3.6.1.4.1.2606.20.2.1.2.61
	setpoint-a-us OBJECT-TYPE
		SYNTAX Integer32 (-999..999)
		UNITS "N/A"
		MAX-ACCESS read-write
		STATUS current
		DESCRIPTION "Set-point MAIN"
		::= { analogObjects 61 }

	-- 1.3.6.1.4.1.2606.20.2.1.2.62
	max-setpoint OBJECT-TYPE
		SYNTAX Integer32 (-999..999)
		UNITS "N/A"
		MAX-ACCESS read-write
		STATUS current
		DESCRIPTION "Max.setpoint"
		::= { analogObjects 62 }

	-- 1.3.6.1.4.1.2606.20.2.1.2.63
	min-setpoint OBJECT-TYPE
		SYNTAX Integer32 (-999..999)
		UNITS "N/A"
		MAX-ACCESS read-write
		STATUS current
		DESCRIPTION "Min.setpoint"
		::= { analogObjects 63 }

	-- 1.3.6.1.4.1.2606.20.2.1.2.64
	diff OBJECT-TYPE
		SYNTAX Integer32 (-999..999)
		UNITS "N/A"
		MAX-ACCESS read-write
		STATUS current
		DESCRIPTION "differential"
		::= { analogObjects 64 }

	-- 1.3.6.1.4.1.2606.20.2.1.2.65
	max-diff OBJECT-TYPE
		SYNTAX Integer32 (-999..999)
		UNITS "N/A"
		MAX-ACCESS read-write
		STATUS current
		DESCRIPTION "Max. differential"
		::= { analogObjects 65 }

	-- 1.3.6.1.4.1.2606.20.2.1.2.66
	min-diff OBJECT-TYPE
		SYNTAX Integer32 (-999..999)
		UNITS "N/A"
		MAX-ACCESS read-write
		STATUS current
		DESCRIPTION "Min.Differential"
		::= { analogObjects 66 }

	-- 1.3.6.1.4.1.2606.20.2.1.2.67
	fcs-out OBJECT-TYPE
		SYNTAX Integer32 (0..1000)
		UNITS "N/A"
		MAX-ACCESS read-only
		STATUS current
		DESCRIPTION "Fans speed controller output %"
		::= { analogObjects 67 }

	-- 1.3.6.1.4.1.2606.20.2.1.2.70
	water-temp OBJECT-TYPE
		SYNTAX Integer32 (-999..999)
		UNITS "N/A"
		MAX-ACCESS read-only
		STATUS current
		DESCRIPTION "Tank - Process water temperature"
		::= { analogObjects 70 }

	-- 1.3.6.1.4.1.2606.20.2.1.2.71
	temp-inlet OBJECT-TYPE
		SYNTAX Integer32 (-999..999)
		UNITS "N/A"
		MAX-ACCESS read-only
		STATUS current
		DESCRIPTION "Water inlet temperature"
		::= { analogObjects 71 }

	-- 1.3.6.1.4.1.2606.20.2.1.2.72
	temp-outlet OBJECT-TYPE
		SYNTAX Integer32 (-999..999)
		UNITS "N/A"
		MAX-ACCESS read-only
		STATUS current
		DESCRIPTION "Water outlet temperature"
		::= { analogObjects 72 }

	-- 1.3.6.1.4.1.2606.20.2.1.2.73
	flow-value OBJECT-TYPE
		SYNTAX Integer32 (-9999..9999)
		UNITS "N/A"
		MAX-ACCESS read-only
		STATUS current
		DESCRIPTION "Flow rate value"
		::= { analogObjects 73 }

	-- 1.3.6.1.4.1.2606.20.2.1.2.74
	amp-value OBJECT-TYPE
		SYNTAX Integer32 (-9999..9999)
		UNITS "N/A"
		MAX-ACCESS read-only
		STATUS current
		DESCRIPTION "Current cunsumption"
		::= { analogObjects 74 }

	-- 1.3.6.1.4.1.2606.20.2.1.2.75
	ta-probe-temp-1 OBJECT-TYPE
		SYNTAX Integer32 (-999..999)
		UNITS "N/A"
		MAX-ACCESS read-only
		STATUS current
		DESCRIPTION "Antifreeze 1 temperature monitoring "
		::= { analogObjects 75 }

	-- 1.3.6.1.4.1.2606.20.2.1.2.76
	ta-probe-temp-2 OBJECT-TYPE
		SYNTAX Integer32 (-999..999)
		UNITS "N/A"
		MAX-ACCESS read-only
		STATUS current
		DESCRIPTION "Antifreeze 2 temperature monitoring"
		::= { analogObjects 76 }

	-- 1.3.6.1.4.1.2606.20.2.1.2.77
	pressione1 OBJECT-TYPE
		SYNTAX Integer32 (-999..999)
		UNITS "N/A"
		MAX-ACCESS read-only
		STATUS current
		DESCRIPTION "Condensation pressure circuit 1"
		::= { analogObjects 77 }

	-- 1.3.6.1.4.1.2606.20.2.1.2.78
	pressione2 OBJECT-TYPE
		SYNTAX Integer32 (-999..999)
		UNITS "N/A"
		MAX-ACCESS read-only
		STATUS current
		DESCRIPTION "Condensation pressure circuit 2"
		::= { analogObjects 78 }

	-- 1.3.6.1.4.1.2606.20.2.1.2.79
	pump-sp-press OBJECT-TYPE
		SYNTAX Integer32 (-999..999)
		UNITS "N/A"
		MAX-ACCESS read-only
		STATUS current
		DESCRIPTION "Pump discharge pressure "
		::= { analogObjects 79 }

	-- 1.3.6.1.4.1.2606.20.2.1.2.80
	p-wat2 OBJECT-TYPE
		SYNTAX Integer32 (-999..999)
		UNITS "N/A"
		MAX-ACCESS read-only
		STATUS current
		DESCRIPTION "Pump suction or static pressure"
		::= { analogObjects 80 }

	-- 1.3.6.1.4.1.2606.20.2.1.2.81
	temp-amb OBJECT-TYPE
		SYNTAX Integer32 (-999..999)
		UNITS "N/A"
		MAX-ACCESS read-only
		STATUS current
		DESCRIPTION "Ambient temperature"
		::= { analogObjects 81 }

	-- 1.3.6.1.4.1.2606.20.2.1.2.82
	temp-fc OBJECT-TYPE
		SYNTAX Integer32 (-999..999)
		UNITS "N/A"
		MAX-ACCESS read-only
		STATUS current
		DESCRIPTION "Inlet - freecooling temperature"
		::= { analogObjects 82 }

	-- 1.3.6.1.4.1.2606.20.2.1.2.90
	pp1 OBJECT-TYPE
		SYNTAX Integer32 (0..100)
		UNITS "N/A"
		MAX-ACCESS read-only
		STATUS current
		DESCRIPTION "Pump 1 speed"
		::= { analogObjects 90 }

	-- 1.3.6.1.4.1.2606.20.2.1.2.91
	pp2 OBJECT-TYPE
		SYNTAX Integer32 (0..100)
		UNITS "N/A"
		MAX-ACCESS read-only
		STATUS current
		DESCRIPTION "Pump 2 speed"
		::= { analogObjects 91 }


	-- 1.3.6.1.4.1.2606.20.2.1.2.100
	cooling-capacity OBJECT-TYPE
		SYNTAX Integer32 (0..9999)
		UNITS "N/A"
		MAX-ACCESS read-only
		STATUS current
		DESCRIPTION "Cooling Capacity"
		::= { analogObjects 100 }

	-- 1.3.6.1.4.1.2606.20.2.1.2.101
	freecooling-capacity OBJECT-TYPE
		SYNTAX Integer32 (0..9999)
		UNITS "N/A"
		MAX-ACCESS read-only
		STATUS current
		DESCRIPTION "FreeCooling Capacity"
		::= { analogObjects 101 }

	-- 1.3.6.1.4.1.2606.20.2.1.2.102
	total-capacity OBJECT-TYPE
		SYNTAX Integer32 (0..9999)
		UNITS "N/A"
		MAX-ACCESS read-only
		STATUS current
		DESCRIPTION "TotalCooling Capacity"
		::= { analogObjects 102 }



--
-- INTEGER VARIABLES
--

	-- 1.3.6.1.4.1.2606.20.2.1.3
	integerObjects OBJECT IDENTIFIER	::= { rittal-IT-Chiller 3 }

	-- 1.3.6.1.4.1.2606.20.2.1.3.6
	ip-Address1 OBJECT-TYPE
		SYNTAX Integer32 (1..255)
		UNITS "N/A"
		MAX-ACCESS read-only
		STATUS current
		DESCRIPTION "IP Address 1 (XXX.xxx.xxx.xxx)"
		::= { integerObjects 6 }

	-- 1.3.6.1.4.1.2606.20.2.1.3.7
	ip-Address2 OBJECT-TYPE
		SYNTAX Integer32 (1..255)
		UNITS "N/A"
		MAX-ACCESS read-only
		STATUS current
		DESCRIPTION "IP Address 2 (xxx.XXX.xxx.xxx)"
		::= { integerObjects 7 }

	-- 1.3.6.1.4.1.2606.20.2.1.3.8
	ip-Address3 OBJECT-TYPE
		SYNTAX Integer32 (1..255)
		UNITS "N/A"
		MAX-ACCESS read-only
		STATUS current
		DESCRIPTION "IP Address 3 (xxx.xxx.XXX.xxx)"
		::= { integerObjects 8 }

	-- 1.3.6.1.4.1.2606.20.2.1.3.9
	ip-Address4 OBJECT-TYPE
		SYNTAX Integer32 (1..255)
		UNITS "N/A"
		MAX-ACCESS read-only
		STATUS current
		DESCRIPTION "IP Address 4 (xxx.xxx.xxx.XXX)"
		::= { integerObjects 9 }

	-- 1.3.6.1.4.1.2606.20.2.1.3.10
	netMask OBJECT-TYPE
		SYNTAX Integer32 (8..32)
		UNITS "N/A"
		MAX-ACCESS read-only
		STATUS current
		DESCRIPTION "NetMask 8-16-24-32"
		::= { integerObjects 10 }

	-- 1.3.6.1.4.1.2606.20.2.1.3.11
	gateway1 OBJECT-TYPE
		SYNTAX Integer32 (1..255)
		UNITS "N/A"
		MAX-ACCESS read-only
		STATUS current
		DESCRIPTION "Gateway 1 (XXX.xxx.xxx.xxx)"
		::= { integerObjects 11 }

	-- 1.3.6.1.4.1.2606.20.2.1.3.12
	gateway2 OBJECT-TYPE
		SYNTAX Integer32 (1..255)
		UNITS "N/A"
		MAX-ACCESS read-only
		STATUS current
		DESCRIPTION "Gateway 2 (xxx.XXX.xxx.xxx)"
		::= { integerObjects 12 }

	-- 1.3.6.1.4.1.2606.20.2.1.3.13
	gateway3 OBJECT-TYPE
		SYNTAX Integer32 (1..255)
		UNITS "N/A"
		MAX-ACCESS read-only
		STATUS current
		DESCRIPTION "Gateway 3 (xxx.xxx.XXX.xxx)"
		::= { integerObjects 13 }

	-- 1.3.6.1.4.1.2606.20.2.1.3.14
	gateway4 OBJECT-TYPE
		SYNTAX Integer32 (1..255)
		UNITS "N/A"
		MAX-ACCESS read-only
		STATUS current
		DESCRIPTION "Gateway 4 (xxx.xxx.xxx.XXX)"
		::= { integerObjects 14 }

	-- 1.3.6.1.4.1.2606.20.2.1.3.15
	dns1-1 OBJECT-TYPE
		SYNTAX Integer32 (1..255)
		UNITS "N/A"
		MAX-ACCESS read-only
		STATUS current
		DESCRIPTION "DNS (1) 1 (XXX.xxx.xxx.xxx)"
		::= { integerObjects 15 }

	-- 1.3.6.1.4.1.2606.20.2.1.3.16
	dns1-2 OBJECT-TYPE
		SYNTAX Integer32 (1..255)
		UNITS "N/A"
		MAX-ACCESS read-only
		STATUS current
		DESCRIPTION "DNS (1) 2 (xxx.XXX.xxx.xxx)"
		::= { integerObjects 16 }

	-- 1.3.6.1.4.1.2606.20.2.1.3.17
	dns1-3 OBJECT-TYPE
		SYNTAX Integer32 (1..255)
		UNITS "N/A"
		MAX-ACCESS read-only
		STATUS current
		DESCRIPTION "DNS (1) 3 (xxx.xxx.XXX.xxx)"
		::= { integerObjects 17 }

	-- 1.3.6.1.4.1.2606.20.2.1.3.18
	dns1-4 OBJECT-TYPE
		SYNTAX Integer32 (1..255)
		UNITS "N/A"
		MAX-ACCESS read-only
		STATUS current
		DESCRIPTION "DNS (1) 4 (xxx.xxx.xxx.XXX)"
		::= { integerObjects 18 }

	-- 1.3.6.1.4.1.2606.20.2.1.3.19
	dns2-1 OBJECT-TYPE
		SYNTAX Integer32 (1..255)
		UNITS "N/A"
		MAX-ACCESS read-only
		STATUS current
		DESCRIPTION "DNS (2) 1 (XXX.xxx.xxx.xxx)"
		::= { integerObjects 19 }

	-- 1.3.6.1.4.1.2606.20.2.1.3.20
	dns2-2 OBJECT-TYPE
		SYNTAX Integer32 (1..255)
		UNITS "N/A"
		MAX-ACCESS read-only
		STATUS current
		DESCRIPTION "DNS (2) 2 (xxx.XXX.xxx.xxx)"
		::= { integerObjects 20 }

	-- 1.3.6.1.4.1.2606.20.2.1.3.21
	dns2-3 OBJECT-TYPE
		SYNTAX Integer32 (1..255)
		UNITS "N/A"
		MAX-ACCESS read-only
		STATUS current
		DESCRIPTION "DNS (2) 3 (xxx.xxx.XXX.xxx)"
		::= { integerObjects 21 }

	-- 1.3.6.1.4.1.2606.20.2.1.3.22
	dns2-4 OBJECT-TYPE
		SYNTAX Integer32 (1..255)
		UNITS "N/A"
		MAX-ACCESS read-only
		STATUS current
		DESCRIPTION "DNS (2) 4 (xxx.xxx.xxx.XXX)"
		::= { integerObjects 22 }

	-- 1.3.6.1.4.1.2606.20.2.1.3.26
	ip-Address1-Out OBJECT-TYPE
		SYNTAX Integer32 (1..255)
		UNITS "N/A"
		MAX-ACCESS read-only
		STATUS current
		DESCRIPTION "IP Address Out 1 (XXX.xxx.xxx.xxx)"
		::= { integerObjects 26 }

	-- 1.3.6.1.4.1.2606.20.2.1.3.27
	ip-Address2-Out OBJECT-TYPE
		SYNTAX Integer32 (1..255)
		UNITS "N/A"
		MAX-ACCESS read-only
		STATUS current
		DESCRIPTION "IP Address Out 2 (xxx.XXX.xxx.xxx)"
		::= { integerObjects 27 }

	-- 1.3.6.1.4.1.2606.20.2.1.3.28
	ip-Address3-Out OBJECT-TYPE
		SYNTAX Integer32 (1..255)
		UNITS "N/A"
		MAX-ACCESS read-only
		STATUS current
		DESCRIPTION "IP Address Out 3 (xxx.xxx.XXX.xxx)"
		::= { integerObjects 28 }

	-- 1.3.6.1.4.1.2606.20.2.1.3.29
	ip-Address4-Out OBJECT-TYPE
		SYNTAX Integer32 (1..255)
		UNITS "N/A"
		MAX-ACCESS read-only
		STATUS current
		DESCRIPTION "IP Address Out 4 (xxx.xxx.xxx.XXX)"
		::= { integerObjects 29 }

	-- 1.3.6.1.4.1.2606.20.2.1.3.30
	starting-delay-Second-Pump OBJECT-TYPE
		SYNTAX Integer32 (0..99)
		UNITS "N/A"
		MAX-ACCESS read-write
		STATUS current
		DESCRIPTION "Starting delay Second Pump"
		::= { integerObjects 30 }

	-- 1.3.6.1.4.1.2606.20.2.1.3.31
	starting-delay-btw-Pump-Compressor OBJECT-TYPE
		SYNTAX Integer32 (0..32767)
		UNITS "N/A"
		MAX-ACCESS read-write
		STATUS current
		DESCRIPTION "Starting delay btw Pump - Compressor"
		::= { integerObjects 31 }

	-- 1.3.6.1.4.1.2606.20.2.1.3.32
	overlap-time-Pumps OBJECT-TYPE
		SYNTAX Integer32 (0..999)
		UNITS "N/A"
		MAX-ACCESS read-write
		STATUS current
		DESCRIPTION "Overlap time Pumps"
		::= { integerObjects 32 }

	-- 1.3.6.1.4.1.2606.20.2.1.3.33
	working-time-Pumps OBJECT-TYPE
		SYNTAX Integer32 (1..9999)
		UNITS "N/A"
		MAX-ACCESS read-write
		STATUS current
		DESCRIPTION "Working time Pumps"
		::= { integerObjects 33 }

	-- 1.3.6.1.4.1.2606.20.2.1.3.34
	running-time-Chillers OBJECT-TYPE
		SYNTAX Integer32 (0..32767)
		UNITS "N/A"
		MAX-ACCESS read-write
		STATUS current
		DESCRIPTION "Running time Chillers"
		::= { integerObjects 34 }

	-- 1.3.6.1.4.1.2606.20.2.1.3.35
	overlap-time-Chillers OBJECT-TYPE
		SYNTAX Integer32 (0..32767)
		UNITS "N/A"
		MAX-ACCESS read-write
		STATUS current
		DESCRIPTION "Overlap time Chillers"
		::= { integerObjects 35 }

	-- 1.3.6.1.4.1.2606.20.2.1.3.36
	n-chillers-Max OBJECT-TYPE
		SYNTAX Integer32 (1..8)
		UNITS "N/A"
		MAX-ACCESS read-write
		STATUS current
		DESCRIPTION "N chillers Max"
		::= { integerObjects 36 }

	-- 1.3.6.1.4.1.2606.20.2.1.3.37
	n-chillers-ON OBJECT-TYPE
		SYNTAX Integer32 (1..8)
		UNITS "N/A"
		MAX-ACCESS read-write
		STATUS current
		DESCRIPTION "N chillers ON"
		::= { integerObjects 37 }

	-- 1.3.6.1.4.1.2606.20.2.1.3.38
	n-pumps-ON OBJECT-TYPE
		SYNTAX Integer32 (1..8)
		UNITS "N/A"
		MAX-ACCESS read-write
		STATUS current
		DESCRIPTION "N pumps ON"
		::= { integerObjects 38 }

	-- 1.3.6.1.4.1.2606.20.2.1.3.39
	time-Enable-Pumps-Chiller-Offline OBJECT-TYPE
		SYNTAX Integer32 (0..999)
		UNITS "N/A"
		MAX-ACCESS read-write
		STATUS current
		DESCRIPTION "Time Enable Pumps - Chiller Offline"
		::= { integerObjects 39 }

	-- 1.3.6.1.4.1.2606.20.2.1.3.40
	time-Running-Pumps-Chiller-Offline OBJECT-TYPE
		SYNTAX Integer32 (0..9999)
		UNITS "N/A"
		MAX-ACCESS read-write
		STATUS current
		DESCRIPTION "Time Running Pumps - Chiller Offline"
		::= { integerObjects 40 }

	-- 1.3.6.1.4.1.2606.20.2.1.3.41
	integral-Time-3Way-Valve-Hydraulic-PID OBJECT-TYPE
		SYNTAX Integer32 (0..999)
		UNITS "N/A"
		MAX-ACCESS read-write
		STATUS current
		DESCRIPTION "Integral Time 3Way Valve Hydraulic (PID)"
		::= { integerObjects 41 }

	-- 1.3.6.1.4.1.2606.20.2.1.3.42
	derivative-Time-3Way-Valve-Hydraulic-PID OBJECT-TYPE
		SYNTAX Integer32 (0..999)
		UNITS "N/A"
		MAX-ACCESS read-write
		STATUS current
		DESCRIPTION "Derivative Time 3Way Valve Hydraulic (PID)"
		::= { integerObjects 42 }

	-- 1.3.6.1.4.1.2606.20.2.1.3.43
	output-Address-3Way-Valve-Hydraulic OBJECT-TYPE
		SYNTAX Integer32 (0..6)
		UNITS "N/A"
		MAX-ACCESS read-write
		STATUS current
		DESCRIPTION "Output Address 3Way Valve Hydraulic"
		::= { integerObjects 43 }

	-- 1.3.6.1.4.1.2606.20.2.1.3.44
	time-Speed-Up-FCM OBJECT-TYPE
		SYNTAX Integer32 (0..99)
		UNITS "N/A"
		MAX-ACCESS read-write
		STATUS current
		DESCRIPTION "Time Speed-Up (FCM)"
		::= { integerObjects 44 }

	-- 1.3.6.1.4.1.2606.20.2.1.3.45
	time-Soft-Start-FCM OBJECT-TYPE
		SYNTAX Integer32 (0..100)
		UNITS "N/A"
		MAX-ACCESS read-write
		STATUS current
		DESCRIPTION "Time Soft-Start (FCM)"
		::= { integerObjects 45 }

	-- 1.3.6.1.4.1.2606.20.2.1.3.47
	delay-Freecooling OBJECT-TYPE
		SYNTAX Integer32 (0..9999)
		UNITS "N/A"
		MAX-ACCESS read-write
		STATUS current
		DESCRIPTION "Delay Freecooling"
		::= { integerObjects 47 }

	-- 1.3.6.1.4.1.2606.20.2.1.3.48
	integral-Time-Freeccoling-PID OBJECT-TYPE
		SYNTAX Integer32 (0..999)
		UNITS "N/A"
		MAX-ACCESS read-write
		STATUS current
		DESCRIPTION "Integral Time Freeccoling (PID)"
		::= { integerObjects 48 }

	-- 1.3.6.1.4.1.2606.20.2.1.3.49
	derivative-Time-Freeccoling-PID OBJECT-TYPE
		SYNTAX Integer32 (0..999)
		UNITS "N/A"
		MAX-ACCESS read-write
		STATUS current
		DESCRIPTION "Derivative Time Freeccoling (PID)"
		::= { integerObjects 49 }

	-- 1.3.6.1.4.1.2606.20.2.1.3.50
	time-Min-On-Freecooling-Chiller-timing OBJECT-TYPE
		SYNTAX Integer32 (0..32767)
		UNITS "N/A"
		MAX-ACCESS read-write
		STATUS current
		DESCRIPTION "Time Min. On (Freecooling - Chiller timing)"
		::= { integerObjects 50 }

	-- 1.3.6.1.4.1.2606.20.2.1.3.51
	time-Min-Off-Freecooling-Chiller-timing OBJECT-TYPE
		SYNTAX Integer32 (0..32767)
		UNITS "N/A"
		MAX-ACCESS read-write
		STATUS current
		DESCRIPTION "Time Min. Off (Freecooling - Chiller timing)"
		::= { integerObjects 51 }

	-- 1.3.6.1.4.1.2606.20.2.1.3.52
	time-Min-Different-Freecooling-Chiller-timing OBJECT-TYPE
		SYNTAX Integer32 (0..32767)
		UNITS "N/A"
		MAX-ACCESS read-write
		STATUS current
		DESCRIPTION "Time Min. Different (Freecooling - Chiller timing)"
		::= { integerObjects 52 }

	-- 1.3.6.1.4.1.2606.20.2.1.3.53
	time-Min-Same-Freecooling-Chiller-timing OBJECT-TYPE
		SYNTAX Integer32 (0..32767)
		UNITS "N/A"
		MAX-ACCESS read-write
		STATUS current
		DESCRIPTION "Time Min. Same (Freecooling - Chiller timing)"
		::= { integerObjects 53 }

	-- 1.3.6.1.4.1.2606.20.2.1.3.54
	integral-Time-Freeccoling-Valve-PID OBJECT-TYPE
		SYNTAX Integer32 (0..999)
		UNITS "N/A"
		MAX-ACCESS read-write
		STATUS current
		DESCRIPTION "Integral Time Freeccoling Valve (PID)"
		::= { integerObjects 54 }

	-- 1.3.6.1.4.1.2606.20.2.1.3.55
	derivative-Time-Freeccoling-Valve-PID OBJECT-TYPE
		SYNTAX Integer32 (0..999)
		UNITS "N/A"
		MAX-ACCESS read-write
		STATUS current
		DESCRIPTION "Derivative Time Freeccoling Valve (PID)"
		::= { integerObjects 55 }

	-- 1.3.6.1.4.1.2606.20.2.1.3.56
	output-Address-Valve-Freecooling OBJECT-TYPE
		SYNTAX Integer32 (0..6)
		UNITS "N/A"
		MAX-ACCESS read-write
		STATUS current
		DESCRIPTION "Output Address Valve Freecooling"
		::= { integerObjects 56 }

	-- 1.3.6.1.4.1.2606.20.2.1.3.57
	delay-Freecooling-Thermal-Exclusion OBJECT-TYPE
		SYNTAX Integer32 (0..999)
		UNITS "N/A"
		MAX-ACCESS read-write
		STATUS current
		DESCRIPTION "Delay Freecoolimg Thermal Exclusion"
		::= { integerObjects 57 }

	-- 1.3.6.1.4.1.2606.20.2.1.3.58
	n-of-alarm-External-Dry-Cooler OBJECT-TYPE
		SYNTAX Integer32 (0..9)
		UNITS "N/A"
		MAX-ACCESS read-write
		STATUS current
		DESCRIPTION "N of alarm (External Dry-Cooler)"
		::= { integerObjects 58 }

	-- 1.3.6.1.4.1.2606.20.2.1.3.59
	delay-Alarm-Static-Pressure OBJECT-TYPE
		SYNTAX Integer32 (0..99)
		UNITS "N/A"
		MAX-ACCESS read-write
		STATUS current
		DESCRIPTION "Delay Alarm (Static Pressure)"
		::= { integerObjects 59 }

	-- 1.3.6.1.4.1.2606.20.2.1.3.60
	n-of-Alarm-Static-Pressure OBJECT-TYPE
		SYNTAX Integer32 (1..10)
		UNITS "N/A"
		MAX-ACCESS read-write
		STATUS current
		DESCRIPTION "N of Alarm (Static Pressure)"
		::= { integerObjects 60 }

	-- 1.3.6.1.4.1.2606.20.2.1.3.61
	delay-Warning-Static-Pressure OBJECT-TYPE
		SYNTAX Integer32 (0..99)
		UNITS "N/A"
		MAX-ACCESS read-write
		STATUS current
		DESCRIPTION "Delay Warning (Static Pressure)"
		::= { integerObjects 61 }

	-- 1.3.6.1.4.1.2606.20.2.1.3.62
	n-of-Warning-Static-Pressure OBJECT-TYPE
		SYNTAX Integer32 (1..10)
		UNITS "N/A"
		MAX-ACCESS read-write
		STATUS current
		DESCRIPTION "N of Warning (Static Pressure)"
		::= { integerObjects 62 }

	-- 1.3.6.1.4.1.2606.20.2.1.3.63
	n-of-Alarm-Differential-Pressure OBJECT-TYPE
		SYNTAX Integer32 (1..10)
		UNITS "N/A"
		MAX-ACCESS read-write
		STATUS current
		DESCRIPTION "N of Alarm (Differential Pressure)"
		::= { integerObjects 63 }

	-- 1.3.6.1.4.1.2606.20.2.1.3.64
	priming-Time-Hydraulic-Pressure OBJECT-TYPE
		SYNTAX Integer32 (0..99)
		UNITS "N/A"
		MAX-ACCESS read-write
		STATUS current
		DESCRIPTION "Priming Time (Hydraulic Pressure)"
		::= { integerObjects 64 }

	-- 1.3.6.1.4.1.2606.20.2.1.3.65
	delay-priming-Time-Hydraulic-Pressure OBJECT-TYPE
		SYNTAX Integer32 (0..99)
		UNITS "N/A"
		MAX-ACCESS read-write
		STATUS current
		DESCRIPTION "Delay Priming Time (Hydraulic Pressure)"
		::= { integerObjects 65 }

	-- 1.3.6.1.4.1.2606.20.2.1.3.66
	output-Address-Alarm-Static-Pressure OBJECT-TYPE
		SYNTAX Integer32 (0..18)
		UNITS "N/A"
		MAX-ACCESS read-write
		STATUS current
		DESCRIPTION "Output Address Alarm (Static Pressure)"
		::= { integerObjects 66 }

	-- 1.3.6.1.4.1.2606.20.2.1.3.67
	n-of-Alarm-Flow-Rate OBJECT-TYPE
		SYNTAX Integer32 (1..10)
		UNITS "N/A"
		MAX-ACCESS read-write
		STATUS current
		DESCRIPTION "N of Alarm (Flow Rate)"
		::= { integerObjects 67 }

	-- 1.3.6.1.4.1.2606.20.2.1.3.68
	priming-Time-Flow-Rate OBJECT-TYPE
		SYNTAX Integer32 (0..99)
		UNITS "N/A"
		MAX-ACCESS read-write
		STATUS current
		DESCRIPTION "Priming Time (Flow Rate)"
		::= { integerObjects 68 }

	-- 1.3.6.1.4.1.2606.20.2.1.3.69
	delay-priming-Time-Flow-Rate OBJECT-TYPE
		SYNTAX Integer32 (0..99)
		UNITS "N/A"
		MAX-ACCESS read-write
		STATUS current
		DESCRIPTION "Delay Priming Time (Flow Rate)"
		::= { integerObjects 69 }

	-- 1.3.6.1.4.1.2606.20.2.1.3.70
	bms-address-IDENT OBJECT-TYPE
		SYNTAX Integer32 (1..200)
		UNITS "N/A"
		MAX-ACCESS read-only
		STATUS current
		DESCRIPTION "BMS address (IDENT)"
		::= { integerObjects 70 }

	-- 1.3.6.1.4.1.2606.20.2.1.3.99
	chiller-name0 OBJECT-TYPE
		SYNTAX Integer32 (0..9999)
		UNITS "N/A"
		MAX-ACCESS read-only
		STATUS current
		DESCRIPTION "Chiller Model - Article Number - 0"
		::= { integerObjects 99 }

	-- 1.3.6.1.4.1.2606.20.2.1.3.100
	chiller-name1 OBJECT-TYPE
		SYNTAX Integer32 (0..999)
		UNITS "N/A"
		MAX-ACCESS read-only
		STATUS current
		DESCRIPTION "Chiller Model - Article Number - 1"
		::= { integerObjects 100 }

	-- 1.3.6.1.4.1.2606.20.2.1.3.123
	current-day OBJECT-TYPE
		SYNTAX Integer32 (1..31)
		UNITS "N/A"
		MAX-ACCESS read-only
		STATUS current
		DESCRIPTION "Current Day"
		::= { integerObjects 123 }

	-- 1.3.6.1.4.1.2606.20.2.1.3.124
	current-month OBJECT-TYPE
		SYNTAX Integer32 (1..12)
		UNITS "N/A"
		MAX-ACCESS read-only
		STATUS current
		DESCRIPTION "Current Month"
		::= { integerObjects 124 }

	-- 1.3.6.1.4.1.2606.20.2.1.3.125
	current-year OBJECT-TYPE
		SYNTAX Integer32 (0..99)
		UNITS "N/A"
		MAX-ACCESS read-only
		STATUS current
		DESCRIPTION "Current Year"
		::= { integerObjects 125 }

	-- 1.3.6.1.4.1.2606.20.2.1.3.126
	current-hour OBJECT-TYPE
		SYNTAX Integer32 (0..23)
		UNITS "N/A"
		MAX-ACCESS read-only
		STATUS current
		DESCRIPTION "Current Hour"
		::= { integerObjects 126 }

	-- 1.3.6.1.4.1.2606.20.2.1.3.127
	current-minute OBJECT-TYPE
		SYNTAX Integer32 (0..59)
		UNITS "N/A"
		MAX-ACCESS read-only
		STATUS current
		DESCRIPTION "Current Minute"
		::= { integerObjects 127 }

	-- 1.3.6.1.4.1.2606.20.2.1.3.150
	chiller-mode-operation OBJECT-TYPE
		SYNTAX Integer32 (0..4)
		UNITS "N/A"
		MAX-ACCESS read-only
		STATUS current
		DESCRIPTION "Chiller mode operation"
		::= { integerObjects 150 }



--
-- Trap definitions
--

	-- 1.3.6.1.4.1.2606.20.2.1.120
	trapObjects OBJECT IDENTIFIER		::= { rittal-IT-Chiller 120 }


	-- 1.3.6.1.4.1.2606.20.2.1.120.1
	-- high-pressure-switch-1-alarm NOTIFICATION-TYPE
	trap1	NOTIFICATION-TYPE
		STATUS current
		DESCRIPTION "High pressure switch 1 alarm"
		::= { trapObjects 1 }

	-- 1.3.6.1.4.1.2606.20.2.1.120.2
	-- high-pressure-switch-2-alarm NOTIFICATION-TYPE
	trap2	NOTIFICATION-TYPE
		STATUS current
		DESCRIPTION "High pressure switch 2 alarm"
		::= { trapObjects 2 }

	-- 1.3.6.1.4.1.2606.20.2.1.120.3
	-- low-pressure-switch-1-alarm NOTIFICATION-TYPE
	trap3	NOTIFICATION-TYPE
		STATUS current
		DESCRIPTION "Low pressure switch 1 alarm"
		::= { trapObjects 3 }

	-- 1.3.6.1.4.1.2606.20.2.1.120.4
	-- low-pressure-switch-2-alarm NOTIFICATION-TYPE
	trap4	NOTIFICATION-TYPE
		STATUS current
		DESCRIPTION "Low pressure switch 2 alarm"
		::= { trapObjects 4 }

	-- 1.3.6.1.4.1.2606.20.2.1.120.5
	-- antifreeze-alarm NOTIFICATION-TYPE
	--trap5	NOTIFICATION-TYPE
	--	STATUS current
	--	DESCRIPTION "Antifreeze alarm"
	--	::= { trapObjects 5 }

	-- 1.3.6.1.4.1.2606.20.2.1.120.6
	-- water-level-alarm NOTIFICATION-TYPE
	trap6	NOTIFICATION-TYPE
		STATUS current
		DESCRIPTION "Water level alarm"
		::= { trapObjects 6 }

	-- 1.3.6.1.4.1.2606.20.2.1.120.7
	-- digital-input-7 NOTIFICATION-TYPE
	--trap7	NOTIFICATION-TYPE
	--	STATUS current
	--	DESCRIPTION "Digital input 7"
	--	::= { trapObjects 7 }

	-- 1.3.6.1.4.1.2606.20.2.1.120.8
	-- flow-switch-alarm NOTIFICATION-TYPE
	trap8	NOTIFICATION-TYPE
		STATUS current
		DESCRIPTION "Flow switch alarm"
		::= { trapObjects 8 }

	-- 1.3.6.1.4.1.2606.20.2.1.120.9
	-- water-static-pressure-alarm NOTIFICATION-TYPE
	trap9	NOTIFICATION-TYPE
		STATUS current
		DESCRIPTION "Water static pressure alarm"
		::= { trapObjects 9 }

	-- 1.3.6.1.4.1.2606.20.2.1.120.10
	-- water-static-pressure-warning NOTIFICATION-TYPE
	trap10	NOTIFICATION-TYPE
		STATUS current
		DESCRIPTION "Water static pressure warning"
		::= { trapObjects 10 }

	-- 1.3.6.1.4.1.2606.20.2.1.120.11
	-- flow-rate-alarm NOTIFICATION-TYPE
	trap11	NOTIFICATION-TYPE
		STATUS current
		DESCRIPTION "Flow rate alarm"
		::= { trapObjects 11 }

	-- 1.3.6.1.4.1.2606.20.2.1.120.12
	-- overload-compressor1-circuit1-alarm NOTIFICATION-TYPE
	trap12	NOTIFICATION-TYPE
		STATUS current
		DESCRIPTION "Overload compressor 1 circuit 1 alarm"
		::= { trapObjects 12 }

	-- 1.3.6.1.4.1.2606.20.2.1.120.13
	-- overload-compressor2-circuit1-alarm NOTIFICATION-TYPE
	trap13	NOTIFICATION-TYPE
		STATUS current
		DESCRIPTION "Overload compressor 2 circuit 1 alarm"
		::= { trapObjects 13 }

	-- 1.3.6.1.4.1.2606.20.2.1.120.14
	-- overload-compressor3-circuit1-alarm NOTIFICATION-TYPE
	trap14	NOTIFICATION-TYPE
		STATUS current
		DESCRIPTION "Overload compressor 3 circuit 1 alarm"
		::= { trapObjects 14 }

	-- 1.3.6.1.4.1.2606.20.2.1.120.15
	-- overload-compressor1-circuit2-alarm NOTIFICATION-TYPE
	trap15	NOTIFICATION-TYPE
		STATUS current
		DESCRIPTION "Overload compressor 1 circuit 2 alarm"
		::= { trapObjects 15 }

	-- 1.3.6.1.4.1.2606.20.2.1.120.16
	-- overload-compressor2-circuit2-alarm NOTIFICATION-TYPE
	trap16	NOTIFICATION-TYPE
		STATUS current
		DESCRIPTION "Overload compressor 2 circuit 2 alarm"
		::= { trapObjects 16 }

	-- 1.3.6.1.4.1.2606.20.2.1.120.17
	-- overload-compressor3-circuit2-alarm NOTIFICATION-TYPE
	trap17	NOTIFICATION-TYPE
		STATUS current
		DESCRIPTION "Overload compressor 3 circuit 2 alarm"
		::= { trapObjects 17 }

	-- 1.3.6.1.4.1.2606.20.2.1.120.18
	-- overload-fans-circuit1 NOTIFICATION-TYPE
	trap18	NOTIFICATION-TYPE
		STATUS current
		DESCRIPTION "Overload fans circuit 1"
		::= { trapObjects 18 }

	-- 1.3.6.1.4.1.2606.20.2.1.120.19
	-- overload-fans-circuit2 NOTIFICATION-TYPE
	trap19	NOTIFICATION-TYPE
		STATUS current
		DESCRIPTION "Overload fans circuit 2"
		::= { trapObjects 19 }

	-- 1.3.6.1.4.1.2606.20.2.1.120.20
	-- overload-fan1-circuit1-alarm NOTIFICATION-TYPE
	trap20	NOTIFICATION-TYPE
		STATUS current
		DESCRIPTION "Overload fan 1 circuit 1 alarm"
		::= { trapObjects 20 }

	-- 1.3.6.1.4.1.2606.20.2.1.120.21
	-- overload-fan2-circuit1-alarm NOTIFICATION-TYPE
	trap21	NOTIFICATION-TYPE
		STATUS current
		DESCRIPTION "Overload fan 2 circuit 1 alarm"
		::= { trapObjects 21 }

	-- 1.3.6.1.4.1.2606.20.2.1.120.22
	-- overload-fan3-circuit1-alarm NOTIFICATION-TYPE
	trap22	NOTIFICATION-TYPE
		STATUS current
		DESCRIPTION "Overload fan 3 circuit 1 alarm"
		::= { trapObjects 22 }

	-- 1.3.6.1.4.1.2606.20.2.1.120.23
	-- overload-fan4-circuit1-alarm NOTIFICATION-TYPE
	trap23	NOTIFICATION-TYPE
		STATUS current
		DESCRIPTION "Overload fan 4 circuit 1 alarm"
		::= { trapObjects 23 }

	-- 1.3.6.1.4.1.2606.20.2.1.120.24
	-- overload-fan1-circuit-2-alarm NOTIFICATION-TYPE
	trap24	NOTIFICATION-TYPE
		STATUS current
		DESCRIPTION "Overload fan 1 circuit 2 alarm"
		::= { trapObjects 24 }

	-- 1.3.6.1.4.1.2606.20.2.1.120.25
	-- overload-fan2-circuit2-alarm NOTIFICATION-TYPE
	trap25	NOTIFICATION-TYPE
		STATUS current
		DESCRIPTION "Overload fan 2 circuit 2 alarm"
		::= { trapObjects 25 }

	-- 1.3.6.1.4.1.2606.20.2.1.120.26
	-- overload-fan3-circuit2-alarm NOTIFICATION-TYPE
	trap26	NOTIFICATION-TYPE
		STATUS current
		DESCRIPTION "Overload fan 3 circuit 2 alarm"
		::= { trapObjects 26 }

	-- 1.3.6.1.4.1.2606.20.2.1.120.27
	-- overload-fan4-circuit2-alarm NOTIFICATION-TYPE
	trap27	NOTIFICATION-TYPE
		STATUS current
		DESCRIPTION "Overload fan 4 circuit 2 alarm"
		::= { trapObjects 27 }

	-- 1.3.6.1.4.1.2606.20.2.1.120.28
	-- overload-pump1-alarm NOTIFICATION-TYPE
	trap28	NOTIFICATION-TYPE
		STATUS current
		DESCRIPTION "Overload pump 1 alarm"
		::= { trapObjects 28 }

	-- 1.3.6.1.4.1.2606.20.2.1.120.29
	-- overload-pump2-alarm NOTIFICATION-TYPE
	trap29	NOTIFICATION-TYPE
		STATUS current
		DESCRIPTION "Overload pump 2 alarm"
		::= { trapObjects 29 }

	-- 1.3.6.1.4.1.2606.20.2.1.120.30
	-- wrong-phase-rotation-alarm NOTIFICATION-TYPE
	trap30	NOTIFICATION-TYPE
		STATUS current
		DESCRIPTION "Wrong phase rotation alarm"
		::= { trapObjects 30 }

	-- 1.3.6.1.4.1.2606.20.2.1.120.31
	-- back-Door-open-alarm NOTIFICATION-TYPE
	trap31	NOTIFICATION-TYPE
		STATUS current
		DESCRIPTION "Back Door open alarm"
		::= { trapObjects 31 }


	-- 1.3.6.1.4.1.2606.20.2.1.120.75
	-- alarm-idrofrigo-pump-c-1 NOTIFICATION-TYPE
	trap75	NOTIFICATION-TYPE
		STATUS current
		DESCRIPTION "Condensation pump 1 breaker switch alarm"
		::= { trapObjects 75 }


	-- 1.3.6.1.4.1.2606.20.2.1.120.76
	-- alarm-idrofrigo-pump-c-2 NOTIFICATION-TYPE
	trap76	NOTIFICATION-TYPE
		STATUS current
		DESCRIPTION "Condensation pump 2 breaker switch alarm"
		::= { trapObjects 76 }


	-- 1.3.6.1.4.1.2606.20.2.1.120.80
	-- alarm-idrofrigo-fl-C NOTIFICATION-TYPE
	trap80	NOTIFICATION-TYPE
		STATUS current
		DESCRIPTION "Condensation flow switch alarm"
		::= { trapObjects 80 }


	-- 1.3.6.1.4.1.2606.20.2.1.120.130
	-- remote-on-off NOTIFICATION-TYPE
	trap130	NOTIFICATION-TYPE
		STATUS current
		DESCRIPTION "Remote on-off"
		::= { trapObjects 130 }

	-- 1.3.6.1.4.1.2606.20.2.1.120.131
	-- chiller-ON-OFF NOTIFICATION-TYPE
	trap131	NOTIFICATION-TYPE
		STATUS current
		DESCRIPTION "Chiller ON/OFF"
		::= { trapObjects 131 }


	-- 1.3.6.1.4.1.2606.20.2.1.120.148
	-- alarm-disch-scw-1 NOTIFICATION-TYPE
	trap148	NOTIFICATION-TYPE
		STATUS current
		DESCRIPTION "Discharge screw compressor 1 alarm"
		::= { trapObjects 148 }

	-- 1.3.6.1.4.1.2606.20.2.1.120.149
	-- alarm-disch-scw-2 NOTIFICATION-TYPE
	trap149	NOTIFICATION-TYPE
		STATUS current
		DESCRIPTION "Discharge screw compressor 2 alarm"
		::= { trapObjects 149 }


	-- 1.3.6.1.4.1.2606.20.2.1.120.150
	-- alarm-probe-inlet NOTIFICATION-TYPE
	trap150	NOTIFICATION-TYPE
		STATUS current
		DESCRIPTION "Inlet probe alarm (broken or disconnected)"
		::= { trapObjects 150 }


	-- 1.3.6.1.4.1.2606.20.2.1.120.151
	-- alarm-probe-amb NOTIFICATION-TYPE
	trap151	NOTIFICATION-TYPE
		STATUS current
		DESCRIPTION "Ambient probe alarm (broken or disconnected)"
		::= { trapObjects 151 }


	-- 1.3.6.1.4.1.2606.20.2.1.120.152
	-- alarm-frigo-fl1 NOTIFICATION-TYPE
	trap152	NOTIFICATION-TYPE
		STATUS current
		DESCRIPTION "Flow switch alarm (cooling alarm)"
		::= { trapObjects 152 }


	-- 1.3.6.1.4.1.2606.20.2.1.120.153
	-- alarm-idro-pump1 NOTIFICATION-TYPE
	trap153	NOTIFICATION-TYPE
		STATUS current
		DESCRIPTION "Pump 1 hydraulic alarm"
		::= { trapObjects 153 }


	-- 1.3.6.1.4.1.2606.20.2.1.120.154
	-- alarm-idro-pump2 NOTIFICATION-TYPE
	trap154	NOTIFICATION-TYPE
		STATUS current
		DESCRIPTION "Pump 2 hydraulic alarm"
		::= { trapObjects 154 }


	-- 1.3.6.1.4.1.2606.20.2.1.120.155
	-- alarm-idro-fl1 NOTIFICATION-TYPE
	trap155	NOTIFICATION-TYPE
		STATUS current
		DESCRIPTION "Flow switch alarm (hydraulic alarm)"
		::= { trapObjects 155 }


	-- 1.3.6.1.4.1.2606.20.2.1.120.156
	-- alarm-warning-fl1 NOTIFICATION-TYPE
	trap156	NOTIFICATION-TYPE
		STATUS current
		DESCRIPTION "Flow switch alarm (warning alarm)"
		::= { trapObjects 156 }


	-- 1.3.6.1.4.1.2606.20.2.1.120.157
	-- alarm-hi-water-temp NOTIFICATION-TYPE
	trap157	NOTIFICATION-TYPE
		STATUS current
		DESCRIPTION "High Temperature alarm"
		::= { trapObjects 157 }


	-- 1.3.6.1.4.1.2606.20.2.1.120.158
	-- alarm-lo-water-temp NOTIFICATION-TYPE
	trap158	NOTIFICATION-TYPE
		STATUS current
		DESCRIPTION "Low Temperature alarm"
		::= { trapObjects 158 }

	-- 1.3.6.1.4.1.2606.20.2.1.120.159
	-- alarm-ta-probe1 NOTIFICATION-TYPE
	trap159	NOTIFICATION-TYPE
		STATUS current
		DESCRIPTION "Antifreeze/evaporator probe 1 alarm"
		::= { trapObjects 159 }


	-- 1.3.6.1.4.1.2606.20.2.1.120.160
	-- alarm-hi-press NOTIFICATION-TYPE
	trap160	NOTIFICATION-TYPE
		STATUS current
		DESCRIPTION "High condensation pressure alarm"
		::= { trapObjects 160 }

	-- 1.3.6.1.4.1.2606.20.2.1.120.161
	-- alarm-lo-press NOTIFICATION-TYPE
	trap161	NOTIFICATION-TYPE
		STATUS current
		DESCRIPTION "Low condensation pressure alarm"
		::= { trapObjects 161 }


	-- 1.3.6.1.4.1.2606.20.2.1.120.162
	-- alarm-probe-evap-1 NOTIFICATION-TYPE
	trap162	NOTIFICATION-TYPE
		STATUS current
		DESCRIPTION "Antifreeze/evaporator probe 1 alarm (broken or disconnected)"
		::= { trapObjects 162 }


	-- 1.3.6.1.4.1.2606.20.2.1.120.163
	-- alarm-probe-evap-2 NOTIFICATION-TYPE
	trap163	NOTIFICATION-TYPE
		STATUS current
		DESCRIPTION "Antifreeze/evaporator probe 2 alarm (broken or disconnected)"
		::= { trapObjects 163 }


	-- 1.3.6.1.4.1.2606.20.2.1.120.164
	-- alarm-hi-press-1 NOTIFICATION-TYPE
	trap164	NOTIFICATION-TYPE
		STATUS current
		DESCRIPTION "High condensation pressure 1 alarm"
		::= { trapObjects 164 }


	-- 1.3.6.1.4.1.2606.20.2.1.120.165
	-- alarm-hi-press-2 NOTIFICATION-TYPE
	trap165	NOTIFICATION-TYPE
		STATUS current
		DESCRIPTION "High condensation pressure 2 alarm"
		::= { trapObjects 165 }


	-- 1.3.6.1.4.1.2606.20.2.1.120.166
	-- alarm-lo-press-1 NOTIFICATION-TYPE
	trap166	NOTIFICATION-TYPE
		STATUS current
		DESCRIPTION "Low condensation pressure 1 alarm"
		::= { trapObjects 166 }


	-- 1.3.6.1.4.1.2606.20.2.1.120.167
	-- alarm-lo-press-2 NOTIFICATION-TYPE
	trap167	NOTIFICATION-TYPE
		STATUS current
		DESCRIPTION "Low condensation pressure 2 alarm"
		::= { trapObjects 167 }


	-- 1.3.6.1.4.1.2606.20.2.1.120.168
	-- alarm-probe-tank NOTIFICATION-TYPE
	trap168	NOTIFICATION-TYPE
		STATUS current
		DESCRIPTION "Tank/Out probe alarm (broken or disconnected)"
		::= { trapObjects 168 }


	-- 1.3.6.1.4.1.2606.20.2.1.120.169
	-- alarm-off-line-1 NOTIFICATION-TYPE
	trap169	NOTIFICATION-TYPE
		STATUS current
		DESCRIPTION "Chiller 1 offline"
		::= { trapObjects 169 }


	-- 1.3.6.1.4.1.2606.20.2.1.120.170
	-- alarm-off-line-2 NOTIFICATION-TYPE
	trap170	NOTIFICATION-TYPE
		STATUS current
		DESCRIPTION "Chiller 2 offline"
		::= { trapObjects 170 }


	-- 1.3.6.1.4.1.2606.20.2.1.120.171
	-- alarm-off-line-3 NOTIFICATION-TYPE
	trap171	NOTIFICATION-TYPE
		STATUS current
		DESCRIPTION "Chiller 3 offline"
		::= { trapObjects 171 }


	-- 1.3.6.1.4.1.2606.20.2.1.120.172
	-- alarm-off-line-4 NOTIFICATION-TYPE
	trap172	NOTIFICATION-TYPE
		STATUS current
		DESCRIPTION "Chiller 4 offline"
		::= { trapObjects 172 }


	-- 1.3.6.1.4.1.2606.20.2.1.120.173
	-- alarm-off-line-5 NOTIFICATION-TYPE
	trap173	NOTIFICATION-TYPE
		STATUS current
		DESCRIPTION "Chiller 5 offline"
		::= { trapObjects 173 }


	-- 1.3.6.1.4.1.2606.20.2.1.120.174
	-- alarm-off-line-6 NOTIFICATION-TYPE
	trap174	NOTIFICATION-TYPE
		STATUS current
		DESCRIPTION "Chiller 6 offline"
		::= { trapObjects 174 }


	-- 1.3.6.1.4.1.2606.20.2.1.120.175
	-- alarm-off-line-7 NOTIFICATION-TYPE
	trap175	NOTIFICATION-TYPE
		STATUS current
		DESCRIPTION "Chiller 7 offline"
		::= { trapObjects 175 }


	-- 1.3.6.1.4.1.2606.20.2.1.120.176
	-- alarm-off-line-8 NOTIFICATION-TYPE
	trap176	NOTIFICATION-TYPE
		STATUS current
		DESCRIPTION "Chiller 8 offline"
		::= { trapObjects 176 }


	-- 1.3.6.1.4.1.2606.20.2.1.120.177
	-- alarm-ta-probe2 NOTIFICATION-TYPE
	trap177	NOTIFICATION-TYPE
		STATUS current
		DESCRIPTION "Antifreeze/evaporator probe 2 alarm"
		::= { trapObjects 177 }


	-- 1.3.6.1.4.1.2606.20.2.1.120.178
	-- alarm-sms NOTIFICATION-TYPE
	trap178	NOTIFICATION-TYPE
		STATUS current
		DESCRIPTION "SMS alarm"
		::= { trapObjects 178 }


	-- 1.3.6.1.4.1.2606.20.2.1.120.179
	-- alarm-modem NOTIFICATION-TYPE
	trap179	NOTIFICATION-TYPE
		STATUS current
		DESCRIPTION "Modem alarm"
		::= { trapObjects 179 }


	-- 1.3.6.1.4.1.2606.20.2.1.120.180
	-- alarm-sms-coda NOTIFICATION-TYPE
	trap180	NOTIFICATION-TYPE
		STATUS current
		DESCRIPTION "SMS coda alarm"
		::= { trapObjects 180 }

	-- 1.3.6.1.4.1.2606.20.2.1.120.181
	-- alarm-probe-fc NOTIFICATION-TYPE
	trap181	NOTIFICATION-TYPE
		STATUS current
		DESCRIPTION "Freecooling probe alarm (broken or disconnected)"
		::= { trapObjects 181 }


	-- 1.3.6.1.4.1.2606.20.2.1.120.182
	-- alarm-maint-pw1 NOTIFICATION-TYPE
	trap182	NOTIFICATION-TYPE
		STATUS current
		DESCRIPTION "Maintenance pump 1 alarm)"
		::= { trapObjects 182 }


	-- 1.3.6.1.4.1.2606.20.2.1.120.183
	-- alarm-maint-pw2 NOTIFICATION-TYPE
	trap183	NOTIFICATION-TYPE
		STATUS current
		DESCRIPTION "Maintenance pump 2 alarm)"
		::= { trapObjects 183 }


	-- 1.3.6.1.4.1.2606.20.2.1.120.184
	-- alarm-hi-temp-rid NOTIFICATION-TYPE
	trap184	NOTIFICATION-TYPE
		STATUS current
		DESCRIPTION "High temperature alarm (redundance)"
		::= { trapObjects 184 }


	-- 1.3.6.1.4.1.2606.20.2.1.120.185
	-- alarm-q-fc-sep NOTIFICATION-TYPE
	trap185	NOTIFICATION-TYPE
		STATUS current
		DESCRIPTION "DryCooler breaker switch alarm"
		::= { trapObjects 185 }


	-- 1.3.6.1.4.1.2606.20.2.1.120.186
	-- alarm-p-wat2 NOTIFICATION-TYPE
	trap186	NOTIFICATION-TYPE
		STATUS current
		DESCRIPTION "Water pressure 2 alarm"
		::= { trapObjects 186 }


	-- 1.3.6.1.4.1.2606.20.2.1.120.187
	-- alarm-p-wat1 NOTIFICATION-TYPE
	trap187	NOTIFICATION-TYPE
		STATUS current
		DESCRIPTION "Water pressure 1 alarm"
		::= { trapObjects 187 }


	-- 1.3.6.1.4.1.2606.20.2.1.120.188
	-- alarm-foult-flow-p1 NOTIFICATION-TYPE
	trap188	NOTIFICATION-TYPE
		STATUS current
		DESCRIPTION "Pump 1 flow alarm"
		::= { trapObjects 188 }


	-- 1.3.6.1.4.1.2606.20.2.1.120.189
	-- alarm-foult-flow-p2 NOTIFICATION-TYPE
	trap189	NOTIFICATION-TYPE
		STATUS current
		DESCRIPTION "Pump 2 flow alarm"
		::= { trapObjects 189 }


	-- 1.3.6.1.4.1.2606.20.2.1.120.190
	-- alarm-foult-fl1-p1 NOTIFICATION-TYPE
	trap190	NOTIFICATION-TYPE
		STATUS current
		DESCRIPTION "Pump 1 flow-switch alarm"
		::= { trapObjects 190 }


	-- 1.3.6.1.4.1.2606.20.2.1.120.191
	-- alarm-foult-fl1-p2 NOTIFICATION-TYPE
	trap191	NOTIFICATION-TYPE
		STATUS current
		DESCRIPTION "Pump 2 flow-switch alarm"
		::= { trapObjects 191 }


	-- 1.3.6.1.4.1.2606.20.2.1.120.192
	-- alarm-warning-le NOTIFICATION-TYPE
	trap192	NOTIFICATION-TYPE
		STATUS current
		DESCRIPTION "Water level warning"
		::= { trapObjects 192 }


	-- 1.3.6.1.4.1.2606.20.2.1.120.193
	-- alarm-frigo-fl-C NOTIFICATION-TYPE
	trap193	NOTIFICATION-TYPE
		STATUS current
		DESCRIPTION "Flow switch condensation alarm (cooling alarm)"
		::= { trapObjects 193 }


	-- 1.3.6.1.4.1.2606.20.2.1.120.194
	-- alarm-idro-pump-c-1 NOTIFICATION-TYPE
	trap194	NOTIFICATION-TYPE
		STATUS current
		DESCRIPTION "Pump 1 condensation hydraulic alarm"
		::= { trapObjects 194 }


	-- 1.3.6.1.4.1.2606.20.2.1.120.195
	-- alarm-idro-pump-c-2 NOTIFICATION-TYPE
	trap195	NOTIFICATION-TYPE
		STATUS current
		DESCRIPTION "Pump 2 condensation hydraulic alarm"
		::= { trapObjects 195 }


	-- 1.3.6.1.4.1.2606.20.2.1.120.196
	-- alarm-idro-fl-C NOTIFICATION-TYPE
	trap196	NOTIFICATION-TYPE
		STATUS current
		DESCRIPTION "Flow switch condensation alarm (hydraulic alarm)"
		::= { trapObjects 196 }


	-- 1.3.6.1.4.1.2606.20.2.1.120.197
	-- alarm-warning-fl-C NOTIFICATION-TYPE
	trap197	NOTIFICATION-TYPE
		STATUS current
		DESCRIPTION "Flow switch condensation alarm (warning alarm)"
		::= { trapObjects 197 }


	-- 1.3.6.1.4.1.2606.20.2.1.120.198
	-- alarm-foul-fl-C-p1 NOTIFICATION-TYPE
	trap198	NOTIFICATION-TYPE
		STATUS current
		DESCRIPTION "Pump 1 condensation flow-switch alarm"
		::= { trapObjects 198 }


	-- 1.3.6.1.4.1.2606.20.2.1.120.199
	-- alarm-foul-fl-C-p2 NOTIFICATION-TYPE
	trap199	NOTIFICATION-TYPE
		STATUS current
		DESCRIPTION "Pump 2 condensation flow-switch alarm"
		::= { trapObjects 199 }


	END

--
-- Kelvin-IT-Chiller.mib
--
