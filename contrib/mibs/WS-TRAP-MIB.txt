-- vim: syntax=mib
--
-- WS-TRAP-MIB.my
-- MIB generated by MG-SOFT Visual MIB Builder Version 6.0  Build 88
-- Thursday, May 31, 2007 at 12:12:14
--

--  WS-TRAP-MIB.my
-- MIB generated by MG-SOFT Visual MIB Builder Version 6.0  Build 88
-- Thursday, May 25, 2006 at 12:51:13
-- 

	WS-TRAP-MIB DEFINITIONS ::= BEGIN
 
		IMPORTS
			OBJECT-GROUP, MODULE-COMPLIANCE, NOTIFICATION-GROUP			
				FROM SNMPv2-CONF			
			IpAddress, Integer32, Unsigned32, OBJECT-TYPE, MODULE-IDENTITY, 
			NOTIFICATION-TYPE			
				FROM SNMPv2-SMI			
			DisplayString, PhysAddress, TruthValue			
				FROM SNMPv2-TC			
			wsCcRfMuCnt, wsCcRfMuLastMac, wsCcRfMuMac, wsCcRfMuWlanIndex, wsCcRfMuRadioIndex, 
			wsCcRfMuVlanIndex, wsCcRfMuKeyIndex, wsCcRfMuIpAddr, wsCcRfMuBSS, wsCcRfMuAuthMethod, 
			wsCcRfMuEncMethod, wsCcRfMuRadioType, wsCcRfMuPowerMode, wsCcRfMuSupportedRates, wsCcRfMuVoice, 
			wsCcRfMuIsDataReady, wsCcRfMuRogueApEna, wsCcRfMuIsWmm, wsCcRfMuDisassociateNow, wsCcRfRapStatusMac, 
			wsCcRfRapStatusHeardAp, wsCcRfIdsRadioIndex, wsCcRfIdsViolationType, wsCcRfIdsViolCountLastDetWindow			
				FROM WS-CC-RF-MIB			
			wsCcStatsRadioIndex, wsCcStatsMuMac, wsCcStatsWlanIndex, wsCcStatsTrapCtrlConfIndex, wsCcStatsTrapCtrlConfUnits, 
			wsCcStatsTrapCtrlConfThresholdMus, wsCcStatsTrapCtrlConfThresholdPortals, wsCcStatsTrapCtrlConfThresholdWlans, wsCcStatsTrapCtrlConfThresholdSwitch			
				FROM WS-CC-STATS-MIB			
			wsInfraClusterId, wsInfraClusterLicNum, wsInfraClusterApCnt, wsInfraClusterMemberIpAddr			
				FROM WS-INFRA-CLUSTER-MIB			
			wsInfraDiagTempCurrentTemp, wsInfraDiagTempHighTemp, wsInfraDiagTempHighTempHysteresis, wsInfraDiagSysFanSpeed, wsDiagProcFanSpeed, 
			wsInfraHwTotalNum, wsInfraHwBuildInfoModuleIndex, wsInfraHwBuildInfoModuleName, wsInfraHwBuildInfoVersion, wsInfraHwBuildInfoManufacturer, 
			wsInfraHwBuildInfoDesc, wsInfraResCpuLoad1, wsInfraResCpuLoad5, wsInfraResCpuLoad15, wsInfraFreeMemory, 
			wsInfraRootFSFree, wsInfraRootFSInodesFree, wsInfraRamFSFree, wsInfraRamFSInodesFree, wsInfraFreeFileDesc, 
			wsInfraUsedKernBuff32, wsInfraUsedKernBuff64, wsInfraUsedKernBuff128, wsInfraUsedKernBuff256, wsInfraUsedKernBuff512, 
			wsInfraUsedKernBuff1024, wsInfraUsedKernBuff2048, wsInfraUsedKernBuff4096, wsInfraUsedKernBuff8192, wsInfraUsedKernBuff16384, 
			wsInfraUsedKernBuff32768, wsInfraUsedKernBuff65536, wsInfraUsedKernBuff131072, wsInfraResCpuLoad1MinLimit, wsInfraResCpuLoad5MinLimit, 
			wsInfraResCpuLoad15MinLimit, wsInfraUsedKernBuff32Limit, wsInfraUsedKernBuff64Limit, wsInfraUsedKernBuff128Limit, wsInfraUsedKernBuff256Limit, 
			wsInfraUsedKernBuff512Limit, wsInfraUsedKernBuff1024Limit, wsInfraUsedKernBuff2048Limit, wsInfraUsedKernBuff4096Limit, wsInfraUsedKernBuff8192Limit, 
			wsInfraUsedKernBuff16384Limit, wsInfraUsedKernBuff32768Limit, wsInfraUsedKernBuff65536Limit, wsInfraUsedKernBuff131072Limit, wsInfraDiagMonitoredFSTableIndex, 
			wsInfraDiagMonitoredFSName, wsInfraDiagMonitoredFSFreeSpace, wsInfraDiagMonitoredFSFreeSpacePercent, wsInfraDiagMonitoredFSFreeSpaceLimit, wsInfraDiagMonitoredFSSize, 
			wsInfraDiagMonitoredFSUsed, wsInfraDiagMonitoredFSINodesFree, wsInfraDiagMonitoredFSINodesLimit, wsInfraDiagTempIndex, wsInfraDiagTempSensorName, 
			wsInfraDiagTempCurrTemp, wsInfraDiagTempMaxTemp, wsInfraDiagTempOverTemp, wsInfraDiagFanIndex, wsInfraDiagFanName, 
			wsInfraDiagFanSpeed, wsInfraDiagFanLowSpeedLimit, wsInfraDiagProcIndex, wsInfraDiagProcName, wsInfraDiagProcPercentCPU, 
			wsInfraDiagProcPercentMem, wsInfraDiagRamStatsTotal, wsInfraDiagRamStatsUsed, wsInfraDiagRamStatsFree, wsInfraDiagRamStatsPercentFree, 
			wsInfraDiagRamStatsPercentFreeLimit, wsInfraDiagPktBuffAlloc, wsInfraDiagPktBuffUsed, wsInfraDiagPktBuffMax, wsInfraDiagIpRouteCacheAlloc, 
			wsInfraDiagIpRouteCacheUsed, wsInfraDiagIpRouteCacheMax, wsInfraDiagFileDescInUse, wsInfraDiagFileDescHWM, wsInfraDiagFileDescLimit, 
			wsInfraDiagProcMemLimit			
				FROM WS-INFRA-DIAG-MIB			
			wsInfraProcMonProcessName, wsInfraProcMonProcessMaxRestart			
				FROM WS-INFRA-PM-MIB			
			wsMgmtCertViewTrustpoint			
				FROM WS-MGMT-MIB			
			wsTrap			
				FROM WS-SMI			
			wsSwMobilityPeerIp, wsSwMobilityPeerJOINSent, wsSwMobilityPeerJOINRecvd, wsSwMobilityPeerLEAVESent, wsSwMobilityPeerLEAVERecvd, 
			wsSwMobilityPeerL2ROAMSent, wsSwMobilityPeerL2ROAMRecvd, wsSwMobilityPeerL3ROAMSent, wsSwMobilityPeerL3ROAMRecvd, wsSwMobilityPeerSessionState, 
			wsSwMobilityPeerClearStatistics, wsSwMobilityPeerRowStatus, wsSwMobilityMUMACAddr, wsSwMobilityMUIPAddress, wsSwMobilityMUHSIPAddr, 
			wsSwMobilityMUCSIPAddr, wsSwMobilityMUHSVLAN, wsSwMobilityLocalAddr, wsSwMobilityEnable, wsSwMobilityRoamPeriod, 
			wsSwMobilityMibCompliance, wsSwMobilityGroup			
				FROM WS-SW-MOBILITY-MIB			
			DoActionNow			
				FROM WS-TYPE-MIB;
	
	
--  1.3.6.1.4.1.388.14.5.1
-- January 06, 2006 at 16:06 GMT
-- May 25, 2006 at 12:50 GMT
-- January 06, 2006 at 16:06 GMT
-- January 04, 2006 at 18:21 GMT
-- December 14, 2005 at 14:41 GMT
-- December 12, 2005 at 17:20 GMT
-- November 30, 2005 at 16:24 GMT
-- October 20, 2005 at 19:10 GMT
-- October 12, 2005 at 17:01 GMT
-- September 24, 2005 at 22:33 GMT
		-- 1.3.6.1.4.1.388.14.5.1
		wsTrapMIB MODULE-IDENTITY 
			LAST-UPDATED "200704231624Z"		-- April 23, 2007 at 16:24 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"This MIB defines all the Traps that can occur within the WLAN 
				module.
				
				The following functionality is provided for Enabling/Disabling
				traps :
				1. Each trap has a 'read-write' Enable 'Truth-Value' Flag
				associated with it. 
				
				2. The Traps are organized in groups on a per module basis. 
				Each module  has two 'doActionNow' variables to Enable &
				Disable ALL the traps within that module. Setting these 
				variables directly changes the Enable Flags of all the
				traps within that module.
				
				3. There is a Global Trap Enable 'Truth-Value' Flag which 
				determines whether any trap is sent out or not. Setting this
				variable does not affect the settings of the individual traps."
			REVISION "200612141613Z"		-- December 14, 2006 at 16:13 GMT
			DESCRIPTION 
				"01a17"
			REVISION "200610311306Z"		-- October 31, 2006 at 13:06 GMT
			DESCRIPTION 
				"01a16"
			REVISION "200609251858Z"		-- September 25, 2006 at 18:58 GMT
			DESCRIPTION 
				"01a15"
			REVISION "200609241810Z"		-- September 24, 2006 at 18:10 GMT
			DESCRIPTION 
				"01a14"
			REVISION "200609051530Z"		-- September 05, 2006 at 15:30 GMT
			DESCRIPTION 
				"01a13"
			REVISION "200608280936Z"		-- August 28, 2006 at 09:36 GMT
			DESCRIPTION 
				"01a12"
			REVISION "200607071104Z"		-- July 07, 2006 at 11:04 GMT
			DESCRIPTION 
				"01a11"
			REVISION "200606201301Z"		-- June 20, 2006 at 13:01 GMT
			DESCRIPTION 
				"01a10"
			REVISION "200601061606Z"		-- January 06, 2006 at 16:06 GMT
			DESCRIPTION 
				"01a08"
			REVISION "200605251250Z"		-- May 25, 2006 at 12:50 GMT
			DESCRIPTION 
				"01a09"
			::= { wsTrap 1 }

		
	
	
	
--
-- Node definitions
--
	
--  Node definitions
-- 
-- 1.3.6.1.4.1.388.14.5.1.1
		-- 1.3.6.1.4.1.388.14.5.1.1
		wsTrapSnmp OBJECT IDENTIFIER ::= { wsTrapMIB 1 }

		
--  1.3.6.1.4.1.388.14.5.1.1.1
		-- 1.3.6.1.4.1.388.14.5.1.1.1
		wsTrapSnmpColdStart NOTIFICATION-TYPE
			STATUS current
			DESCRIPTION 
				"Agent reinitialized; configuration may have changed.
				
				Solution:
				Not applicable.
				
				Other Possibilities:
				None."
			::= { wsTrapSnmp 1 }

		
--  1.3.6.1.4.1.388.14.5.1.1.2
		-- 1.3.6.1.4.1.388.14.5.1.1.2
		wsTrapEnableSnmpColdStart OBJECT-TYPE
			SYNTAX TruthValue
			MAX-ACCESS read-write
			STATUS current
			DESCRIPTION
				"Description."
			::= { wsTrapSnmp 2 }

		
--  1.3.6.1.4.1.388.14.5.1.1.3
		-- 1.3.6.1.4.1.388.14.5.1.1.3
		wsTrapSnmpLinkDown NOTIFICATION-TYPE
			OBJECTS { wsTrapNsmIfDescr }
			STATUS current
			DESCRIPTION 
				"No connectivity on the port.
				
				Solution:
				Check if blade is properly inserted in the slot.
				
				Other Possibilities:
				None.
				"
			::= { wsTrapSnmp 3 }

		
--  1.3.6.1.4.1.388.14.5.1.1.4
		-- 1.3.6.1.4.1.388.14.5.1.1.4
		wsTrapEnableSnmpLinkDown OBJECT-TYPE
			SYNTAX TruthValue
			MAX-ACCESS read-write
			STATUS current
			DESCRIPTION
				"Description."
			::= { wsTrapSnmp 4 }

		
--  1.3.6.1.4.1.388.14.5.1.1.5
		-- 1.3.6.1.4.1.388.14.5.1.1.5
		wsTrapSnmpLinkUp NOTIFICATION-TYPE
			OBJECTS { wsTrapNsmIfDescr }
			STATUS current
			DESCRIPTION 
				"Connectivity on the port has been restored.
				
				Solution:
				Not Applicable.
				
				Other Possibilities:
				None.
				"
			::= { wsTrapSnmp 5 }

		
--  1.3.6.1.4.1.388.14.5.1.1.6
		-- 1.3.6.1.4.1.388.14.5.1.1.6
		wsTrapEnableSnmpLinkUp OBJECT-TYPE
			SYNTAX TruthValue
			MAX-ACCESS read-write
			STATUS current
			DESCRIPTION
				"Description."
			::= { wsTrapSnmp 6 }

		
--  1.3.6.1.4.1.388.14.5.1.1.7
		-- 1.3.6.1.4.1.388.14.5.1.1.7
		wsTrapSnmpAuthenticationFail NOTIFICATION-TYPE
			STATUS current
			DESCRIPTION 
				"The SNMP user authentication failed.
				
				Solution:
				Check the user-id/password/community name.
				
				Other Possibilities:
				None.
				"
			::= { wsTrapSnmp 7 }

		
--  1.3.6.1.4.1.388.14.5.1.1.8
		-- 1.3.6.1.4.1.388.14.5.1.1.8
		wsTrapEnableSnmpAuthFail OBJECT-TYPE
			SYNTAX TruthValue
			MAX-ACCESS read-write
			STATUS current
			DESCRIPTION
				"Description."
			::= { wsTrapSnmp 8 }

		
--  1.3.6.1.4.1.388.14.5.1.1.9
		-- 1.3.6.1.4.1.388.14.5.1.1.9
		wsTrapEnableAllSnmpTrap OBJECT-TYPE
			SYNTAX DoActionNow
			MAX-ACCESS read-write
			STATUS current
			DESCRIPTION
				"Description."
			::= { wsTrapSnmp 9 }

		
--  1.3.6.1.4.1.388.14.5.1.1.10
		-- 1.3.6.1.4.1.388.14.5.1.1.10
		wsTrapDisableAllSnmpTrap OBJECT-TYPE
			SYNTAX DoActionNow
			MAX-ACCESS read-write
			STATUS current
			DESCRIPTION
				"Description."
			::= { wsTrapSnmp 10 }

		
--  1.3.6.1.4.1.388.14.5.1.2
		-- 1.3.6.1.4.1.388.14.5.1.2
		wsTrapUpdSvr OBJECT IDENTIFIER ::= { wsTrapMIB 2 }

		
--  1.3.6.1.4.1.388.14.5.1.3
		-- 1.3.6.1.4.1.388.14.5.1.3
		wsTrapNsm OBJECT IDENTIFIER ::= { wsTrapMIB 3 }

		
--  1.3.6.1.4.1.388.14.5.1.3.1
		-- 1.3.6.1.4.1.388.14.5.1.3.1
		wsTrapNsmIfDescr OBJECT-TYPE
			SYNTAX DisplayString
			MAX-ACCESS accessible-for-notify
			STATUS current
			DESCRIPTION
				"Description."
			::= { wsTrapNsm 1 }

		
--  1.3.6.1.4.1.388.14.5.1.3.2
		-- 1.3.6.1.4.1.388.14.5.1.3.2
		wsTrapNsmIpAdEntAddr OBJECT-TYPE
			SYNTAX IpAddress
			MAX-ACCESS accessible-for-notify
			STATUS current
			DESCRIPTION
				"Description."
			::= { wsTrapNsm 2 }

		
--  1.3.6.1.4.1.388.14.5.1.3.3
		-- 1.3.6.1.4.1.388.14.5.1.3.3
		wsTrapNsmIpAdEntNetMask OBJECT-TYPE
			SYNTAX IpAddress
			MAX-ACCESS accessible-for-notify
			STATUS current
			DESCRIPTION
				"Description."
			::= { wsTrapNsm 3 }

		
--  1.3.6.1.4.1.388.14.5.1.3.4
		-- 1.3.6.1.4.1.388.14.5.1.3.4
		wsTrapNsmDhcpIPChanged NOTIFICATION-TYPE
			OBJECTS { wsTrapNsmIfDescr, wsTrapNsmIpAdEntAddr, wsTrapNsmIpAdEntNetMask }
			STATUS current
			DESCRIPTION 
				"Interface IP Address assigned by DHCP has changed.
				
				Solution:
				If a different DHCP server assigned the IP address this time,
				disable the unwanted server and restart the blade.
				
				Other Possibilities:
				Time may not be correctly set on the blade. If the current 
				time on the blade is significantly off from the time on the
				DHCP server, the same DHCP server may assign a new IP address
				when the lease is renewed.
				"
			::= { wsTrapNsm 4 }

		
--  1.3.6.1.4.1.388.14.5.1.3.5
		-- 1.3.6.1.4.1.388.14.5.1.3.5
		wsTrapEnableNsmDhcpIPChanged OBJECT-TYPE
			SYNTAX TruthValue
			MAX-ACCESS read-write
			STATUS current
			DESCRIPTION
				"Description."
			::= { wsTrapNsm 5 }

		
--  1.3.6.1.4.1.388.14.5.1.3.6
		-- 1.3.6.1.4.1.388.14.5.1.3.6
		wsTrapEnableAllNsmTrap OBJECT-TYPE
			SYNTAX DoActionNow
			MAX-ACCESS read-write
			STATUS current
			DESCRIPTION
				"Description."
			::= { wsTrapNsm 6 }

		
--  1.3.6.1.4.1.388.14.5.1.3.7
		-- 1.3.6.1.4.1.388.14.5.1.3.7
		wsTrapDisableAllNsmTrap OBJECT-TYPE
			SYNTAX DoActionNow
			MAX-ACCESS read-write
			STATUS current
			DESCRIPTION
				"Description."
			::= { wsTrapNsm 7 }

		
		-- 1.3.6.1.4.1.388.14.5.1.4
		wsTrapDiag OBJECT IDENTIFIER ::= { wsTrapMIB 4 }

		
		-- 1.3.6.1.4.1.388.14.5.1.4.1
		wsTrapDiagTempHigh NOTIFICATION-TYPE
			OBJECTS { wsInfraDiagTempSensorName, wsInfraDiagTempCurrTemp, wsInfraDiagTempMaxTemp, wsInfraDiagTempOverTemp }
			STATUS current
			DESCRIPTION 
				"Temperature greater than High limit.
				
				Solution:
				None.
				
				Other Possibilities:
				None."
			::= { wsTrapDiag 1 }

		
		-- 1.3.6.1.4.1.388.14.5.1.4.2
		wsTrapEnableDiagTempHigh OBJECT-TYPE
			SYNTAX TruthValue
			MAX-ACCESS read-write
			STATUS current
			DESCRIPTION
				"Description."
			::= { wsTrapDiag 2 }

		
		-- 1.3.6.1.4.1.388.14.5.1.4.3
		wsTrapDiagTempOver NOTIFICATION-TYPE
			OBJECTS { wsInfraDiagTempSensorName, wsInfraDiagTempCurrTemp, wsInfraDiagTempMaxTemp, wsInfraDiagTempOverTemp }
			STATUS current
			DESCRIPTION 
				"Temperature greater than Critical limit.
				
				Solution:
				None.
				
				Other Possibilities:
				None."
			::= { wsTrapDiag 3 }

		
		-- 1.3.6.1.4.1.388.14.5.1.4.4
		wsTrapEnableDiagTempOver OBJECT-TYPE
			SYNTAX TruthValue
			MAX-ACCESS read-write
			STATUS current
			DESCRIPTION
				"Description."
			::= { wsTrapDiag 4 }

		
		-- 1.3.6.1.4.1.388.14.5.1.4.5
		wsTrapDiagFanSpeedLow NOTIFICATION-TYPE
			OBJECTS { wsInfraDiagFanName, wsInfraDiagFanSpeed, wsInfraDiagFanLowSpeedLimit }
			STATUS current
			DESCRIPTION 
				"Fan speed lower than limit.
				
				Solution:
				None.
				
				Other Possibilities:
				None."
			::= { wsTrapDiag 5 }

		
		-- 1.3.6.1.4.1.388.14.5.1.4.6
		wsTrapEnableDiagFanSpeedLow OBJECT-TYPE
			SYNTAX TruthValue
			MAX-ACCESS read-write
			STATUS current
			DESCRIPTION
				"Description."
			::= { wsTrapDiag 6 }

		
		-- 1.3.6.1.4.1.388.14.5.1.4.7
		wsTrapDiagResCpuLoad1Min NOTIFICATION-TYPE
			OBJECTS { wsInfraResCpuLoad1MinLimit, wsInfraResCpuLoad1 }
			STATUS current
			DESCRIPTION 
				"CPU load in last minute averaged greater than limit.
				
				Solution:
				lower usage.
				
				Other Possibilities:
				None."
			::= { wsTrapDiag 7 }

		
		-- 1.3.6.1.4.1.388.14.5.1.4.8
		wsTrapEnableDiagResCpuLoad1Min OBJECT-TYPE
			SYNTAX TruthValue
			MAX-ACCESS read-write
			STATUS current
			DESCRIPTION
				"Description."
			::= { wsTrapDiag 8 }

		
		-- 1.3.6.1.4.1.388.14.5.1.4.9
		wsTrapDiagResCpuLoad5Min NOTIFICATION-TYPE
			OBJECTS { wsInfraResCpuLoad5MinLimit, wsInfraResCpuLoad5 }
			STATUS current
			DESCRIPTION 
				"CPU load in last five minutes averaged greater than 5-minute limit.
				
				Solution:
				lower usage.
				
				Other Possibilities:
				None."
			::= { wsTrapDiag 9 }

		
		-- 1.3.6.1.4.1.388.14.5.1.4.10
		wsTrapEnableDiagResCpuLoad5Min OBJECT-TYPE
			SYNTAX TruthValue
			MAX-ACCESS read-write
			STATUS current
			DESCRIPTION
				"Description."
			::= { wsTrapDiag 10 }

		
		-- 1.3.6.1.4.1.388.14.5.1.4.11
		wsTrapDiagResCpuLoad15Min NOTIFICATION-TYPE
			OBJECTS { wsInfraResCpuLoad15, wsInfraResCpuLoad15MinLimit }
			STATUS current
			DESCRIPTION 
				"CPU load in last 15 minutes averaged greater than 15-minute limit.
				
				Solution:
				lower usage.
				
				Other Possibilities:
				None."
			::= { wsTrapDiag 11 }

		
		-- 1.3.6.1.4.1.388.14.5.1.4.12
		wsTrapEnableDiagResCpuLoad15Min OBJECT-TYPE
			SYNTAX TruthValue
			MAX-ACCESS read-write
			STATUS current
			DESCRIPTION
				"Description."
			::= { wsTrapDiag 12 }

		
		-- 1.3.6.1.4.1.388.14.5.1.4.13
		wsTrapDiagUsedKernBuffSize OBJECT-TYPE
			SYNTAX Integer32 (32 | 64 | 128 | 256 | 512 | 1024 | 2048 | 4096 | 8192 | 16384 | 32768 | 65536 | 131072)
			MAX-ACCESS accessible-for-notify
			STATUS current
			DESCRIPTION
				"Description."
			::= { wsTrapDiag 13 }

		
		-- 1.3.6.1.4.1.388.14.5.1.4.14
		wsTrapDiagUsedKernBuffUsed OBJECT-TYPE
			SYNTAX Integer32
			MAX-ACCESS accessible-for-notify
			STATUS current
			DESCRIPTION
				"Description."
			::= { wsTrapDiag 14 }

		
		-- 1.3.6.1.4.1.388.14.5.1.4.15
		wsTrapDiagUsedKernBuffLimit OBJECT-TYPE
			SYNTAX Integer32
			MAX-ACCESS accessible-for-notify
			STATUS current
			DESCRIPTION
				"Description."
			::= { wsTrapDiag 15 }

		
		-- 1.3.6.1.4.1.388.14.5.1.4.16
		wsTrapDiagUsedKernBuff NOTIFICATION-TYPE
			OBJECTS { wsTrapDiagUsedKernBuffSize, wsTrapDiagUsedKernBuffUsed, wsTrapDiagUsedKernBuffLimit }
			STATUS current
			DESCRIPTION 
				"Usage of kernel buffer greater than limit for given size.
				
				Solution:
				defrag memory.
				
				Other Possibilities:
				None."
			::= { wsTrapDiag 16 }
-- Usage of kernel buffer greater than limit for given size.
-- 
-- Solution:
-- defrag memory.
-- 
-- Other Possibilities:
-- None.
		
		-- 1.3.6.1.4.1.388.14.5.1.4.17
		wsTrapEnableUsedKernBuff OBJECT-TYPE
			SYNTAX TruthValue
			MAX-ACCESS read-write
			STATUS current
			DESCRIPTION
				"Description."
			::= { wsTrapDiag 17 }

		
		-- 1.3.6.1.4.1.388.14.5.1.4.18
		wsTrapDiagRamFree NOTIFICATION-TYPE
			OBJECTS { wsInfraDiagRamStatsTotal, wsInfraDiagRamStatsUsed, wsInfraDiagRamStatsFree, wsInfraDiagRamStatsPercentFree, wsInfraDiagRamStatsPercentFreeLimit
				 }
			STATUS current
			DESCRIPTION 
				"Usage of RAM greater than limit.
				
				Solution:
				None.
				
				Other Possibilities:
				None."
			::= { wsTrapDiag 18 }

		
		-- 1.3.6.1.4.1.388.14.5.1.4.19
		wsTrapEnableDiagRamFree OBJECT-TYPE
			SYNTAX TruthValue
			MAX-ACCESS read-write
			STATUS current
			DESCRIPTION
				"Description."
			::= { wsTrapDiag 19 }

		
		-- 1.3.6.1.4.1.388.14.5.1.4.20
		wsTrapDiagProcMemUsage NOTIFICATION-TYPE
			OBJECTS { wsInfraDiagProcMemLimit, wsInfraDiagProcName, wsInfraDiagProcPercentCPU, wsInfraDiagProcPercentMem }
			STATUS current
			DESCRIPTION 
				"Memory usage of given process greater than limit.
				
				Solution:
				None.
				
				Other Possibilities:
				None."
			::= { wsTrapDiag 20 }

		
		-- 1.3.6.1.4.1.388.14.5.1.4.21
		wsTrapEnableDiagProcMemUsage OBJECT-TYPE
			SYNTAX Integer32
			MAX-ACCESS read-write
			STATUS current
			DESCRIPTION
				"Description."
			::= { wsTrapDiag 21 }

		
		-- 1.3.6.1.4.1.388.14.5.1.4.22
		wsTrapDiagPktBuf NOTIFICATION-TYPE
			OBJECTS { wsInfraDiagPktBuffAlloc, wsInfraDiagPktBuffUsed, wsInfraDiagPktBuffMax }
			STATUS current
			DESCRIPTION 
				"Usage of packet buffer greater than limit.
				
				Solution:
				None.
				
				Other Possibilities:
				None."
			::= { wsTrapDiag 22 }

		
		-- 1.3.6.1.4.1.388.14.5.1.4.23
		wsTrapEnableDiagPktBuf OBJECT-TYPE
			SYNTAX TruthValue
			MAX-ACCESS read-write
			STATUS current
			DESCRIPTION
				"Description."
			::= { wsTrapDiag 23 }

		
		-- 1.3.6.1.4.1.388.14.5.1.4.24
		wsTrapDiagIpRouteCache NOTIFICATION-TYPE
			OBJECTS { wsInfraDiagIpRouteCacheAlloc, wsInfraDiagIpRouteCacheUsed, wsInfraDiagIpRouteCacheMax }
			STATUS current
			DESCRIPTION 
				"IP Route Cache too large.
				
				Solution:
				None.
				
				Other Possibilities:
				None."
			::= { wsTrapDiag 24 }

		
		-- 1.3.6.1.4.1.388.14.5.1.4.25
		wsTrapEnableDiagIpRouteCache OBJECT-TYPE
			SYNTAX TruthValue
			MAX-ACCESS read-write
			STATUS current
			DESCRIPTION
				"Description."
			::= { wsTrapDiag 25 }

		
		-- 1.3.6.1.4.1.388.14.5.1.4.26
		wsTrapDiagFileDesc NOTIFICATION-TYPE
			OBJECTS { wsInfraDiagFileDescInUse, wsInfraDiagFileDescHWM, wsInfraDiagFileDescLimit }
			STATUS current
			DESCRIPTION 
				"Too many file descriptors used.
				
				Solution:
				None.
				
				Other Possibilities:
				None."
			::= { wsTrapDiag 26 }

		
		-- 1.3.6.1.4.1.388.14.5.1.4.27
		wsTrapEnableDiagFileDesc OBJECT-TYPE
			SYNTAX TruthValue
			MAX-ACCESS read-write
			STATUS current
			DESCRIPTION
				"Description."
			::= { wsTrapDiag 27 }

		
		-- 1.3.6.1.4.1.388.14.5.1.4.28
		wsTrapEnableAllDiagTrap OBJECT-TYPE
			SYNTAX DoActionNow
			MAX-ACCESS read-write
			STATUS current
			DESCRIPTION
				"Description."
			::= { wsTrapDiag 28 }

		
		-- 1.3.6.1.4.1.388.14.5.1.4.29
		wsTrapDisableAllDiagTrap OBJECT-TYPE
			SYNTAX DoActionNow
			MAX-ACCESS read-write
			STATUS current
			DESCRIPTION
				"Description."
			::= { wsTrapDiag 29 }

		
--  1.3.6.1.4.1.388.14.5.1.5
		-- 1.3.6.1.4.1.388.14.5.1.5
		wsTrapCluster OBJECT IDENTIFIER ::= { wsTrapMIB 5 }

		
--  1.3.6.1.4.1.388.14.5.1.5.1
		-- 1.3.6.1.4.1.388.14.5.1.5.1
		wsTrapClusterMemberUp NOTIFICATION-TYPE
			OBJECTS { wsInfraClusterMemberIpAddr, wsInfraClusterId }
			STATUS current
			DESCRIPTION 
				"Heartbeats are getting exchanged with this member.
				
				Solution: 
				None
				
				Other Possibilities:
				None.
				"
			::= { wsTrapCluster 1 }

		
--  1.3.6.1.4.1.388.14.5.1.5.2
		-- 1.3.6.1.4.1.388.14.5.1.5.2
		wsTrapEnableClusterMemberUp OBJECT-TYPE
			SYNTAX TruthValue
			MAX-ACCESS read-write
			STATUS current
			DESCRIPTION
				"Description."
			::= { wsTrapCluster 2 }

		
--  1.3.6.1.4.1.388.14.5.1.5.3
		-- 1.3.6.1.4.1.388.14.5.1.5.3
		wsTrapClusterMemberDown NOTIFICATION-TYPE
			OBJECTS { wsInfraClusterId, wsInfraClusterMemberIpAddr }
			STATUS current
			DESCRIPTION 
				"No longer able to see this member. 
				
				Solution:
				1.The member may be rebooted.
				2. Check that the member is reachable via network using ping.
				
				Other Possibilities:
				None.
				"
			::= { wsTrapCluster 3 }

		
--  1.3.6.1.4.1.388.14.5.1.5.4
		-- 1.3.6.1.4.1.388.14.5.1.5.4
		wsTrapEnableClusterMemberDown OBJECT-TYPE
			SYNTAX TruthValue
			MAX-ACCESS read-write
			STATUS current
			DESCRIPTION
				"Description."
			::= { wsTrapCluster 4 }

		
--  1.3.6.1.4.1.388.14.5.1.5.5
		-- 1.3.6.1.4.1.388.14.5.1.5.5
		wsTrapClusterMemberMisConfigured NOTIFICATION-TYPE
			OBJECTS { wsInfraClusterId, wsInfraClusterMemberIpAddr }
			STATUS current
			DESCRIPTION 
				"The member cluster parameter is not sync with this switch.
				
				Solution:
				Check all the cluster parameters are configured same in 
				both switches. (For ex - heartbeat interval, discovery interval, 
				cluster id, hold interval etc.)
				
				
				Other Possibilities:
				None.
				"
			::= { wsTrapCluster 5 }

		
--  1.3.6.1.4.1.388.14.5.1.5.6
		-- 1.3.6.1.4.1.388.14.5.1.5.6
		wsTrapEnableClusterMemberMisConfig OBJECT-TYPE
			SYNTAX TruthValue
			MAX-ACCESS read-write
			STATUS current
			DESCRIPTION
				"Description."
			::= { wsTrapCluster 6 }

		
--  1.3.6.1.4.1.388.14.5.1.5.7
		-- 1.3.6.1.4.1.388.14.5.1.5.7
		wsTrapClusterAdoptionExceeded NOTIFICATION-TYPE
			OBJECTS { wsInfraClusterId, wsInfraClusterApCnt, wsInfraClusterLicNum }
			STATUS current
			DESCRIPTION 
				"All switches in this cluster adopted more access ports than the cluster license.
				
				Solution:
				1. It is a transient condition, but it will converge back 
				   to normal.
				2. Remove excess of ports from the network.
				
				Other Possibilities:
				None.
				"
			::= { wsTrapCluster 7 }

		
--  1.3.6.1.4.1.388.14.5.1.5.8
		-- 1.3.6.1.4.1.388.14.5.1.5.8
		wsTrapEnableClusterAdoptionExceeded OBJECT-TYPE
			SYNTAX TruthValue
			MAX-ACCESS read-write
			STATUS current
			DESCRIPTION
				"Description."
			::= { wsTrapCluster 8 }

		
--  1.3.6.1.4.1.388.14.5.1.5.9
		-- 1.3.6.1.4.1.388.14.5.1.5.9
		wsTrapClusterLicenseChanged NOTIFICATION-TYPE
			OBJECTS { wsInfraClusterId, wsInfraClusterLicNum }
			STATUS current
			DESCRIPTION 
				"Cluster license has been changed. It may either be decreased 
				or increased.
				
				Solution:
				Decrease in cluster license may be because of license
				downgrade happened.
				
				
				Other Possibilities:
				None.
				"
			::= { wsTrapCluster 9 }

		
--  1.3.6.1.4.1.388.14.5.1.5.10
		-- 1.3.6.1.4.1.388.14.5.1.5.10
		wsTrapEnableClusterLicChanged OBJECT-TYPE
			SYNTAX TruthValue
			MAX-ACCESS read-write
			STATUS current
			DESCRIPTION
				"Description."
			::= { wsTrapCluster 10 }

		
--  1.3.6.1.4.1.388.14.5.1.5.11
		-- 1.3.6.1.4.1.388.14.5.1.5.11
		wsTrapEnableAllClusterTrap OBJECT-TYPE
			SYNTAX DoActionNow
			MAX-ACCESS read-write
			STATUS current
			DESCRIPTION
				"Description."
			::= { wsTrapCluster 11 }

		
--  1.3.6.1.4.1.388.14.5.1.5.12
		-- 1.3.6.1.4.1.388.14.5.1.5.12
		wsTrapDisableAllClusterTrap OBJECT-TYPE
			SYNTAX DoActionNow
			MAX-ACCESS read-write
			STATUS current
			DESCRIPTION
				"Description."
			::= { wsTrapCluster 12 }

		
--  1.3.6.1.4.1.388.14.5.1.6
		-- 1.3.6.1.4.1.388.14.5.1.6
		wsTrapMisc OBJECT IDENTIFIER ::= { wsTrapMIB 6 }

		
--  1.3.6.1.4.1.388.14.5.1.6.1
		-- 1.3.6.1.4.1.388.14.5.1.6.1
		wsTrapMiscLowFileSystemSpace NOTIFICATION-TYPE
			OBJECTS { wsInfraDiagMonitoredFSName, wsInfraDiagMonitoredFSFreeSpace, wsInfraDiagMonitoredFSFreeSpaceLimit }
			STATUS current
			DESCRIPTION 
				"Low free space on one of the monitored file systems.
				
				Solution:
				Remove some files from that file system.
				
				Other Possibilities: 
				None.
				"
			::= { wsTrapMisc 1 }

		
--  1.3.6.1.4.1.388.14.5.1.6.2
		-- 1.3.6.1.4.1.388.14.5.1.6.2
		wsTrapEnableMiscLowFileSystemSpace OBJECT-TYPE
			SYNTAX TruthValue
			MAX-ACCESS read-write
			STATUS current
			DESCRIPTION
				"Description."
			::= { wsTrapMisc 2 }

		
--  1.3.6.1.4.1.388.14.5.1.6.3
		-- 1.3.6.1.4.1.388.14.5.1.6.3
		wsTrapMiscProcessMaxRestartsReached NOTIFICATION-TYPE
			OBJECTS { wsInfraProcMonProcessName, wsInfraProcMonProcessMaxRestart }
			STATUS current
			DESCRIPTION 
				"The max restart count of this process by the Process Monitor 
				has been reached.
				
				Solution:
				Please contact technical support.
				
				Other Possibilities: 
				None."
			::= { wsTrapMisc 3 }

		
--  1.3.6.1.4.1.388.14.5.1.6.4
		-- 1.3.6.1.4.1.388.14.5.1.6.4
		wsTrapEnableMiscProcMaxRestart OBJECT-TYPE
			SYNTAX TruthValue
			MAX-ACCESS read-write
			STATUS current
			DESCRIPTION
				"Description."
			::= { wsTrapMisc 4 }

		
		-- 1.3.6.1.4.1.388.14.5.1.6.5
		wsTrapMiscSavedConfigModified NOTIFICATION-TYPE
			STATUS current
			DESCRIPTION 
				"A trap generated when the command 'write mem' is run from the CLI to save the modified config.
						
				Solution:
				Not applicable.
						
				Other Possibilities:
				None."
			::= { wsTrapMisc 5 }

		
		-- 1.3.6.1.4.1.388.14.5.1.6.6
		wsTrapEnableMiscSavedConfigModified OBJECT-TYPE
			SYNTAX TruthValue
			MAX-ACCESS read-write
			STATUS current
			DESCRIPTION
				"A scalar for enabling the trap wsTrapMiscSavedConfigModified to be sent by the SNMP agent on the switch."
			::= { wsTrapMisc 6 }

		
		-- 1.3.6.1.4.1.388.14.5.1.6.7
		wsTrapMiscServerCertExpired NOTIFICATION-TYPE
			OBJECTS { wsMgmtCertViewTrustpoint }
			STATUS current
			DESCRIPTION 
				"Server certificate Expired.
						
				Solution:
				Install a valid server certificate.
						
				Other Possibilities: 
				None.
				"
			::= { wsTrapMisc 7 }

		
		-- 1.3.6.1.4.1.388.14.5.1.6.8
		wsTrapEnableMiscServerCertExpired OBJECT-TYPE
			SYNTAX TruthValue
			MAX-ACCESS read-write
			STATUS current
			DESCRIPTION
				"Description."
			::= { wsTrapMisc 8 }

		
		-- 1.3.6.1.4.1.388.14.5.1.6.9
		wsTrapMiscCaCertExpired NOTIFICATION-TYPE
			OBJECTS { wsMgmtCertViewTrustpoint }
			STATUS current
			DESCRIPTION 
				"Ca certificate Expired
						
				Solution:
				Install a valid ca certificate.
						
				Other Possibilities: 
				None.
				"
			::= { wsTrapMisc 9 }

		
		-- 1.3.6.1.4.1.388.14.5.1.6.10
		wsTrapEnableMiscCaCertExpired OBJECT-TYPE
			SYNTAX TruthValue
			MAX-ACCESS read-write
			STATUS current
			DESCRIPTION
				"Description."
			::= { wsTrapMisc 10 }

		
--  1.3.6.1.4.1.388.14.5.1.6.5
		-- 1.3.6.1.4.1.388.14.5.1.6.11
		wsTrapEnableAllMiscTrap OBJECT-TYPE
			SYNTAX DoActionNow
			MAX-ACCESS read-write
			STATUS current
			DESCRIPTION
				"Description."
			::= { wsTrapMisc 11 }

		
--  1.3.6.1.4.1.388.14.5.1.6.6
		-- 1.3.6.1.4.1.388.14.5.1.6.12
		wsTrapDisableAllMiscTrap OBJECT-TYPE
			SYNTAX DoActionNow
			MAX-ACCESS read-write
			STATUS current
			DESCRIPTION
				"Description."
			::= { wsTrapMisc 12 }

		
		-- 1.3.6.1.4.1.388.14.5.1.6.13
		wsTrapMiscPeriodicHeartbeat NOTIFICATION-TYPE
			STATUS current
			DESCRIPTION 
				"This trap/heartbeat shall be triggered only if no other SNMP 
				Trap was sent by that switch in the specified time frame.
				
				Solution:
				None.
						
				Other Possibilities: 
				None."
			::= { wsTrapMisc 13 }

		
		-- 1.3.6.1.4.1.388.14.5.1.6.14
		wsTrapEnableMiscPeriodicHeartbeat OBJECT-TYPE
			SYNTAX TruthValue
			MAX-ACCESS read-write
			STATUS current
			DESCRIPTION
				"Enable the periodic system heartbeat trap."
			::= { wsTrapMisc 14 }

		
--  1.3.6.1.4.1.388.14.5.1.7
		-- 1.3.6.1.4.1.388.14.5.1.7
		wsTrapWireless OBJECT IDENTIFIER ::= { wsTrapMIB 7 }

		
--  1.3.6.1.4.1.388.14.5.1.7.1
		-- 1.3.6.1.4.1.388.14.5.1.7.1
		wsTrapWirelessStation OBJECT IDENTIFIER ::= { wsTrapWireless 1 }

		
--  1.3.6.1.4.1.388.14.5.1.7.1.1
		-- 1.3.6.1.4.1.388.14.5.1.7.1.1
		wsTrapWirelessStationMac OBJECT-TYPE
			SYNTAX PhysAddress
			MAX-ACCESS accessible-for-notify
			STATUS current
			DESCRIPTION
				"Description."
			::= { wsTrapWirelessStation 1 }

		
--  1.3.6.1.4.1.388.14.5.1.7.1.2
		-- 1.3.6.1.4.1.388.14.5.1.7.1.2
		wsTrapWirelessStationRadioNum OBJECT-TYPE
			SYNTAX Integer32
			MAX-ACCESS accessible-for-notify
			STATUS current
			DESCRIPTION
				"Description."
			::= { wsTrapWirelessStation 2 }

		
--  1.3.6.1.4.1.388.14.5.1.7.1.3
		-- 1.3.6.1.4.1.388.14.5.1.7.1.3
		wsTrapWirelessStationLimitOnRadio OBJECT-TYPE
			SYNTAX Integer32
			MAX-ACCESS accessible-for-notify
			STATUS current
			DESCRIPTION
				"Description."
			::= { wsTrapWirelessStation 3 }

		
--  1.3.6.1.4.1.388.14.5.1.7.1.4
		-- 1.3.6.1.4.1.388.14.5.1.7.1.4
		wsTrapWirelessStationAssociated NOTIFICATION-TYPE
			OBJECTS { wsTrapWirelessStationMac, wsTrapWirelessStationRadioNum }
			STATUS current
			DESCRIPTION 
				"A station has associated to the wlan controller.        
				
				Solution: 
				If this is not an authorized station, add it to the 
				Access Control List or increase your wireless security.
				
				Other Possibilities: 
				None.
				"
			::= { wsTrapWirelessStation 4 }

		
--  1.3.6.1.4.1.388.14.5.1.7.1.5
		-- 1.3.6.1.4.1.388.14.5.1.7.1.5
		wsTrapEnableWirelessStationAssoc OBJECT-TYPE
			SYNTAX TruthValue
			MAX-ACCESS read-write
			STATUS current
			DESCRIPTION
				"Description."
			::= { wsTrapWirelessStation 5 }

		
--  1.3.6.1.4.1.388.14.5.1.7.1.6
		-- 1.3.6.1.4.1.388.14.5.1.7.1.6
		wsTrapWirelessStationDisassociated NOTIFICATION-TYPE
			OBJECTS { wsTrapWirelessStationMac, wsTrapWirelessStationRadioNum }
			STATUS current
			DESCRIPTION 
				"A station has disassociated from the wlan controller.
				
				Solution:
				Make sure your station is powered on and within the 
				service area of the wlan controller.
				
				Other Possibilities:
				The station may not have the correct credentials to
				associate to the wlan.
				
				"
			::= { wsTrapWirelessStation 6 }

		
--  1.3.6.1.4.1.388.14.5.1.7.1.7
		-- 1.3.6.1.4.1.388.14.5.1.7.1.7
		wsTrapEnableWirelessStationDisAssoc OBJECT-TYPE
			SYNTAX TruthValue
			MAX-ACCESS read-write
			STATUS current
			DESCRIPTION
				"Description."
			::= { wsTrapWirelessStation 7 }

		
--  1.3.6.1.4.1.388.14.5.1.7.1.8
		-- 1.3.6.1.4.1.388.14.5.1.7.1.8
		wsTrapWirelessStationDeniedAssociationOnCapability NOTIFICATION-TYPE
			OBJECTS { wsTrapWirelessStationMac, wsTrapWirelessStationRadioNum }
			STATUS current
			DESCRIPTION 
				"The station was denied association due to conflicts 
				in the 802.11 capabilities field.
				
				Solution:
				The station needs to be updated to support the correct
				capability fields.
				
				Other Possibilities: 
				None.
				"
			::= { wsTrapWirelessStation 8 }

		
--  1.3.6.1.4.1.388.14.5.1.7.1.9
		-- 1.3.6.1.4.1.388.14.5.1.7.1.9
		wsTrapEnableWirelessStationDenAssocOnCap OBJECT-TYPE
			SYNTAX TruthValue
			MAX-ACCESS read-write
			STATUS current
			DESCRIPTION
				"Description."
			::= { wsTrapWirelessStation 9 }

		
--  1.3.6.1.4.1.388.14.5.1.7.1.10
		-- 1.3.6.1.4.1.388.14.5.1.7.1.10
		wsTrapWirelessStationDeniedAssociationOnShortPreamble NOTIFICATION-TYPE
			OBJECTS { wsTrapWirelessStationMac, wsTrapWirelessStationRadioNum }
			STATUS current
			DESCRIPTION 
				"The station was denied association because it does not
				support short preamble.
				
				Solution:
				Turn off short preamble on the wlan or update the 
				station so it can support short preamble.
				
				Other Possibilities:
				None.
				"
			::= { wsTrapWirelessStation 10 }

		
--  1.3.6.1.4.1.388.14.5.1.7.1.11
		-- 1.3.6.1.4.1.388.14.5.1.7.1.11
		wsTrapEnableWirelessStationDenAssocOnShortPmbl OBJECT-TYPE
			SYNTAX TruthValue
			MAX-ACCESS read-write
			STATUS current
			DESCRIPTION
				"Description."
			::= { wsTrapWirelessStation 11 }

		
--  1.3.6.1.4.1.388.14.5.1.7.1.12
		-- 1.3.6.1.4.1.388.14.5.1.7.1.12
		wsTrapWirelessStationDeniedAssociationOnSpectrum NOTIFICATION-TYPE
			OBJECTS { wsTrapWirelessStationMac, wsTrapWirelessStationRadioNum }
			STATUS current
			DESCRIPTION 
				"The station was denied association because it does not
				support spectrum magagement.
				
				Solution:
				The country and channel of operation require spectrum
				management on stations.  Update your station or try a 
				different channel.
				
				Other Possibilities:
				None.
				"
			::= { wsTrapWirelessStation 12 }

		
--  1.3.6.1.4.1.388.14.5.1.7.1.13
		-- 1.3.6.1.4.1.388.14.5.1.7.1.13
		wsTrapEnableWirelessStationDenAssocOnSpectrum OBJECT-TYPE
			SYNTAX TruthValue
			MAX-ACCESS read-write
			STATUS current
			DESCRIPTION
				"Description."
			::= { wsTrapWirelessStation 13 }

		
--  1.3.6.1.4.1.388.14.5.1.7.1.14
		-- 1.3.6.1.4.1.388.14.5.1.7.1.14
		wsTrapWirelessStationDeniedAssociationOnErr NOTIFICATION-TYPE
			OBJECTS { wsTrapWirelessStationMac, wsTrapWirelessStationRadioNum }
			STATUS current
			DESCRIPTION 
				"The station was denied association because the 802.11
				packet was malformed.
				
				Solution: 
				Check your station hardware and software for errors.
				
				Other Possibilities:
				Interference or a cracking attempt.
				"
			::= { wsTrapWirelessStation 14 }

		
--  1.3.6.1.4.1.388.14.5.1.7.1.15
		-- 1.3.6.1.4.1.388.14.5.1.7.1.15
		wsTrapEnableWirelessStationDenAssocOnErr OBJECT-TYPE
			SYNTAX TruthValue
			MAX-ACCESS read-write
			STATUS current
			DESCRIPTION
				"Description."
			::= { wsTrapWirelessStation 15 }

		
--  1.3.6.1.4.1.388.14.5.1.7.1.16
		-- 1.3.6.1.4.1.388.14.5.1.7.1.16
		wsTrapWirelessStationDeniedAssociationOnSSID NOTIFICATION-TYPE
			OBJECTS { wsTrapWirelessStationMac, wsTrapWirelessStationRadioNum }
			STATUS current
			DESCRIPTION 
				"The station was denied association because the SSID 
				supplied by the MU was too large.
				
				Solution:
				Check your MU software. It appears to be sending a
				malformed association request.
				
				Other Possibilities:
				Interference or a cracking attempt.
				"
			::= { wsTrapWirelessStation 16 }

		
--  1.3.6.1.4.1.388.14.5.1.7.1.17
		-- 1.3.6.1.4.1.388.14.5.1.7.1.17
		wsTrapEnableWirelessStationDenAssocOnSSID OBJECT-TYPE
			SYNTAX TruthValue
			MAX-ACCESS read-write
			STATUS current
			DESCRIPTION
				"Description."
			::= { wsTrapWirelessStation 17 }

		
--  1.3.6.1.4.1.388.14.5.1.7.1.18
		-- 1.3.6.1.4.1.388.14.5.1.7.1.18
		wsTrapWirelessStationDeniedAssociationOnRates NOTIFICATION-TYPE
			OBJECTS { wsTrapWirelessStationMac, wsTrapWirelessStationRadioNum }
			STATUS current
			DESCRIPTION 
				"The station was denied association because it does not
				support the rates required.
				
				Solution:
				Reduce the supported rate set on the radio or update
				the radio on the station to support the required rates.
				
				Other Possibilities:
				None.
				
				"
			::= { wsTrapWirelessStation 18 }

		
--  1.3.6.1.4.1.388.14.5.1.7.1.19
		-- 1.3.6.1.4.1.388.14.5.1.7.1.19
		wsTrapEnableWirelessStationDenAssocOnRates OBJECT-TYPE
			SYNTAX TruthValue
			MAX-ACCESS read-write
			STATUS current
			DESCRIPTION
				"Description."
			::= { wsTrapWirelessStation 19 }

		
--  1.3.6.1.4.1.388.14.5.1.7.1.20
		-- 1.3.6.1.4.1.388.14.5.1.7.1.20
		wsTrapWirelessStationDeniedAssociationOnInvalidWPA NOTIFICATION-TYPE
			OBJECTS { wsTrapWirelessStationMac, wsTrapWirelessStationRadioNum }
			STATUS current
			DESCRIPTION 
				"The station was denied association because it did not
				send a WPA/WPA2 element.
				
				Solution:
				Ensure the station supports WPA/WPA2 or turn off 
				WPA/WPA2.
				
				Other Possibilities:
				None.
				"
			::= { wsTrapWirelessStation 20 }

		
--  1.3.6.1.4.1.388.14.5.1.7.1.21
		-- 1.3.6.1.4.1.388.14.5.1.7.1.21
		wsTrapEnableWirelessStationDenAssocOnInvalidWPA OBJECT-TYPE
			SYNTAX TruthValue
			MAX-ACCESS read-write
			STATUS current
			DESCRIPTION
				"Description."
			::= { wsTrapWirelessStation 21 }

		
--  1.3.6.1.4.1.388.14.5.1.7.1.22
		-- 1.3.6.1.4.1.388.14.5.1.7.1.22
		wsTrapWirelessStationDeniedAssociationAsPortCapacityReached NOTIFICATION-TYPE
			OBJECTS { wsTrapWirelessStationMac, wsTrapWirelessStationRadioNum, wsTrapWirelessStationLimitOnRadio }
			STATUS current
			DESCRIPTION 
				"The station was denied association because the radio
				it was attempting to associate to has reached its 
				station limit. 
				
				Solution:
				Increase the number of stations that can associate to
				the radio or increase radio density to allow for more
				stations.
				
				Other Possibilities:
				None.
				"
			::= { wsTrapWirelessStation 22 }

		
--  1.3.6.1.4.1.388.14.5.1.7.1.23
		-- 1.3.6.1.4.1.388.14.5.1.7.1.23
		wsTrapEnableWirelessStationDenAssocAsPortCapReached OBJECT-TYPE
			SYNTAX TruthValue
			MAX-ACCESS read-write
			STATUS current
			DESCRIPTION
				"Description."
			::= { wsTrapWirelessStation 23 }

		
--  1.3.6.1.4.1.388.14.5.1.7.1.24
		-- 1.3.6.1.4.1.388.14.5.1.7.1.24
		wsTrapWirelessStationTkipCounterMeasures NOTIFICATION-TYPE
			STATUS current
			DESCRIPTION 
				"There have been 2 or more TKIP MIC checksum failures
				in the last 60 seconds, as a result that Wireless Lan
				has been disabled for 60 seconds. MIC failures can 
				occur either because someone is trying to attack the 
				network and guess your TKIP keys, or because of some 
				stations that have drivers that generate invalid 
				frames.
				
				Solution: 
				View the system logs to see which wireless station is
				generating these MIC failures. If it is on your network,
				then take that station off the network for now. 
				Contact support.
				
				
				Other Possibilities: 
				If your network is setup for eap authentication with
				TKIP encryption, and there are frequent 
				reauthentications, MIC failures can occur. If this is 
				the case, try reducing the frequency of 
				re-authentications, and see if it helps with the 
				countermeasures. Again see if the failures are caused 
				by one particular station.
				
				"
			::= { wsTrapWirelessStation 24 }

		
--  1.3.6.1.4.1.388.14.5.1.7.1.25
		-- 1.3.6.1.4.1.388.14.5.1.7.1.25
		wsTrapEnableWirelessStationTkipCntMeasures OBJECT-TYPE
			SYNTAX TruthValue
			MAX-ACCESS read-write
			STATUS current
			DESCRIPTION
				"Description."
			::= { wsTrapWirelessStation 25 }

		
--  1.3.6.1.4.1.388.14.5.1.7.1.26
		-- 1.3.6.1.4.1.388.14.5.1.7.1.26
		wsTrapWirelessStationDeniedAuthentication NOTIFICATION-TYPE
			OBJECTS { wsTrapWirelessStationMac }
			STATUS current
			DESCRIPTION 
				"The station was denied authentication due to the 
				maximum number of stations being reached for the 
				controller.
				
				Solution:
				Add another controller to you network or reduce the
				number of stations.
				
				Other Possibilities: 
				The authentication algorithm being used by the WLAN
				is not supported by the station or a malformed auth
				packet from the station.
				
				"
			::= { wsTrapWirelessStation 26 }

		
--  1.3.6.1.4.1.388.14.5.1.7.1.27
		-- 1.3.6.1.4.1.388.14.5.1.7.1.27
		wsTrapEnableWirelessStationDenAuth OBJECT-TYPE
			SYNTAX TruthValue
			MAX-ACCESS read-write
			STATUS current
			DESCRIPTION
				"Description."
			::= { wsTrapWirelessStation 27 }

		
--  1.3.6.1.4.1.388.14.5.1.7.1.28
		-- 1.3.6.1.4.1.388.14.5.1.7.1.28
		wsTrapWirelessStationRadiusAuthFailed NOTIFICATION-TYPE
			OBJECTS { wsTrapWirelessStationMac, wsTrapWirelessStationRadioNum }
			STATUS current
			DESCRIPTION 
				"The station was denied access to the wlan because
				Radius authentication failed.
				
				Solution:
				Check radius server connectivity and the stations 
				username/password.
				
				Other Possibilities:
				None
				
				"
			::= { wsTrapWirelessStation 28 }

		
--  1.3.6.1.4.1.388.14.5.1.7.1.29
		-- 1.3.6.1.4.1.388.14.5.1.7.1.29
		wsTrapEnableWirelessStationRadAuthFail OBJECT-TYPE
			SYNTAX TruthValue
			MAX-ACCESS read-write
			STATUS current
			DESCRIPTION
				"Description."
			::= { wsTrapWirelessStation 29 }

		
--  1.3.6.1.4.1.388.14.5.1.7.1.30
		-- 1.3.6.1.4.1.388.14.5.1.7.1.30
		wsTrapEnableAllWirelessStationTrap OBJECT-TYPE
			SYNTAX DoActionNow
			MAX-ACCESS read-write
			STATUS current
			DESCRIPTION
				"Description."
			::= { wsTrapWirelessStation 30 }

		
--  1.3.6.1.4.1.388.14.5.1.7.1.31
		-- 1.3.6.1.4.1.388.14.5.1.7.1.31
		wsTrapDisableAllWirelessStationTrap OBJECT-TYPE
			SYNTAX DoActionNow
			MAX-ACCESS read-write
			STATUS current
			DESCRIPTION
				"Description."
			::= { wsTrapWirelessStation 31 }

		
--  1.3.6.1.4.1.388.14.5.1.7.2
		-- 1.3.6.1.4.1.388.14.5.1.7.2
		wsTrapWirelessRadio OBJECT IDENTIFIER ::= { wsTrapWireless 2 }

		
--  1.3.6.1.4.1.388.14.5.1.7.2.1
		-- 1.3.6.1.4.1.388.14.5.1.7.2.1
		wsTrapWirelessRadioName OBJECT-TYPE
			SYNTAX OCTET STRING (SIZE (0..20))
			MAX-ACCESS accessible-for-notify
			STATUS current
			DESCRIPTION
				"Description."
			::= { wsTrapWirelessRadio 1 }

		
--  1.3.6.1.4.1.388.14.5.1.7.2.2
		-- 1.3.6.1.4.1.388.14.5.1.7.2.2
		wsTrapWirelessRadioChannelNum OBJECT-TYPE
			SYNTAX Unsigned32
			MAX-ACCESS accessible-for-notify
			STATUS current
			DESCRIPTION
				"Description."
			::= { wsTrapWirelessRadio 2 }

		
--  1.3.6.1.4.1.388.14.5.1.7.2.3
		-- 1.3.6.1.4.1.388.14.5.1.7.2.3
		wsTrapWirelessAPMac OBJECT-TYPE
			SYNTAX PhysAddress
			MAX-ACCESS accessible-for-notify
			STATUS current
			DESCRIPTION
				"Description."
			::= { wsTrapWirelessRadio 3 }

		
--  1.3.6.1.4.1.388.14.5.1.7.2.4
		-- 1.3.6.1.4.1.388.14.5.1.7.2.4
		wsTrapWirelessRadioAdopted NOTIFICATION-TYPE
			OBJECTS { wsTrapWirelessRadioName, wsTrapWirelessAPMac }
			STATUS current
			DESCRIPTION 
				"A radio was adopted by the wlan controller. 
				
				Solution:
				If this is not a authorized station, turn off
				adopt-unconf-radio                    
				
				Other Possibilities:
				None.
				"
			::= { wsTrapWirelessRadio 4 }

		
--  1.3.6.1.4.1.388.14.5.1.7.2.5
		-- 1.3.6.1.4.1.388.14.5.1.7.2.5
		wsTrapEnableWirelessRadioAdopted OBJECT-TYPE
			SYNTAX TruthValue
			MAX-ACCESS read-write
			STATUS current
			DESCRIPTION
				"Description."
			::= { wsTrapWirelessRadio 5 }

		
--  1.3.6.1.4.1.388.14.5.1.7.2.6
		-- 1.3.6.1.4.1.388.14.5.1.7.2.6
		wsTrapWirelessRadioUnadopted NOTIFICATION-TYPE
			OBJECTS { wsTrapWirelessRadioName, wsTrapWirelessAPMac }
			STATUS current
			DESCRIPTION 
				"A radio was un-adopted from the wlan controller. 
				
				Solution:
				Check network connectivity between the controller and 
				radio port.
				
				Other Possibilities:
				The radio was removed or reconfigured.
				"
			::= { wsTrapWirelessRadio 6 }

		
--  1.3.6.1.4.1.388.14.5.1.7.2.7
		-- 1.3.6.1.4.1.388.14.5.1.7.2.7
		wsTrapEnableWirelessRadioUnadopted OBJECT-TYPE
			SYNTAX TruthValue
			MAX-ACCESS read-write
			STATUS current
			DESCRIPTION
				"Description."
			::= { wsTrapWirelessRadio 7 }

		
--  1.3.6.1.4.1.388.14.5.1.7.2.8
		-- 1.3.6.1.4.1.388.14.5.1.7.2.8
		wsTrapWirelessRadioDetectedRadar NOTIFICATION-TYPE
			OBJECTS { wsTrapWirelessRadioName, wsTrapWirelessRadioChannelNum, wsTrapWirelessAPMac }
			STATUS current
			DESCRIPTION 
				"A radio detected radar on its channel of operation and
				is switching channels.
				
				Solution:
				Retry the channel later.
				
				Other Possibilities:
				Interference.
				"
			::= { wsTrapWirelessRadio 8 }

		
--  1.3.6.1.4.1.388.14.5.1.7.2.9
		-- 1.3.6.1.4.1.388.14.5.1.7.2.9
		wsTrapEnableWirelessRadioDetectedRadar OBJECT-TYPE
			SYNTAX TruthValue
			MAX-ACCESS read-write
			STATUS current
			DESCRIPTION
				"Description."
			::= { wsTrapWirelessRadio 9 }

		
--  1.3.6.1.4.1.388.14.5.1.7.2.10
		-- 1.3.6.1.4.1.388.14.5.1.7.2.10
		wsTrapEnableAllWirelessRadioTrap OBJECT-TYPE
			SYNTAX DoActionNow
			MAX-ACCESS read-write
			STATUS current
			DESCRIPTION
				"Description."
			::= { wsTrapWirelessRadio 10 }

		
--  1.3.6.1.4.1.388.14.5.1.7.2.11
		-- 1.3.6.1.4.1.388.14.5.1.7.2.11
		wsTrapDisableAllWirelessRadioTrap OBJECT-TYPE
			SYNTAX DoActionNow
			MAX-ACCESS read-write
			STATUS current
			DESCRIPTION
				"Description."
			::= { wsTrapWirelessRadio 11 }

		
--  1.3.6.1.4.1.388.14.5.1.7.3
		-- 1.3.6.1.4.1.388.14.5.1.7.3
		wsTrapWirelessUnapprovedAP OBJECT IDENTIFIER ::= { wsTrapWireless 3 }

		
--  1.3.6.1.4.1.388.14.5.1.7.3.1
		-- 1.3.6.1.4.1.388.14.5.1.7.3.1
		wsTrapWirelessUnapprovedAPDetected NOTIFICATION-TYPE
			OBJECTS { wsCcRfRapStatusMac, wsCcRfRapStatusHeardAp }
			STATUS current
			DESCRIPTION 
				"An external, unapproved AP was detected in the 
				vicinity of your wlan.
				
				Solution:
				Add the unapproved AP to the approved list or remove
				the unapproved AP.
				
				Other Possibilities:
				None.
				"
			::= { wsTrapWirelessUnapprovedAP 1 }

		
--  1.3.6.1.4.1.388.14.5.1.7.3.2
		-- 1.3.6.1.4.1.388.14.5.1.7.3.2
		wsTrapEnableWirelessUnapprovedAPDetected OBJECT-TYPE
			SYNTAX TruthValue
			MAX-ACCESS read-write
			STATUS current
			DESCRIPTION
				"Description."
			::= { wsTrapWirelessUnapprovedAP 2 }

		
--  1.3.6.1.4.1.388.14.5.1.7.3.3
		-- 1.3.6.1.4.1.388.14.5.1.7.3.3
		wsTrapEnableAllWirelessUnapprovedAPTrap OBJECT-TYPE
			SYNTAX DoActionNow
			MAX-ACCESS read-write
			STATUS current
			DESCRIPTION
				"Description."
			::= { wsTrapWirelessUnapprovedAP 3 }

		
--  1.3.6.1.4.1.388.14.5.1.7.3.4
		-- 1.3.6.1.4.1.388.14.5.1.7.3.4
		wsTrapDisableAllWirelessUnapprovedAPTrap OBJECT-TYPE
			SYNTAX DoActionNow
			MAX-ACCESS read-write
			STATUS current
			DESCRIPTION
				"Description."
			::= { wsTrapWirelessUnapprovedAP 4 }

		
--  1.3.6.1.4.1.388.14.5.1.7.4
		-- 1.3.6.1.4.1.388.14.5.1.7.4
		wsTrapWirelessSelfHeal OBJECT IDENTIFIER ::= { wsTrapWireless 4 }

		
--  1.3.6.1.4.1.388.14.5.1.7.4.1
		-- 1.3.6.1.4.1.388.14.5.1.7.4.1
		wsTrapWirelessSelfHealActivate NOTIFICATION-TYPE
			STATUS current
			DESCRIPTION 
				"This radio is attempting to cover for a neighboring AP that
				is down.
				
				Solution:
				1. Verify that the neighboring AP is still adopted.
				2. Verify that there are no physical obstructions between
				 the down AP and other APs.
				
				Other Possibilities:
				1. The neighboring AP may have a physical obstruction or has 
				become unadopted.
				2. Mis-configuration. Set the healing AP and the down AP to 
				not be neighbors.
				"
			::= { wsTrapWirelessSelfHeal 1 }

		
--  1.3.6.1.4.1.388.14.5.1.7.4.2
		-- 1.3.6.1.4.1.388.14.5.1.7.4.2
		wsTrapEnableWirelessSelfHealActivate OBJECT-TYPE
			SYNTAX TruthValue
			MAX-ACCESS read-write
			STATUS current
			DESCRIPTION
				"Description."
			::= { wsTrapWirelessSelfHeal 2 }

		
--  1.3.6.1.4.1.388.14.5.1.7.4.3
		-- 1.3.6.1.4.1.388.14.5.1.7.4.3
		wsTrapEnableAllWirelessSelfHealTrap OBJECT-TYPE
			SYNTAX DoActionNow
			MAX-ACCESS read-write
			STATUS current
			DESCRIPTION
				"Description."
			::= { wsTrapWirelessSelfHeal 3 }

		
--  1.3.6.1.4.1.388.14.5.1.7.4.4
		-- 1.3.6.1.4.1.388.14.5.1.7.4.4
		wsTrapDisableAllWirelessSelfHealTrap OBJECT-TYPE
			SYNTAX DoActionNow
			MAX-ACCESS read-write
			STATUS current
			DESCRIPTION
				"Description."
			::= { wsTrapWirelessSelfHeal 4 }

		
--  1.3.6.1.4.1.388.14.5.1.7.5
		-- 1.3.6.1.4.1.388.14.5.1.7.5
		wsTrapWirelessIds OBJECT IDENTIFIER ::= { wsTrapWireless 5 }

		
		-- 1.3.6.1.4.1.388.14.5.1.7.5.1
		wsTrapWirelessIdsMuEvent NOTIFICATION-TYPE
			OBJECTS { wsCcRfIdsViolationType, wsTrapWirelessStationMac, wsCcRfIdsViolCountLastDetWindow, wsCcRfIdsRadioIndex }
			STATUS current
			DESCRIPTION 
				"The number of requests from the MU has exceeded the 
				configured threshold for the violation type. The MU 
				is being filtered for the configured number of seconds.
				
				
				Solution:
				This may be indicative of an attack on your wireless LAN. 
				If the MU is one of your own, it may be experiencing problems. 
				
				Other Possibilities:
				The threshold may be set too low, make it higher.
				"
			::= { wsTrapWirelessIds 1 }

		
		-- 1.3.6.1.4.1.388.14.5.1.7.5.2
		wsTrapEnableWirelessIdsMuEvent OBJECT-TYPE
			SYNTAX TruthValue
			MAX-ACCESS read-write
			STATUS current
			DESCRIPTION
				"Description"
			::= { wsTrapWirelessIds 2 }

		
		-- 1.3.6.1.4.1.388.14.5.1.7.5.3
		wsTrapWirelessIdsRadioEvent NOTIFICATION-TYPE
			OBJECTS { wsCcRfIdsViolationType, wsCcRfIdsViolCountLastDetWindow, wsCcRfIdsRadioIndex }
			STATUS current
			DESCRIPTION 
				"The number of requests from the radio has exceeded the 
				configured threshold for the violation type. 
				
				
				Solution:
				This may be indicative of an attack on your wireless LAN. 
				If the radio is one of your own, it may be experiencing problems. 
				
				Other Possibilities:
				The threshold may be set too low, make it higher.
				"
			::= { wsTrapWirelessIds 3 }

		
		-- 1.3.6.1.4.1.388.14.5.1.7.5.4
		wsTrapEnableWirelessIdsRadioEvent OBJECT-TYPE
			SYNTAX TruthValue
			MAX-ACCESS read-write
			STATUS current
			DESCRIPTION
				"Description"
			::= { wsTrapWirelessIds 4 }

		
		-- 1.3.6.1.4.1.388.14.5.1.7.5.5
		wsTrapWirelessIdsSwitchEvent NOTIFICATION-TYPE
			OBJECTS { wsCcRfIdsViolationType, wsCcRfIdsViolCountLastDetWindow }
			STATUS current
			DESCRIPTION 
				"The number of requests from the switch has exceeded the 
				configured threshold for the violation type. 
				
				
				Solution:
				This may be indicative of an attack on your wireless LAN. 
				If the switch is one of your own, it may be experiencing problems. 
				
				Other Possibilities:
				The threshold may be set too low, make it higher.
				"
			::= { wsTrapWirelessIds 5 }

		
		-- 1.3.6.1.4.1.388.14.5.1.7.5.6
		wsTrapEnableWirelessIdsSwitchEvent OBJECT-TYPE
			SYNTAX TruthValue
			MAX-ACCESS read-write
			STATUS current
			DESCRIPTION
				"To be added."
			::= { wsTrapWirelessIds 6 }

		
--  1.3.6.1.4.1.388.14.5.1.7.5.5
		-- 1.3.6.1.4.1.388.14.5.1.7.5.7
		wsTrapEnableAllWirelessIdsTrap OBJECT-TYPE
			SYNTAX DoActionNow
			MAX-ACCESS read-write
			STATUS current
			DESCRIPTION
				"Description."
			::= { wsTrapWirelessIds 7 }

		
--  1.3.6.1.4.1.388.14.5.1.7.5.6
		-- 1.3.6.1.4.1.388.14.5.1.7.5.8
		wsTrapDisableAllWirelessIdsTrap OBJECT-TYPE
			SYNTAX DoActionNow
			MAX-ACCESS read-write
			STATUS current
			DESCRIPTION
				"Description."
			::= { wsTrapWirelessIds 8 }

		
--  1.3.6.1.4.1.388.14.5.1.7.6
		-- 1.3.6.1.4.1.388.14.5.1.7.6
		wsTrapWirelessStat OBJECT IDENTIFIER ::= { wsTrapWireless 6 }

		
--  1.3.6.1.4.1.388.14.5.1.7.6.1
		-- 1.3.6.1.4.1.388.14.5.1.7.6.1
		wsTrapWirelessStatWlanName OBJECT-TYPE
			SYNTAX OCTET STRING
			MAX-ACCESS accessible-for-notify
			STATUS current
			DESCRIPTION
				"Description."
			::= { wsTrapWirelessStat 1 }

		
--  1.3.6.1.4.1.388.14.5.1.7.6.2
		-- 1.3.6.1.4.1.388.14.5.1.7.6.2
		wsTrapWirelessStatMuIPAddr OBJECT-TYPE
			SYNTAX IpAddress
			MAX-ACCESS accessible-for-notify
			STATUS current
			DESCRIPTION
				"Description."
			::= { wsTrapWirelessStat 2 }

		
--  1.3.6.1.4.1.388.14.5.1.7.6.3
		-- 1.3.6.1.4.1.388.14.5.1.7.6.3
		wsTrapWirelessStatPortalMac OBJECT-TYPE
			SYNTAX PhysAddress
			MAX-ACCESS accessible-for-notify
			STATUS current
			DESCRIPTION
				"Description."
			::= { wsTrapWirelessStat 3 }

		
--  1.3.6.1.4.1.388.14.5.1.7.6.4
		-- 1.3.6.1.4.1.388.14.5.1.7.6.4
		wsTrapWirelessStatStation NOTIFICATION-TYPE
			OBJECTS { wsCcStatsTrapCtrlConfIndex, wsTrapWirelessStatMuIPAddr, wsCcStatsMuMac, wsCcStatsTrapCtrlConfUnits, wsCcStatsTrapCtrlConfThresholdMus
				 }
			STATUS current
			DESCRIPTION 
				"This trap is generated when the user set values are 
				violated for the station.
				
				Solution:
				Check the stations for proper operation.
				
				Other Possibilities: 
				None.
				"
			::= { wsTrapWirelessStat 4 }

		
--  1.3.6.1.4.1.388.14.5.1.7.6.6
		-- 1.3.6.1.4.1.388.14.5.1.7.6.6
		wsTrapWirelessStatRadio NOTIFICATION-TYPE
			OBJECTS { wsCcStatsTrapCtrlConfThresholdPortals, wsCcStatsTrapCtrlConfUnits, wsCcStatsTrapCtrlConfIndex, wsCcStatsRadioIndex }
			STATUS current
			DESCRIPTION 
				"This trap is generated when the user set values are violated
				for the radio.
				
				Solution:
				Check the stations for proper operation.
				
				Other Possibilities: 
				None."
			::= { wsTrapWirelessStat 6 }

		
--  1.3.6.1.4.1.388.14.5.1.7.6.8
		-- 1.3.6.1.4.1.388.14.5.1.7.6.8
		wsTrapWirelessStatWlan NOTIFICATION-TYPE
			OBJECTS { wsCcStatsTrapCtrlConfIndex, wsCcStatsTrapCtrlConfUnits, wsCcStatsTrapCtrlConfThresholdWlans, wsTrapWirelessStatWlanName }
			STATUS current
			DESCRIPTION 
				"This trap is generated when the user set values are violated
				for the wlan.
				
				Solution:
				Check the wlan for proper operation.
				
				Other Possibilities: 
				None."
			::= { wsTrapWirelessStat 8 }

		
--  1.3.6.1.4.1.388.14.5.1.7.6.10
		-- 1.3.6.1.4.1.388.14.5.1.7.6.10
		wsTrapWirelessStatModule NOTIFICATION-TYPE
			OBJECTS { wsCcStatsTrapCtrlConfIndex, wsCcStatsTrapCtrlConfThresholdSwitch, wsCcStatsTrapCtrlConfUnits }
			STATUS current
			DESCRIPTION 
				"This trap is generated when the user set values are violated 
				for the wlan-module.
				
				Solution:
				Check the wlan-module for proper operation.
				
				Other Possibilities: 
				None."
			::= { wsTrapWirelessStat 10 }

		
--  1.3.6.1.4.1.388.14.5.1.7.7
		-- 1.3.6.1.4.1.388.14.5.1.7.7
		wsTrapEnableAllWirelessTrap OBJECT-TYPE
			SYNTAX DoActionNow
			MAX-ACCESS read-write
			STATUS current
			DESCRIPTION
				"Description."
			::= { wsTrapWireless 7 }

		
--  1.3.6.1.4.1.388.14.5.1.7.8
		-- 1.3.6.1.4.1.388.14.5.1.7.8
		wsTrapDisableAllWirelessTrap OBJECT-TYPE
			SYNTAX DoActionNow
			MAX-ACCESS read-write
			STATUS current
			DESCRIPTION
				"Description."
			::= { wsTrapWireless 8 }

		
		-- 1.3.6.1.4.1.388.14.5.1.8
		wsTrapMobility OBJECT IDENTIFIER ::= { wsTrapMIB 8 }

		
		-- 1.3.6.1.4.1.388.14.5.1.8.1
		wsTrapMobilityOperUp NOTIFICATION-TYPE
			STATUS current
			DESCRIPTION 
				"Mobility is operationally UP.
				
				Solution: 
				None
				
				Other Possibilities:
				None.
				"
			::= { wsTrapMobility 1 }

		
		-- 1.3.6.1.4.1.388.14.5.1.8.2
		wsTrapEnableMobilityOperUp OBJECT-TYPE
			SYNTAX TruthValue
			MAX-ACCESS read-write
			STATUS current
			DESCRIPTION
				"Description."
			::= { wsTrapMobility 2 }

		
		-- 1.3.6.1.4.1.388.14.5.1.8.3
		wsTrapMobilityOperDown NOTIFICATION-TYPE
			STATUS current
			DESCRIPTION 
				"Mobility is operationally DOWN.
				
				Solution: 
				None
				
				Other Possibilities:
				None.
				"
			::= { wsTrapMobility 3 }

		
		-- 1.3.6.1.4.1.388.14.5.1.8.4
		wsTrapEnableMobilityOperDown OBJECT-TYPE
			SYNTAX TruthValue
			MAX-ACCESS read-write
			STATUS current
			DESCRIPTION
				"Description."
			::= { wsTrapMobility 4 }

		
		-- 1.3.6.1.4.1.388.14.5.1.8.5
		wsTrapMobilityPeerUp NOTIFICATION-TYPE
			OBJECTS { wsSwMobilityPeerIp }
			STATUS current
			DESCRIPTION 
				"Mobility Peer is UP.
				
				Solution: 
				None
				
				Other Possibilities:
				None.
				"
			::= { wsTrapMobility 5 }

		
		-- 1.3.6.1.4.1.388.14.5.1.8.6
		wsTrapEnableMobilityPeerUp OBJECT-TYPE
			SYNTAX TruthValue
			MAX-ACCESS read-write
			STATUS current
			DESCRIPTION
				"Description."
			::= { wsTrapMobility 6 }

		
		-- 1.3.6.1.4.1.388.14.5.1.8.7
		wsTrapMobilityPeerDown NOTIFICATION-TYPE
			OBJECTS { wsSwMobilityPeerIp }
			STATUS current
			DESCRIPTION 
				"Mobility Peer is DOWN.
				
				Solution: 
				Check IP connectivity with Peer IP-address.
				
				Other Possibilities:
				None.
				"
			::= { wsTrapMobility 7 }

		
		-- 1.3.6.1.4.1.388.14.5.1.8.8
		wsTrapEnableMobilityPeerDown OBJECT-TYPE
			SYNTAX TruthValue
			MAX-ACCESS read-write
			STATUS current
			DESCRIPTION
				"Description."
			::= { wsTrapMobility 8 }

		
		-- 1.3.6.1.4.1.388.14.5.1.8.9
		wsTrapEnableAllMobilityTrap OBJECT-TYPE
			SYNTAX DoActionNow
			MAX-ACCESS read-write
			STATUS current
			DESCRIPTION
				"Description."
			::= { wsTrapMobility 9 }

		
		-- 1.3.6.1.4.1.388.14.5.1.8.10
		wsTrapDisableAllMobilityTrap OBJECT-TYPE
			SYNTAX DoActionNow
			MAX-ACCESS read-write
			STATUS current
			DESCRIPTION
				"Description."
			::= { wsTrapMobility 10 }

		
		-- 1.3.6.1.4.1.388.14.5.1.9
		wsSwTrapDHCPServer OBJECT IDENTIFIER ::= { wsTrapMIB 9 }

		
		-- 1.3.6.1.4.1.388.14.5.1.9.1
		wsTrapDHCPServerStarted NOTIFICATION-TYPE
			STATUS current
			DESCRIPTION 
				"DHCP Server is UP.
				
				Solution: 
				None
				
				Other Possibilities:
				None.
				"
			::= { wsSwTrapDHCPServer 1 }

		
		-- 1.3.6.1.4.1.388.14.5.1.9.2
		wsTrapEnableDHCPServerStarted OBJECT-TYPE
			SYNTAX TruthValue
			MAX-ACCESS read-write
			STATUS current
			DESCRIPTION
				"Description."
			::= { wsSwTrapDHCPServer 2 }

		
		-- 1.3.6.1.4.1.388.14.5.1.9.3
		wsTrapDHCPServerStopped NOTIFICATION-TYPE
			STATUS current
			DESCRIPTION 
				"DHCP Server is Down.
				
				Solution: 
				None
				
				Other Possibilities:
				None.
				"
			::= { wsSwTrapDHCPServer 3 }

		
		-- 1.3.6.1.4.1.388.14.5.1.9.4
		wsTrapEnableDHCPServerStopped OBJECT-TYPE
			SYNTAX TruthValue
			MAX-ACCESS read-write
			STATUS current
			DESCRIPTION
				"Description."
			::= { wsSwTrapDHCPServer 4 }

		
		-- 1.3.6.1.4.1.388.14.5.1.9.5
		wsTrapEnableAllDHCPServerTrap OBJECT-TYPE
			SYNTAX DoActionNow
			MAX-ACCESS read-write
			STATUS current
			DESCRIPTION
				"Description."
			::= { wsSwTrapDHCPServer 5 }

		
		-- 1.3.6.1.4.1.388.14.5.1.9.6
		wsTrapDisableAllDHCPServerTrap OBJECT-TYPE
			SYNTAX DoActionNow
			MAX-ACCESS read-write
			STATUS current
			DESCRIPTION
				"Description."
			::= { wsSwTrapDHCPServer 6 }

		
		-- 1.3.6.1.4.1.388.14.5.1.10
		wsSwTrapRadiusServer OBJECT IDENTIFIER ::= { wsTrapMIB 10 }

		
		-- 1.3.6.1.4.1.388.14.5.1.10.1
		wsTrapRadiusServerStarted NOTIFICATION-TYPE
			STATUS current
			DESCRIPTION 
				"Radius Server is UP.
				
				Solution: 
				None
				
				Other Possibilities:
				None.
				"
			::= { wsSwTrapRadiusServer 1 }

		
		-- 1.3.6.1.4.1.388.14.5.1.10.2
		wsTrapEnableRadiusServerStarted OBJECT-TYPE
			SYNTAX TruthValue
			MAX-ACCESS read-write
			STATUS current
			DESCRIPTION
				"Description."
			::= { wsSwTrapRadiusServer 2 }

		
		-- 1.3.6.1.4.1.388.14.5.1.10.3
		wsTrapRadiusServerStopped NOTIFICATION-TYPE
			STATUS current
			DESCRIPTION 
				"Radius Server is Down.
				
				Solution: 
				None
				
				Other Possibilities:
				None.
				"
			::= { wsSwTrapRadiusServer 3 }

		
		-- 1.3.6.1.4.1.388.14.5.1.10.4
		wsTrapEnableRadiusServerStopped OBJECT-TYPE
			SYNTAX TruthValue
			MAX-ACCESS read-write
			STATUS current
			DESCRIPTION
				"Description."
			::= { wsSwTrapRadiusServer 4 }

		
		-- 1.3.6.1.4.1.388.14.5.1.10.5
		wsTrapEnableAllRadiusServerTrap OBJECT-TYPE
			SYNTAX DoActionNow
			MAX-ACCESS read-write
			STATUS current
			DESCRIPTION
				"Description."
			::= { wsSwTrapRadiusServer 5 }

		
		-- 1.3.6.1.4.1.388.14.5.1.10.6
		wsTrapDisableAllRadiusServerTrap OBJECT-TYPE
			SYNTAX DoActionNow
			MAX-ACCESS read-write
			STATUS current
			DESCRIPTION
				"Description."
			::= { wsSwTrapRadiusServer 6 }

		
		-- 1.3.6.1.4.1.388.14.5.1.11
		wsTrapEnableAllTrap OBJECT-TYPE
			SYNTAX DoActionNow
			MAX-ACCESS read-write
			STATUS current
			DESCRIPTION
				"Enables trap flags for all the traps
				applicable to the system."
			::= { wsTrapMIB 11 }

		
		-- 1.3.6.1.4.1.388.14.5.1.12
		wsTrapDisableAllTrap OBJECT-TYPE
			SYNTAX DoActionNow
			MAX-ACCESS read-write
			STATUS current
			DESCRIPTION
				"Disables trap flags for all the traps
				applicable to the system."
			::= { wsTrapMIB 12 }

		
--  1.3.6.1.4.1.388.14.5.3
		-- 1.3.6.1.4.1.388.14.5.1.13
		wsTrapGlobalEnableFlag OBJECT-TYPE
			SYNTAX TruthValue
			MAX-ACCESS read-write
			STATUS current
			DESCRIPTION
				"This is a global variable which determines whether to send
				(or not) any of the system trap. 
				
				When this flag is set to 'true', all the traps which are 
				enabled and have their trap condition met are sent out.
				
				When this flag is set to 'false', no trap is sent out even if
				its own flag is enabled."
			::= { wsTrapMIB 13 }

		
--  1.3.6.1.4.1.388.14.5.100
		-- 1.3.6.1.4.1.388.14.5.100
		wsTrapConformance OBJECT IDENTIFIER ::= { wsTrap 100 }

		
--  1.3.6.1.4.1.388.14.5.100.1
		-- 1.3.6.1.4.1.388.14.5.100.1
		wsTrapCompliances OBJECT IDENTIFIER ::= { wsTrapConformance 1 }

		
--  1.3.6.1.4.1.388.14.5.100.1.1
-- this module
		-- 1.3.6.1.4.1.388.14.5.100.1.1
		wsTrapCompliance MODULE-COMPLIANCE
			STATUS current
			DESCRIPTION 
				"Description."
			MODULE -- this module
				MANDATORY-GROUPS { wsTrapGroup }
			::= { wsTrapCompliances 1 }

		
--  1.3.6.1.4.1.388.14.5.100.2
		-- 1.3.6.1.4.1.388.14.5.100.2
		wsNotificationGroups OBJECT IDENTIFIER ::= { wsTrapConformance 2 }

		
--  1.3.6.1.4.1.388.14.5.100.2.1
		-- 1.3.6.1.4.1.388.14.5.100.2.1
		wsNotificationGroup NOTIFICATION-GROUP
			NOTIFICATIONS { wsTrapWirelessStationAssociated, wsTrapWirelessStationDisassociated, wsTrapWirelessStationDeniedAssociationOnCapability, wsTrapWirelessStationDeniedAssociationOnShortPreamble, wsTrapWirelessStationDeniedAssociationOnSpectrum, 
				wsTrapWirelessStationDeniedAssociationOnErr, wsTrapWirelessStationDeniedAssociationOnSSID, wsTrapWirelessStationDeniedAssociationOnRates, wsTrapWirelessStationDeniedAssociationOnInvalidWPA, wsTrapWirelessStationDeniedAssociationAsPortCapacityReached, 
				wsTrapWirelessStationTkipCounterMeasures, wsTrapWirelessStationDeniedAuthentication, wsTrapWirelessStationRadiusAuthFailed, wsTrapWirelessStatStation, wsTrapWirelessStatRadio, 
				wsTrapWirelessStatWlan, wsTrapWirelessStatModule, wsTrapWirelessRadioAdopted, wsTrapWirelessRadioUnadopted, wsTrapWirelessRadioDetectedRadar, 
				wsTrapWirelessSelfHealActivate, wsTrapSnmpColdStart, wsTrapSnmpAuthenticationFail, wsTrapSnmpLinkUp, wsTrapSnmpLinkDown, 
				wsTrapClusterMemberUp, wsTrapClusterMemberDown, wsTrapClusterMemberMisConfigured, wsTrapClusterAdoptionExceeded, wsTrapClusterLicenseChanged, 
				wsTrapMiscSavedConfigModified, wsTrapMobilityOperUp, wsTrapMobilityOperDown, wsTrapMobilityPeerUp, wsTrapMobilityPeerDown, 
				wsTrapDHCPServerStopped, wsTrapDHCPServerStarted, wsTrapRadiusServerStopped, wsTrapRadiusServerStarted, wsTrapWirelessIdsMuEvent, 
				wsTrapWirelessIdsRadioEvent, wsTrapWirelessIdsSwitchEvent, wsTrapWirelessUnapprovedAPDetected, wsTrapMiscCaCertExpired, wsTrapWirelessUnapprovedAPRemoved, 
				wsTrapMiscPeriodicHeartbeat, wsTrapDiagTempHigh, wsTrapDiagTempOver, wsTrapDiagFanSpeedLow, wsTrapDiagRamFree, 
				wsTrapDiagProcMemUsage, wsTrapDiagPktBuf, wsTrapDiagIpRouteCache, wsTrapDiagFileDesc, wsTrapMiscLowFileSystemSpace, 
				wsTrapNsmDhcpIPChanged, wsTrapMiscProcessMaxRestartsReached, wsTrapMiscServerCertExpired, wsTrapDiagResCpuLoad1Min, wsTrapDiagResCpuLoad5Min, 
				wsTrapDiagResCpuLoad15Min, wsTrapDiagUsedKernBuff }
			STATUS current
			DESCRIPTION 
				"Description."
			::= { wsNotificationGroups 1 }

		
--  1.3.6.1.4.1.388.14.5.100.3
		-- 1.3.6.1.4.1.388.14.5.100.3
		wsTrapGroups OBJECT IDENTIFIER ::= { wsTrapConformance 3 }

		
--  1.3.6.1.4.1.388.14.5.100.3.2
		-- 1.3.6.1.4.1.388.14.5.100.3.2
		wsTrapGroup OBJECT-GROUP
			OBJECTS { wsTrapWirelessStationMac, wsTrapWirelessStationRadioNum, wsTrapWirelessStationLimitOnRadio, wsTrapWirelessRadioName, wsTrapWirelessRadioChannelNum, 
				wsTrapEnableAllWirelessStationTrap, wsTrapEnableAllWirelessIdsTrap, wsTrapEnableAllWirelessRadioTrap, wsTrapEnableAllWirelessSelfHealTrap, wsTrapEnableAllWirelessTrap, 
				wsTrapEnableSnmpLinkUp, wsTrapEnableSnmpLinkDown, wsTrapEnableAllSnmpTrap, wsTrapEnableClusterMemberUp, wsTrapEnableClusterMemberDown, 
				wsTrapEnableClusterMemberMisConfig, wsTrapEnableClusterAdoptionExceeded, wsTrapEnableClusterLicChanged, wsTrapEnableNsmDhcpIPChanged, wsTrapEnableMiscProcMaxRestart, 
				wsTrapEnableSnmpColdStart, wsTrapEnableSnmpAuthFail, wsTrapEnableWirelessStationAssoc, wsTrapEnableWirelessStationDisAssoc, wsTrapEnableWirelessStationDenAssocOnCap, 
				wsTrapEnableWirelessStationDenAssocOnShortPmbl, wsTrapEnableWirelessStationDenAssocOnSpectrum, wsTrapEnableWirelessStationDenAssocOnErr, wsTrapEnableWirelessStationDenAssocOnSSID, wsTrapEnableWirelessStationDenAssocOnRates, 
				wsTrapEnableWirelessStationDenAssocOnInvalidWPA, wsTrapEnableWirelessStationDenAssocAsPortCapReached, wsTrapEnableWirelessStationTkipCntMeasures, wsTrapEnableWirelessStationDenAuth, wsTrapEnableWirelessStationRadAuthFail, 
				wsTrapEnableWirelessRadioAdopted, wsTrapEnableWirelessRadioUnadopted, wsTrapEnableWirelessRadioDetectedRadar, wsTrapEnableWirelessSelfHealActivate, wsTrapEnableAllClusterTrap, 
				wsTrapEnableAllNsmTrap, wsTrapEnableAllMiscTrap, wsTrapWirelessAPMac, wsTrapWirelessStatWlanName, wsTrapWirelessStatMuIPAddr, 
				wsTrapWirelessStatPortalMac, wsTrapDisableAllWirelessTrap, wsTrapNsmIfDescr, wsTrapNsmIpAdEntAddr, wsTrapNsmIpAdEntNetMask, 
				wsTrapDisableAllSnmpTrap, wsTrapDisableAllNsmTrap, wsTrapDisableAllClusterTrap, wsTrapDisableAllMiscTrap, wsTrapDisableAllWirelessStationTrap, 
				wsTrapDisableAllWirelessRadioTrap, wsTrapDisableAllWirelessSelfHealTrap, wsTrapDisableAllWirelessIdsTrap, wsTrapEnableAllTrap, wsTrapDisableAllTrap, 
				wsTrapEnableMobilityOperUp, wsTrapEnableMobilityOperDown, wsTrapEnableMobilityPeerUp, wsTrapEnableMobilityPeerDown, wsTrapEnableAllMobilityTrap, 
				wsTrapDisableAllMobilityTrap, wsTrapDisableAllDHCPServerTrap, wsTrapEnableAllDHCPServerTrap, wsTrapEnableDHCPServerStarted, wsTrapDisableAllRadiusServerTrap, 
				wsTrapEnableAllRadiusServerTrap, wsTrapEnableRadiusServerStopped, wsTrapEnableRadiusServerStarted, wsTrapEnableWirelessIdsMuEvent, wsTrapEnableWirelessIdsRadioEvent, 
				wsTrapEnableWirelessIdsSwitchEvent, wsTrapEnableWirelessUnapprovedAPDetected, wsTrapEnableAllWirelessUnapprovedAPTrap, wsTrapDisableAllWirelessUnapprovedAPTrap, wsTrapGlobalEnableFlag, 
				wsTrapEnableMiscLowFileSystemSpace, wsTrapEnableMiscSavedConfigModified, wsTrapEnableMiscCaCertExpired, wsTrapEnableWirelessUnapprovedAPRemoved, wsTrapEnableMiscPeriodicHeartbeat, 
				wsTrapEnableDHCPServerStopped, wsTrapEnableDiagResCpuLoad1Min, wsTrapEnableDiagResCpuLoad5Min, wsTrapEnableDiagResCpuLoad15Min, wsTrapEnableUsedKernBuff, 
				wsTrapDiagUsedKernBuffSize, wsTrapDiagUsedKernBuffUsed, wsTrapDiagUsedKernBuffLimit, wsTrapEnableAllDiagTrap, wsTrapDisableAllDiagTrap, 
				wsTrapEnableMiscServerCertExpired, wsTrapEnableDiagTempHigh, wsTrapEnableDiagTempOver, wsTrapEnableDiagFanSpeedLow, wsTrapEnableDiagRamFree, 
				wsTrapEnableDiagProcMemUsage, wsTrapEnableDiagPktBuf, wsTrapEnableDiagIpRouteCache, wsTrapEnableDiagFileDesc }
			STATUS current
			DESCRIPTION 
				"Description."
			::= { wsTrapGroups 2 }

		
	
	END

--
-- WS-TRAP-MIB.my
--
