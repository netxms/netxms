-- ============================================================================
-- Copyright (c) 2004-2014 Hangzhou H3C Tech. Co., Ltd.  All rights reserved.
--
-- Description: H3C Product OID MIB
-- Reference: HH3C-OID-MIB
-- Version: V1.55
-- History:
--   V1.00 2006-04-19 Initial version
--   V1.01 2006-05-09
--     Add OID 158 under hh3cProductId by gaolong
--   V1.02 2006-05-18
--     Add OID from 159 to 169 under hh3cProductId by gaolong
--     Add OID from 170 to 175 under hh3cProductId by longyin
--   V1.03 2006-05-31
--     Add OID from 176 to 178 under hh3cProductId by gaolong
--   V1.04 2006-06-08
--     Add OID from 179 to 188 under hh3cProductId by gaolong
--   V1.05 2006-07-14
--     Add OID from 189 to 192 under hh3cProductId by longyin
--   V1.06 2006-07-26
--     Add OID from 193 to 200 under hh3cProductId by gaolong
--   V1.07 2006-08-23
--     Add OID from 201 to 203 under hh3cProductId by gaolong
--   V1.08 2006-09-25
--     Add OID from 204 to 206 under hh3cProductId by gaolong
--   V1.09 2006-10-28
--     Modify name of OID 193 and 194 by gaolong
--   V1.10 2006-11-25
--     Add OID from 207 to 217 under hh3cProductId by gaolong
--   V1.11 2006-12-25
--     Add OEM object Identifier under hh3cProductId by gaolong
--   V1.12 2007-02-01
--     Add OID from 219 to 224 under hh3cProductId by gaolong
--   V1.13 2007-03-07
--     Add OID from 225 to 235 under hh3cProductId by gaolong
--   V1.14 2007-03-28
--     Add OID from 236 to 241 under hh3cProductId by gaolong
--   V1.15 2007-04-26
--     Add OID from 242 to 257 under hh3cProductId by gaolong
--   V1.16 2007-05-28
--     Add OID from 258 to 267 under hh3cProductId by gaolong
--   V1.17 2007-07-02
--     Add OID from 268 to 282 under hh3cProductId by gaolong
--     Remove OID 176 under hh3cProductId by gaolong
--   V1.18 2007-08-08
--     Add OID from 283 to 297 under hh3cProductId by gaolong
--   V1.19 2007-08-25
--     Add OID from 298 to 322 under hh3cProductId by longyin
--   V1.20 2007-09-25
--     Add OID from 323 to 330 under hh3cProductId by longyin
--   V1.21 2007-10-27
--     Add OID from 331 to 341 under hh3cProductId by longyin
--   V1.22 2007-11-26
--     Add OID from 342 to 346 under hh3cProductId by longyin
--   V1.23 2007-12-25
--     Add OID from 347 to 355 under hh3cProductId by longyin
--   V1.24 2008-01-25
--     Add OID from 356 to 370 under hh3cProductId by longyin
--   V1.25 2008-02-27
--     Add OID from 371 to 384 under hh3cProductId by longyin
--   V1.26 2008-03-27
--     Add OID from 385 to 394 under hh3cProductId by longyin
--   V1.27 2008-04-28
--     Modify name of OID 376 and 385 by songhao
--     Add OID from 395 to 414(except 399) under hh3cProductId by songhao
--   V1.28 2008-05-31
--     Modify name of OID 363 by songhao
--     Add OID from 415 to 419 under hh3cProductId by songhao
--   V1.29 2008-06-30
--     Add OID from 420 to 453 under hh3cProductId by songhao
--   V1.30 2008-07-25
--     Add OID from 454 to 459 under hh3cProductId by songhao
--   V1.31 2008-08-28
--     Add OID from 460 to 467 under hh3cProductId by songhao
--   V1.32 2008-10-10
--     Add OID from 468 to 469 under hh3cProductId by songhao
--   V1.33 2008-11-04
--     Add OID from 470 to 477 under hh3cProductId by songhao
--   V1.34 2008-12-01
--     Add OID from 478 to 487 under hh3cProductId by songhao
--   V1.35 2008-12-25
--     Add OID from 488 to 493 under hh3cProductId by shuaixiaojuan
--   V1.36 2009-02-27
--     Add OID from 494 to 505 under hh3cProductId by songhao
--   V1.37 2009-04-10
--     Add OID from 506 to 511 under hh3cProductId by songhao
--     Modify name of OID 505 by songhao
--   V1.38 2009-05-24
--     Add OID from 512 to 531 under hh3cProductId by songhao
--   V1.39 2009-07-03
--     Add OID 532 under hh3cProductId by songhao
--     Modify name of OID 340 and 341 by songhao
--   V1.40 2009-08-28
--     Add OID from 532 to 549 under hh3cProductId by songhao
--   V1.41 2009-11-06
--     Add OID from 550 to 562 under hh3cProductId by songhao
--     Modify name of OID 506 and 507 by songhao
--   V1.42 2009-11-30
--     Add OID from 563 to 571 under hh3cProductId by songhao
--     Modify name of OID 529 and 531 by songhao
--   V1.43 2010-01-11
--     Add OID from 572 to 599 under hh3cProductId by songhao
--   V1.44 2010-08-29 by songhao
--     Added OID from 600 to 649 under hh3cProductId
--     Modified name of OID 552 and 569 under hh3cProductId
--     Removed OID 552 and 553 under hh3cProductId
--     Added OID from 1 to 45 under hpSwitch
--     Added OID from 1 to 23 under hpRouter
--     Added OID from 1 to 3 under hpWireless
--     Added OID from 1 to 14 under hpSecurity
--   V1.45 2011-01-30 by songhao
--     Added OID from 650 to 689 under hh3cProductId
--     Modified name of OID 601 under hh3cProductId
--     Added OID from 46 to 68 under hpSwitch
--     Added OID from 24 to 51 under hpRouter
--     Added OID from 4 to 11 under hpWireless
--     Added OID from 15 to 20 under hpSecurity
--   V1.46 2011-03-10 by songhao
--     Modified name of 615 617 689 under hh3cProductId
--     Removed OID of 616 under hh3cProductId
--     Added OID from 69 to 80 under hpSwitch
--     Added OID 690 to 729 under hh3cProductId
--     Modified name of 11 to 15 under hpSwitch
--     Removed all hyphens under hpNetworking
--   V1.47 2011-04-22 by songhao
--     Added OID from 730 to 742 under hh3cProductId
--     Modified name of 16 to 23, 46 to 47, 62, 65 to 68 under hpSwitch
--     Added OID from 81 to 99 under hpSwitch
--     Added OID from 12 to 14 under hpWireless
--   V1.48 2011-06-30 by songhao
--     Added OID 743 to 747 under hh3cProductId
--     Added OID 100 to 107 under hpSwitch
--     Added OID 15 under hpWireless
--     Added OID 52 to 54 under hpRouter
--     Modified name of 24 to 38, 68 to 77 under hpSwitch
--     Modified name of 12 to 14 under hpWireless
--   V1.49 2011-08-31 by songhao
--     Added 748 under hh3cProductId
--     Modified name of 45, 100 under hpSwitch
--     Added OID 108 to 112 under hpSwitch
--   V1.50 2012-04-22 by songhao
--     Added 749 to 844 under hh3cProductId
--     Modified name of 690, 753 and 754 under hh3cProductId
--     Added OID 114 to 123 under hpSwitch
--     Modified name of 1 to 6, 39 to 45, 51, 78, 86 to 89, 100, 103, 108 to 112 under hpSwitch
--     Added OID 21, 22 under hpSecurity
--     Added OID 55 to 74 under hpRouter
--   V1.51 2013-01-07 by songhao
--     Added OID 845 to 893 under hh3cProductId
--     Added OID 113, 124 to 138 under hpSwitch
--     Added OID 75 to 99 under hpRouter
--     Added OID 16 to 25 under hpWireless
--     Added OID 23 to 24 under hpSecurity
--     Modified name of 842 under hh3cProductId
--     Modified name of 45, 121, 122 under hpSwitch
--     Modified name 55 to 69 under hpRouter
--   V1.52 2013-04-25 by songhao
--     Added OID 894 to 937 under hh3cProductId
--     Added OID 139 to 145 under hpSwitch
--     Added OID 100 to 102 under hpRouter
--     Modified name of 864, 865, 869, 883, 884 under hh3cProductId
--   V1.53 2013-10-09 by songhao
--     Added OID 938 to 1021 under hh3cProductId
--     Modified name of 865, 925 under hh3cProductId
--     Added OID 103 to 107 under hpRouter
--     Modified name 88, 90 under hpRouter
--     Added OID 146 to 150 under hpSwitch
--     Added OID 25 under hpSecurity
--   V1.54 2014-01-27 by songhao
--     Modified name of 1013 under hh3cProductId
--     Added OID 1022 to 1082 under hh3cProductId
--     Added OID 151 to 176 under hpSwitch
--     Added OID 110 under hpRouter
--     Added OID 26 under hpSecurity
--   V1.55 2014-04-27 by songhao
--     Added OID 1083 to 1112 under hh3cProductId
--     Added OID 177 to 204 under hpSwitch
--     Added OID 111 to 117 under hpRouter
--     Added OID 27 under hpSecurity
-- ============================================================================
HH3C-PRODUCT-ID-MIB DEFINITIONS ::= BEGIN
    IMPORTS
        hh3cProductId, hpNetworking
            FROM HH3C-OID-MIB;

-- H3C products

hh3c-s5500-28C-EI                   OBJECT IDENTIFIER ::= { hh3cProductId 1 }
hh3c-s5500-52C-EI                   OBJECT IDENTIFIER ::= { hh3cProductId 2 }
hh3c-s5500-28C-PWR-EI               OBJECT IDENTIFIER ::= { hh3cProductId 3 }
hh3c-s5500-52C-PWR-EI               OBJECT IDENTIFIER ::= { hh3cProductId 4 }
hh3c-s5500-28F-EI                   OBJECT IDENTIFIER ::= { hh3cProductId 5 }
hh3c-s5500-28C-EI-DC                OBJECT IDENTIFIER ::= { hh3cProductId 6 }
hh3c-s6100-20Q-SI                   OBJECT IDENTIFIER ::= { hh3cProductId 7 }
hh3c-s5500-28C-SI                   OBJECT IDENTIFIER ::= { hh3cProductId 8 }
hh3c-s5500-52C-SI                   OBJECT IDENTIFIER ::= { hh3cProductId 9 }
hh3c-s5500-28C-PWR-SI               OBJECT IDENTIFIER ::= { hh3cProductId 10 }
hh3c-s5500-52C-PWR-SI               OBJECT IDENTIFIER ::= { hh3cProductId 11 }
hh3c-s5510-24P                      OBJECT IDENTIFIER ::= { hh3cProductId 12 }
hh3c-s5510-24F                      OBJECT IDENTIFIER ::= { hh3cProductId 13 }
hh3c-s3610-28P                      OBJECT IDENTIFIER ::= { hh3cProductId 14 }
hh3c-s3610-52P                      OBJECT IDENTIFIER ::= { hh3cProductId 15 }
hh3c-s3610-28TP                     OBJECT IDENTIFIER ::= { hh3cProductId 16 }
hh3c-s3610-28F                      OBJECT IDENTIFIER ::= { hh3cProductId 17 }
hh3c-e126                           OBJECT IDENTIFIER ::= { hh3cProductId 18 }
hh3c-e328                           OBJECT IDENTIFIER ::= { hh3cProductId 19 }
hh3c-e352                           OBJECT IDENTIFIER ::= { hh3cProductId 20 }
hh3c-s3100-8C-SI                    OBJECT IDENTIFIER ::= { hh3cProductId 21 }
hh3c-s3100-16C-SI                   OBJECT IDENTIFIER ::= { hh3cProductId 22 }
hh3c-s3100-26C-SI                   OBJECT IDENTIFIER ::= { hh3cProductId 23 }
hh3c-s3100-8T-SI                    OBJECT IDENTIFIER ::= { hh3cProductId 24 }
hh3c-s3100-16T-SI                   OBJECT IDENTIFIER ::= { hh3cProductId 25 }
hh3c-s3100-26T-SI                   OBJECT IDENTIFIER ::= { hh3cProductId 26 }
hh3c-s3100-26TP-SI                  OBJECT IDENTIFIER ::= { hh3cProductId 27 }
hh3c-s5100-24P-EI                   OBJECT IDENTIFIER ::= { hh3cProductId 28 }
hh3c-s5100-26C-EI                   OBJECT IDENTIFIER ::= { hh3cProductId 29 }
hh3c-s5100-50C-EI                   OBJECT IDENTIFIER ::= { hh3cProductId 30 }
hh3c-s5100-48P-EI                   OBJECT IDENTIFIER ::= { hh3cProductId 31 }
hh3c-s3600-28P-SI                   OBJECT IDENTIFIER ::= { hh3cProductId 32 }
hh3c-s3600-52P-SI                   OBJECT IDENTIFIER ::= { hh3cProductId 33 }
hh3c-s3600-28TP-SI                  OBJECT IDENTIFIER ::= { hh3cProductId 34 }
hh3c-s3600-28P-PWR-SI               OBJECT IDENTIFIER ::= { hh3cProductId 35 }
hh3c-s3600-52P-PWR-SI               OBJECT IDENTIFIER ::= { hh3cProductId 36 }
hh3c-s3600-28P-EI                   OBJECT IDENTIFIER ::= { hh3cProductId 37 }
hh3c-s3600-52P-EI                   OBJECT IDENTIFIER ::= { hh3cProductId 38 }
hh3c-s3600-28P-PWR-EI               OBJECT IDENTIFIER ::= { hh3cProductId 39 }
hh3c-s3600-52P-PWR-EI               OBJECT IDENTIFIER ::= { hh3cProductId 40 }
hh3c-s3600-28F-EI                   OBJECT IDENTIFIER ::= { hh3cProductId 41 }
hh3c-s5600-26C                      OBJECT IDENTIFIER ::= { hh3cProductId 42 }
hh3c-s5600-50C                      OBJECT IDENTIFIER ::= { hh3cProductId 43 }
hh3c-s5600-26C-PWR                  OBJECT IDENTIFIER ::= { hh3cProductId 44 }
hh3c-s5600-50C-PWR                  OBJECT IDENTIFIER ::= { hh3cProductId 45 }
hh3c-s5600-26F                      OBJECT IDENTIFIER ::= { hh3cProductId 46 }
hh3c-s3600-52G-HI                   OBJECT IDENTIFIER ::= { hh3cProductId 47 }
hh3c-s3600-52P-HI                   OBJECT IDENTIFIER ::= { hh3cProductId 48 }
hh3c-s3600-28G-HI                   OBJECT IDENTIFIER ::= { hh3cProductId 49 }
hh3c-s3600-28P-HI                   OBJECT IDENTIFIER ::= { hh3cProductId 50 }
hh3c-s3600-52M-HI                   OBJECT IDENTIFIER ::= { hh3cProductId 51 }
hh3c-s7502                          OBJECT IDENTIFIER ::= { hh3cProductId 52 }
hh3c-s7503                          OBJECT IDENTIFIER ::= { hh3cProductId 53 }
hh3c-s7506                          OBJECT IDENTIFIER ::= { hh3cProductId 54 }
hh3c-s7506R                         OBJECT IDENTIFIER ::= { hh3cProductId 55 }
hh3c-ar28-09                        OBJECT IDENTIFIER ::= { hh3cProductId 57 }
hh3c-ar28-10                        OBJECT IDENTIFIER ::= { hh3cProductId 58 }
hh3c-ar28-11                        OBJECT IDENTIFIER ::= { hh3cProductId 59 }
hh3c-ar28-12                        OBJECT IDENTIFIER ::= { hh3cProductId 60 }
hh3c-ar28-13                        OBJECT IDENTIFIER ::= { hh3cProductId 61 }
hh3c-ar28-14                        OBJECT IDENTIFIER ::= { hh3cProductId 62 }
hh3c-ar28-30                        OBJECT IDENTIFIER ::= { hh3cProductId 63 }
hh3c-ar28-31                        OBJECT IDENTIFIER ::= { hh3cProductId 64 }
hh3c-ar28-40                        OBJECT IDENTIFIER ::= { hh3cProductId 65 }
hh3c-ar28-80                        OBJECT IDENTIFIER ::= { hh3cProductId 66 }
hh3c-ar46-20                        OBJECT IDENTIFIER ::= { hh3cProductId 67 }
hh3c-ar46-40                        OBJECT IDENTIFIER ::= { hh3cProductId 68 }
hh3c-ar46-80                        OBJECT IDENTIFIER ::= { hh3cProductId 69 }
hh3c-msr20-20                       OBJECT IDENTIFIER ::= { hh3cProductId 70 }
hh3c-msr20-21                       OBJECT IDENTIFIER ::= { hh3cProductId 71 }
hh3c-msr20-40                       OBJECT IDENTIFIER ::= { hh3cProductId 72 }
hh3c-msr30-20                       OBJECT IDENTIFIER ::= { hh3cProductId 73 }
hh3c-msr30-40                       OBJECT IDENTIFIER ::= { hh3cProductId 74 }
hh3c-msr30-60                       OBJECT IDENTIFIER ::= { hh3cProductId 75 }
hh3c-msr50-40                       OBJECT IDENTIFIER ::= { hh3cProductId 76 }
hh3c-msr50-60                       OBJECT IDENTIFIER ::= { hh3cProductId 77 }
hh3c-ar18-21                        OBJECT IDENTIFIER ::= { hh3cProductId 88 }
hh3c-ar18-21A                       OBJECT IDENTIFIER ::= { hh3cProductId 89 }
hh3c-ar18-21B                       OBJECT IDENTIFIER ::= { hh3cProductId 90 }
hh3c-ar18-22                        OBJECT IDENTIFIER ::= { hh3cProductId 91 }
hh3c-ar18-22-8                      OBJECT IDENTIFIER ::= { hh3cProductId 92 }
hh3c-ar18-22S-8                     OBJECT IDENTIFIER ::= { hh3cProductId 93 }
hh3c-ar18-22-24                     OBJECT IDENTIFIER ::= { hh3cProductId 94 }
hh3c-ar18-23-1                      OBJECT IDENTIFIER ::= { hh3cProductId 95 }
hh3c-ar18-23S-1                     OBJECT IDENTIFIER ::= { hh3cProductId 96 }
hh3c-ar18-30E                       OBJECT IDENTIFIER ::= { hh3cProductId 98 }
hh3c-ar18-31E                       OBJECT IDENTIFIER ::= { hh3cProductId 100 }
hh3c-ar18-32E                       OBJECT IDENTIFIER ::= { hh3cProductId 102 }
hh3c-ar18-33                        OBJECT IDENTIFIER ::= { hh3cProductId 103 }
hh3c-ar18-33E                       OBJECT IDENTIFIER ::= { hh3cProductId 104 }
hh3c-ar18-34                        OBJECT IDENTIFIER ::= { hh3cProductId 105 }
hh3c-ar18-34E                       OBJECT IDENTIFIER ::= { hh3cProductId 106 }
hh3c-ar18-35E                       OBJECT IDENTIFIER ::= { hh3cProductId 108 }
hh3c-ar18-63-1                      OBJECT IDENTIFIER ::= { hh3cProductId 109 }
hh3c-secpathF100-C                  OBJECT IDENTIFIER ::= { hh3cProductId 110 }
hh3c-secpathF100-A                  OBJECT IDENTIFIER ::= { hh3cProductId 111 }
hh3c-secpathF100-S                  OBJECT IDENTIFIER ::= { hh3cProductId 112 }
hh3c-secpathF100-E                  OBJECT IDENTIFIER ::= { hh3cProductId 113 }
hh3c-secpathF1000-S                 OBJECT IDENTIFIER ::= { hh3cProductId 114 }
hh3c-secpathF1000-A                 OBJECT IDENTIFIER ::= { hh3cProductId 115 }
hh3c-secpathF1800-A                 OBJECT IDENTIFIER ::= { hh3cProductId 116 }
hh3c-secpathV100-S                  OBJECT IDENTIFIER ::= { hh3cProductId 117 }
hh3c-secpathV1000-A                 OBJECT IDENTIFIER ::= { hh3cProductId 118 }
hh3c-secpathF100-AW                 OBJECT IDENTIFIER ::= { hh3cProductId 119 }
hh3c-secpathF1800-S                 OBJECT IDENTIFIER ::= { hh3cProductId 120 }
hh3c-secpathF1800-E                 OBJECT IDENTIFIER ::= { hh3cProductId 121 }
hh3c-secpoint                       OBJECT IDENTIFIER ::= { hh3cProductId 122 }
hh3c-vg10-10                        OBJECT IDENTIFIER ::= { hh3cProductId 123 }
hh3c-vg10-11                        OBJECT IDENTIFIER ::= { hh3cProductId 124 }
hh3c-vg10-40                        OBJECT IDENTIFIER ::= { hh3cProductId 125 }
hh3c-vg10-41                        OBJECT IDENTIFIER ::= { hh3cProductId 126 }
hh3c-vg21-08                        OBJECT IDENTIFIER ::= { hh3cProductId 127 }
hh3c-vg20-16                        OBJECT IDENTIFIER ::= { hh3cProductId 128 }
hh3c-vg20-32                        OBJECT IDENTIFIER ::= { hh3cProductId 129 }
hh3c-vg80-20                        OBJECT IDENTIFIER ::= { hh3cProductId 130 }
hh3c-xe200                          OBJECT IDENTIFIER ::= { hh3cProductId 131 }
hh3c-xe2000                         OBJECT IDENTIFIER ::= { hh3cProductId 132 }
hh3c-xe7200                         OBJECT IDENTIFIER ::= { hh3cProductId 133 }
hh3c-xe7300                         OBJECT IDENTIFIER ::= { hh3cProductId 134 }
hh3c-xe7500                         OBJECT IDENTIFIER ::= { hh3cProductId 135 }
hh3c-xe7600                         OBJECT IDENTIFIER ::= { hh3cProductId 136 }
hh3c-xe7205                         OBJECT IDENTIFIER ::= { hh3cProductId 137 }
hh3c-xe7305                         OBJECT IDENTIFIER ::= { hh3cProductId 138 }
hh3c-xe7505                         OBJECT IDENTIFIER ::= { hh3cProductId 139 }
hh3c-xe7605                         OBJECT IDENTIFIER ::= { hh3cProductId 140 }
hh3c-neoceanIX1000                  OBJECT IDENTIFIER ::= { hh3cProductId 141 }
hh3c-neoceanEX1000                  OBJECT IDENTIFIER ::= { hh3cProductId 142 }
hh3c-neoceanEX800                   OBJECT IDENTIFIER ::= { hh3cProductId 143 }
hh3c-neoceanIX5000                  OBJECT IDENTIFIER ::= { hh3cProductId 144 }
hh3c-neoceanIV5100                  OBJECT IDENTIFIER ::= { hh3cProductId 145 }
hh3c-neoceanIV5200                  OBJECT IDENTIFIER ::= { hh3cProductId 146 }
hh3c-s9502                          OBJECT IDENTIFIER ::= { hh3cProductId 147 }
hh3c-s9505                          OBJECT IDENTIFIER ::= { hh3cProductId 148 }
hh3c-s9508                          OBJECT IDENTIFIER ::= { hh3cProductId 149 }
hh3c-s9508V                         OBJECT IDENTIFIER ::= { hh3cProductId 150 }
hh3c-s9512                          OBJECT IDENTIFIER ::= { hh3cProductId 151 }
hh3c-sR8812                         OBJECT IDENTIFIER ::= { hh3cProductId 152 }
hh3c-sR8808                         OBJECT IDENTIFIER ::= { hh3cProductId 153 }
hh3c-sR8805                         OBJECT IDENTIFIER ::= { hh3cProductId 154 }
hh3c-sR8802                         OBJECT IDENTIFIER ::= { hh3cProductId 155 }
hh3c-e126-SI                        OBJECT IDENTIFIER ::= { hh3cProductId 156 }
hh3c-vg31-08                        OBJECT IDENTIFIER ::= { hh3cProductId 157 }
hh3c-dr834                          OBJECT IDENTIFIER ::= { hh3cProductId 158 }
hh3c-s7510E                         OBJECT IDENTIFIER ::= { hh3cProductId 159 }
hh3c-s5100-24P-SI                   OBJECT IDENTIFIER ::= { hh3cProductId 160 }
hh3c-s5100-48P-SI                   OBJECT IDENTIFIER ::= { hh3cProductId 161 }
hh3c-s5100-8P-SI                    OBJECT IDENTIFIER ::= { hh3cProductId 162 }
hh3c-s5100-16P-SI                   OBJECT IDENTIFIER ::= { hh3cProductId 163 }
hh3c-s5100-8P-EI                    OBJECT IDENTIFIER ::= { hh3cProductId 164 }
hh3c-s5100-16P-EI                   OBJECT IDENTIFIER ::= { hh3cProductId 165 }
hh3c-s5100-8P-PWR-EI                OBJECT IDENTIFIER ::= { hh3cProductId 166 }
hh3c-s5100-16P-PWR-EI               OBJECT IDENTIFIER ::= { hh3cProductId 167 }
hh3c-s5100-26C-PWR-EI               OBJECT IDENTIFIER ::= { hh3cProductId 168 }
hh3c-s5100-50C-PWR-EI               OBJECT IDENTIFIER ::= { hh3cProductId 169 }
hh3c-s3108TP-EI                     OBJECT IDENTIFIER ::= { hh3cProductId 170 }
hh3c-s3116TP-EI                     OBJECT IDENTIFIER ::= { hh3cProductId 171 }
hh3c-s3126TP-EI                     OBJECT IDENTIFIER ::= { hh3cProductId 172 }
hh3c-s3108TP-EI-PWR                 OBJECT IDENTIFIER ::= { hh3cProductId 173 }
hh3c-s3116TP-EI-PWR                 OBJECT IDENTIFIER ::= { hh3cProductId 174 }
hh3c-s3126TP-EI-PWR                 OBJECT IDENTIFIER ::= { hh3cProductId 175 }
hh3c-s5500M-20C                     OBJECT IDENTIFIER ::= { hh3cProductId 177 }
hh3c-s5500M-20F                     OBJECT IDENTIFIER ::= { hh3cProductId 178 }
hh3c-bR304plus                      OBJECT IDENTIFIER ::= { hh3cProductId 179 }
hh3c-s9505-V5                       OBJECT IDENTIFIER ::= { hh3cProductId 180 }
hh3c-s9512-V5                       OBJECT IDENTIFIER ::= { hh3cProductId 181 }
hh3c-s9508-V5                       OBJECT IDENTIFIER ::= { hh3cProductId 182 }
hh3c-s9508V-V5                      OBJECT IDENTIFIER ::= { hh3cProductId 183 }
hh3c-s9502-V5                       OBJECT IDENTIFIER ::= { hh3cProductId 184 }
hh3c-sR8802-V5                      OBJECT IDENTIFIER ::= { hh3cProductId 185 }
hh3c-sR8805-V5                      OBJECT IDENTIFIER ::= { hh3cProductId 186 }
hh3c-sR8812-V5                      OBJECT IDENTIFIER ::= { hh3cProductId 187 }
hh3c-sR8808-V5                      OBJECT IDENTIFIER ::= { hh3cProductId 188 }
hh3c-s3100-52P                      OBJECT IDENTIFIER ::= { hh3cProductId 189 }
hh3c-e152                           OBJECT IDENTIFIER ::= { hh3cProductId 190 }
hh3c-s2008                          OBJECT IDENTIFIER ::= { hh3cProductId 191 }
hh3c-s2026                          OBJECT IDENTIFIER ::= { hh3cProductId 192 }
hh3c-sr6602                         OBJECT IDENTIFIER ::= { hh3cProductId 193 }
hh3c-sr6608                         OBJECT IDENTIFIER ::= { hh3cProductId 194 }
hh3c-s3100-08TP-EI                  OBJECT IDENTIFIER ::= { hh3cProductId 195 }
hh3c-s3100-08TP-PWR-EI              OBJECT IDENTIFIER ::= { hh3cProductId 196 }
hh3c-s3100-16TP-EI                  OBJECT IDENTIFIER ::= { hh3cProductId 197 }
hh3c-s3100-16TP-PWR-EI              OBJECT IDENTIFIER ::= { hh3cProductId 198 }
hh3c-s3100-26TP-EI                  OBJECT IDENTIFIER ::= { hh3cProductId 199 }
hh3c-s3100-26TP-PWR-EI              OBJECT IDENTIFIER ::= { hh3cProductId 200 }
hh3c-s7502-v5                       OBJECT IDENTIFIER ::= { hh3cProductId 201 }
hh3c-vg80-21                        OBJECT IDENTIFIER ::= { hh3cProductId 202 }
hh3c-vg80-80                        OBJECT IDENTIFIER ::= { hh3cProductId 203 }
hh3c-wcm-wx5002                     OBJECT IDENTIFIER ::= { hh3cProductId 204 }
hh3c-wcm-wcma                       OBJECT IDENTIFIER ::= { hh3cProductId 205 }
hh3c-msr30-10                       OBJECT IDENTIFIER ::= { hh3cProductId 206 }
hh3c-s7502e                         OBJECT IDENTIFIER ::= { hh3cProductId 207 }
hh3c-s7503E                         OBJECT IDENTIFIER ::= { hh3cProductId 208 }
hh3c-s7506E                         OBJECT IDENTIFIER ::= { hh3cProductId 209 }
hh3c-s7506E-V                       OBJECT IDENTIFIER ::= { hh3cProductId 210 }
hh3c-secBlade-FW                    OBJECT IDENTIFIER ::= { hh3cProductId 211 }
hh3c-secBlade-IPSec                 OBJECT IDENTIFIER ::= { hh3cProductId 212 }
hh3c-s3100-8TP-SI                   OBJECT IDENTIFIER ::= { hh3cProductId 213 }
hh3c-s3100-16TP-SI                  OBJECT IDENTIFIER ::= { hh3cProductId 214 }
hh3c-e126A                          OBJECT IDENTIFIER ::= { hh3cProductId 215 }
hh3c-s3100-26TP-SI-B                OBJECT IDENTIFIER ::= { hh3cProductId 216 }
hh3c-msr30-16                       OBJECT IDENTIFIER ::= { hh3cProductId 217 }
-- This object is reserved for OEM. See in HH3C-OEM-PRODUCT-ID-MIB
hh3cOEMProductID                    OBJECT IDENTIFIER ::= { hh3cProductId 218 }
hh3c-s2126-ei                       OBJECT IDENTIFIER ::= { hh3cProductId 219 }
hh3c-e150-si                        OBJECT IDENTIFIER ::= { hh3cProductId 220 }
hh3c-msr30-11                       OBJECT IDENTIFIER ::= { hh3cProductId 221 }
hh3c-neoceanIX3040                  OBJECT IDENTIFIER ::= { hh3cProductId 222 }
hh3c-neoceanIX3080                  OBJECT IDENTIFIER ::= { hh3cProductId 223 }
hh3c-secpathF100-M                  OBJECT IDENTIFIER ::= { hh3cProductId 224 }
hh3c-neoceanVX1500                  OBJECT IDENTIFIER ::= { hh3cProductId 225 }
hh3c-neoceanIX1520                  OBJECT IDENTIFIER ::= { hh3cProductId 226 }
hh3c-neoceanIX1540                  OBJECT IDENTIFIER ::= { hh3cProductId 227 }
hh3c-wcm-wx5002-128ap               OBJECT IDENTIFIER ::= { hh3cProductId 228 }
hh3c-msr20-10                       OBJECT IDENTIFIER ::= { hh3cProductId 229 }
hh3c-msr20-11                       OBJECT IDENTIFIER ::= { hh3cProductId 230 }
hh3c-msr20-13                       OBJECT IDENTIFIER ::= { hh3cProductId 231 }
hh3c-msr20-15                       OBJECT IDENTIFIER ::= { hh3cProductId 232 }
hh3c-neoceanDL1008                  OBJECT IDENTIFIER ::= { hh3cProductId 233 }
hh3c-neoceanDL1008S                 OBJECT IDENTIFIER ::= { hh3cProductId 234 }
hh3c-neoceanDL1012                  OBJECT IDENTIFIER ::= { hh3cProductId 235 }
hh3c-s3610-52m                      OBJECT IDENTIFIER ::= { hh3cProductId 236 }
hh3c-IV5680                         OBJECT IDENTIFIER ::= { hh3cProductId 237 }
hh3c-IV5240                         OBJECT IDENTIFIER ::= { hh3cProductId 238 }
hh3c-F1000-E                        OBJECT IDENTIFIER ::= { hh3cProductId 239 }
hh3c-S5024P                         OBJECT IDENTIFIER ::= { hh3cProductId 240 }
hh3c-S5016P                         OBJECT IDENTIFIER ::= { hh3cProductId 241 }
hh3c-LSQ1FWBSC0                     OBJECT IDENTIFIER ::= { hh3cProductId 242 }
hh3c-LSB1FW2A0                      OBJECT IDENTIFIER ::= { hh3cProductId 243 }
hh3c-S3100-8TP-EI                   OBJECT IDENTIFIER ::= { hh3cProductId 244 }
hh3c-S3100-16TP-EI                  OBJECT IDENTIFIER ::= { hh3cProductId 245 }
hh3c-S3100-26TP-EI                  OBJECT IDENTIFIER ::= { hh3cProductId 246 }
hh3c-ET704                          OBJECT IDENTIFIER ::= { hh3cProductId 247 }
hh3c-ec1001                         OBJECT IDENTIFIER ::= { hh3cProductId 248 }
hh3c-ec1001-hf                      OBJECT IDENTIFIER ::= { hh3cProductId 249 }
hh3c-ec1004-hc                      OBJECT IDENTIFIER ::= { hh3cProductId 250 }
hh3c-ec2004-hf                      OBJECT IDENTIFIER ::= { hh3cProductId 251 }
hh3c-dc1001                         OBJECT IDENTIFIER ::= { hh3cProductId 252 }
hh3c-dm8000                         OBJECT IDENTIFIER ::= { hh3cProductId 253 }
hh3c-vm8000                         OBJECT IDENTIFIER ::= { hh3cProductId 254 }
hh3c-ms8000                         OBJECT IDENTIFIER ::= { hh3cProductId 255 }
hh3c-S3100-52TP                     OBJECT IDENTIFIER ::= { hh3cProductId 256 }
hh3c-msr20-12                       OBJECT IDENTIFIER ::= { hh3cProductId 257 }
hh3c-s1550E                         OBJECT IDENTIFIER ::= { hh3cProductId 258 }
hh3c-s1550                          OBJECT IDENTIFIER ::= { hh3cProductId 259 }
hh3c-s1526-EI                       OBJECT IDENTIFIER ::= { hh3cProductId 260 }
hh3c-msr20-12-T                     OBJECT IDENTIFIER ::= { hh3cProductId 261 }
hh3c-msr20-15-I                     OBJECT IDENTIFIER ::= { hh3cProductId 262 }
hh3c-msr20-15-N                     OBJECT IDENTIFIER ::= { hh3cProductId 263 }
hh3c-wx6100EWPX                     OBJECT IDENTIFIER ::= { hh3cProductId 264 }
hh3c-wx6100LSQ                      OBJECT IDENTIFIER ::= { hh3cProductId 265 }
hh3c-wx6100LSB                      OBJECT IDENTIFIER ::= { hh3cProductId 266 }
hh3c-wx6100SW                       OBJECT IDENTIFIER ::= { hh3cProductId 267 }
hh3c-dl1000                         OBJECT IDENTIFIER ::= { hh3cProductId 268 }
hh3c-dl1000s                        OBJECT IDENTIFIER ::= { hh3cProductId 269 }
hh3c-wa1208e-g                      OBJECT IDENTIFIER ::= { hh3cProductId 270 }
hh3c-wa1208e-dg                     OBJECT IDENTIFIER ::= { hh3cProductId 271 }
hh3c-wa1208e-ag                     OBJECT IDENTIFIER ::= { hh3cProductId 272 }
hh3c-wa1208e-agp                    OBJECT IDENTIFIER ::= { hh3cProductId 273 }
hh3c-S7501M-24T                     OBJECT IDENTIFIER ::= { hh3cProductId 274 }
hh3c-s7501M-24TP                    OBJECT IDENTIFIER ::= { hh3cProductId 275 }
hh3c-s7502M                         OBJECT IDENTIFIER ::= { hh3cProductId 276 }
hh3c-s7503M                         OBJECT IDENTIFIER ::= { hh3cProductId 277 }
hh3c-s7506M                         OBJECT IDENTIFIER ::= { hh3cProductId 278 }
hh3c-s7506M-V                       OBJECT IDENTIFIER ::= { hh3cProductId 279 }
hh3c-s7510M                         OBJECT IDENTIFIER ::= { hh3cProductId 280 }
hh3c-secpathT200                    OBJECT IDENTIFIER ::= { hh3cProductId 281 }
hh3c-secpathT200E                   OBJECT IDENTIFIER ::= { hh3cProductId 282 }
hh3c-cc600                          OBJECT IDENTIFIER ::= { hh3cProductId 283 }
hh3c-wa1208e-gp                     OBJECT IDENTIFIER ::= { hh3cProductId 284 }
hh3c-wb2321e-agp                    OBJECT IDENTIFIER ::= { hh3cProductId 285 }
hh3c-wh2520e-agp                    OBJECT IDENTIFIER ::= { hh3cProductId 286 }
hh3c-ICG2000                        OBJECT IDENTIFIER ::= { hh3cProductId 287 }
hh3c-ICG3000                        OBJECT IDENTIFIER ::= { hh3cProductId 288 }
hh3c-ICG5000                        OBJECT IDENTIFIER ::= { hh3cProductId 289 }
hh3c-S5520TP-SI                     OBJECT IDENTIFIER ::= { hh3cProductId 290 }
hh3c-wa2210-ag                      OBJECT IDENTIFIER ::= { hh3cProductId 291 }
hh3c-wa2220-ag                      OBJECT IDENTIFIER ::= { hh3cProductId 292 }
hh3c-wa2220e-ag                     OBJECT IDENTIFIER ::= { hh3cProductId 293 }
hh3c-wa2210x-g                      OBJECT IDENTIFIER ::= { hh3cProductId 294 }
hh3c-wa2220x-ag                     OBJECT IDENTIFIER ::= { hh3cProductId 295 }
hh3c-wa2220x-agp                    OBJECT IDENTIFIER ::= { hh3cProductId 296 }
hh3c-S3100-52TP-SI                  OBJECT IDENTIFIER ::= { hh3cProductId 297 }
hh3c-secpathASE5000-E               OBJECT IDENTIFIER ::= { hh3cProductId 298 }
hh3c-secpathASE5000-S               OBJECT IDENTIFIER ::= { hh3cProductId 299 }
hh3c-secpathU200-C                  OBJECT IDENTIFIER ::= { hh3cProductId 300 }
hh3c-secpathU200-S                  OBJECT IDENTIFIER ::= { hh3cProductId 301 }
hh3c-secpathU200-A                  OBJECT IDENTIFIER ::= { hh3cProductId 302 }
hh3c-secpathU200-M                  OBJECT IDENTIFIER ::= { hh3cProductId 303 }
hh3c-ec3016-hc                      OBJECT IDENTIFIER ::= { hh3cProductId 304 }
hh3c-dc1001-ff                      OBJECT IDENTIFIER ::= { hh3cProductId 305 }
hh3c-ecr3304-hf                     OBJECT IDENTIFIER ::= { hh3cProductId 306 }
hh3c-ecr3308-hd                     OBJECT IDENTIFIER ::= { hh3cProductId 307 }
hh3c-ecr3316-hc                     OBJECT IDENTIFIER ::= { hh3cProductId 308 }
hh3c-isc3000                        OBJECT IDENTIFIER ::= { hh3cProductId 309 }
hh3c-isc3100                        OBJECT IDENTIFIER ::= { hh3cProductId 310 }
hh3c-vm9000                         OBJECT IDENTIFIER ::= { hh3cProductId 311 }
hh3c-vm5000                         OBJECT IDENTIFIER ::= { hh3cProductId 312 }
hh3c-ms9000-vtdu                    OBJECT IDENTIFIER ::= { hh3cProductId 313 }
hh3c-ms9000-nru                     OBJECT IDENTIFIER ::= { hh3cProductId 314 }
hh3c-ums9005                        OBJECT IDENTIFIER ::= { hh3cProductId 315 }
hh3c-CS2104B                        OBJECT IDENTIFIER ::= { hh3cProductId 316 }
hh3c-CS2106B                        OBJECT IDENTIFIER ::= { hh3cProductId 317 }
hh3c-S5024E                         OBJECT IDENTIFIER ::= { hh3cProductId 318 }
hh3c-S5048E                         OBJECT IDENTIFIER ::= { hh3cProductId 319 }
hh3c-secpathF5000-A                 OBJECT IDENTIFIER ::= { hh3cProductId 320 }
hh3c-neoceanIX3240                  OBJECT IDENTIFIER ::= { hh3cProductId 321 }
hh3c-neoceanIX3620                  OBJECT IDENTIFIER ::= { hh3cProductId 322 }
hh3c-MSA7302                        OBJECT IDENTIFIER ::= { hh3cProductId 323 }
hh3c-MSA7306                        OBJECT IDENTIFIER ::= { hh3cProductId 324 }
hh3c-S7501E                         OBJECT IDENTIFIER ::= { hh3cProductId 325 }
hh3c-S3100-8C-EPON-EI               OBJECT IDENTIFIER ::= { hh3cProductId 326 }
hh3c-S3100-16C-EPON-EI              OBJECT IDENTIFIER ::= { hh3cProductId 327 }
hh3c-S3100-26C-EPON-EI              OBJECT IDENTIFIER ::= { hh3cProductId 328 }
hh3c-secBlade-LSQ1AFCBSC0           OBJECT IDENTIFIER ::= { hh3cProductId 329 }
hh3c-secBlade-LSB1AFC1A0            OBJECT IDENTIFIER ::= { hh3cProductId 330 }
hh3c-secpathF1000-C                 OBJECT IDENTIFIER ::= { hh3cProductId 331 }
hh3c-secpathF100-A-SI               OBJECT IDENTIFIER ::= { hh3cProductId 332 }
hh3c-secpathV100-E                  OBJECT IDENTIFIER ::= { hh3cProductId 333 }
hh3c-S5800-32C                      OBJECT IDENTIFIER ::= { hh3cProductId 334 }
hh3c-S5800-56C                      OBJECT IDENTIFIER ::= { hh3cProductId 335 }
hh3c-S5800-32C-PWR                  OBJECT IDENTIFIER ::= { hh3cProductId 336 }
hh3c-S5800-56C-PWR                  OBJECT IDENTIFIER ::= { hh3cProductId 337 }
hh3c-S5800-60C-PWR                  OBJECT IDENTIFIER ::= { hh3cProductId 338 }
hh3c-S5800-32F                      OBJECT IDENTIFIER ::= { hh3cProductId 339 }
hh3c-S5820X-28C                     OBJECT IDENTIFIER ::= { hh3cProductId 340 }
hh3c-S5820X-28S                     OBJECT IDENTIFIER ::= { hh3cProductId 341 }
hh3c-cc602                          OBJECT IDENTIFIER ::= { hh3cProductId 342 }
hh3c-cr400                          OBJECT IDENTIFIER ::= { hh3cProductId 343 }
hh3c-cc600E                         OBJECT IDENTIFIER ::= { hh3cProductId 344 }
hh3c-secpathT1000-M                 OBJECT IDENTIFIER ::= { hh3cProductId 345 }
hh3c-neoceanVX1540                  OBJECT IDENTIFIER ::= { hh3cProductId 346 }
hh3c-msr50-06                       OBJECT IDENTIFIER ::= { hh3cProductId 347 }
hh3c-secpathACG2000-M               OBJECT IDENTIFIER ::= { hh3cProductId 348 }
hh3c-secBlade-LSQ1ACGASC0           OBJECT IDENTIFIER ::= { hh3cProductId 349 }
hh3c-secBlade-LSB1ACG1A0            OBJECT IDENTIFIER ::= { hh3cProductId 350 }
hh3c-wx3024wcm                      OBJECT IDENTIFIER ::= { hh3cProductId 351 }
hh3c-wx3024lsw                      OBJECT IDENTIFIER ::= { hh3cProductId 352 }
hh3c-wx5004                         OBJECT IDENTIFIER ::= { hh3cProductId 353 }
hh3c-sr6604                         OBJECT IDENTIFIER ::= { hh3cProductId 354 }
hh3c-iag5000-A                      OBJECT IDENTIFIER ::= { hh3cProductId 355 }
hh3c-secBlade-SPE-FWM               OBJECT IDENTIFIER ::= { hh3cProductId 356 }
hh3c-ICG2200                        OBJECT IDENTIFIER ::= { hh3cProductId 357 }
hh3c-S7602                          OBJECT IDENTIFIER ::= { hh3cProductId 358 }
hh3c-S7603                          OBJECT IDENTIFIER ::= { hh3cProductId 359 }
hh3c-S7606                          OBJECT IDENTIFIER ::= { hh3cProductId 360 }
hh3c-S7606-V                        OBJECT IDENTIFIER ::= { hh3cProductId 361 }
hh3c-S7610                          OBJECT IDENTIFIER ::= { hh3cProductId 362 }
hh3c-wa2610e-agn                    OBJECT IDENTIFIER ::= { hh3cProductId 363 }
hh3c-wa2620e-agn                    OBJECT IDENTIFIER ::= { hh3cProductId 364 }
hh3c-wa1208e-g-v5                   OBJECT IDENTIFIER ::= { hh3cProductId 365 }
hh3c-wa1208e-dg-v5                  OBJECT IDENTIFIER ::= { hh3cProductId 366 }
hh3c-wa1208e-ag-v5                  OBJECT IDENTIFIER ::= { hh3cProductId 367 }
hh3c-wa1208e-agp-v5                 OBJECT IDENTIFIER ::= { hh3cProductId 368 }
hh3c-wa1208e-gp-v5                  OBJECT IDENTIFIER ::= { hh3cProductId 369 }
hh3c-S7503E-S                       OBJECT IDENTIFIER ::= { hh3cProductId 370 }
hh3c-secpathIAG2000-A               OBJECT IDENTIFIER ::= { hh3cProductId 371 }
hh3c-secpathT1000-A                 OBJECT IDENTIFIER ::= { hh3cProductId 372 }
hh3c-secpathT1000-S                 OBJECT IDENTIFIER ::= { hh3cProductId 373 }
hh3c-secBlade-EWPX1FWA0             OBJECT IDENTIFIER ::= { hh3cProductId 374 }
hh3c-secBlade-LSQ1NSMSC0            OBJECT IDENTIFIER ::= { hh3cProductId 375 }
hh3c-secBlade-LSQ1AFDBSC0           OBJECT IDENTIFIER ::= { hh3cProductId 376 }
hh3c-secBlade-LSQ1LBSC0             OBJECT IDENTIFIER ::= { hh3cProductId 377 }
hh3c-secBlade-LSB1LB1A0             OBJECT IDENTIFIER ::= { hh3cProductId 378 }
hh3c-neoceanIX1560                  OBJECT IDENTIFIER ::= { hh3cProductId 379 }
hh3c-neoceanEX1500S                 OBJECT IDENTIFIER ::= { hh3cProductId 380 }
hh3c-neoceanEX1520S                 OBJECT IDENTIFIER ::= { hh3cProductId 381 }
hh3c-neoceanEX1540S                 OBJECT IDENTIFIER ::= { hh3cProductId 382 }
hh3c-neoceanEX1560S                 OBJECT IDENTIFIER ::= { hh3cProductId 383 }
hh3c-ET716                          OBJECT IDENTIFIER ::= { hh3cProductId 384 }
hh3c-s3600-2P-OLT                   OBJECT IDENTIFIER ::= { hh3cProductId 385 }
hh3c-ER3200                         OBJECT IDENTIFIER ::= { hh3cProductId 386 }
hh3c-ER3100                         OBJECT IDENTIFIER ::= { hh3cProductId 387 }
hh3c-s9505E                         OBJECT IDENTIFIER ::= { hh3cProductId 388 }
hh3c-s9508E-V                       OBJECT IDENTIFIER ::= { hh3cProductId 389 }
hh3c-s9512E                         OBJECT IDENTIFIER ::= { hh3cProductId 390 }
hh3c-s12508                         OBJECT IDENTIFIER ::= { hh3cProductId 391 }
hh3c-s12518                         OBJECT IDENTIFIER ::= { hh3cProductId 392 }
hh3c-ET708                          OBJECT IDENTIFIER ::= { hh3cProductId 393 }
hh3c-ET724                          OBJECT IDENTIFIER ::= { hh3cProductId 394 }
hh3c-s2008TP-EA                     OBJECT IDENTIFIER ::= { hh3cProductId 395 }
hh3c-s2016TP-EA                     OBJECT IDENTIFIER ::= { hh3cProductId 396 }
hh3c-s2403TP-EA                     OBJECT IDENTIFIER ::= { hh3cProductId 397 }
hh3c-ICG2000-CT                     OBJECT IDENTIFIER ::= { hh3cProductId 398 }
hh3c-S3528P-EA                      OBJECT IDENTIFIER ::= { hh3cProductId 400 }
hh3c-S3552P-EA                      OBJECT IDENTIFIER ::= { hh3cProductId 401 }
hh3c-S3552F-EA                      OBJECT IDENTIFIER ::= { hh3cProductId 402 }
hh3c-S3528F-EA                      OBJECT IDENTIFIER ::= { hh3cProductId 403 }
hh3c-S3528TP-EA                     OBJECT IDENTIFIER ::= { hh3cProductId 404 }
hh3c-secpathAFD1000-A               OBJECT IDENTIFIER ::= { hh3cProductId 405 }
hh3c-secpathF100-C-EI               OBJECT IDENTIFIER ::= { hh3cProductId 406 }
hh3c-ER3260                         OBJECT IDENTIFIER ::= { hh3cProductId 407 }
hh3c-ICG800                         OBJECT IDENTIFIER ::= { hh3cProductId 408 }
hh3c-ICG800g                        OBJECT IDENTIFIER ::= { hh3cProductId 409 }
hh3c-ICG1000                        OBJECT IDENTIFIER ::= { hh3cProductId 410 }
hh3c-ICG1800                        OBJECT IDENTIFIER ::= { hh3cProductId 411 }
hh3c-neoceanIX3240E                 OBJECT IDENTIFIER ::= { hh3cProductId 412 }
hh3c-neoceanIX3620E                 OBJECT IDENTIFIER ::= { hh3cProductId 413 }
hh3c-neoceanIX3640E                 OBJECT IDENTIFIER ::= { hh3cProductId 414 }
hh3c-secpathACG8800-S3              OBJECT IDENTIFIER ::= { hh3cProductId 415 }
hh3c-secpathT5000-S3                OBJECT IDENTIFIER ::= { hh3cProductId 416 }
hh3c-secpathIAG2000-S               OBJECT IDENTIFIER ::= { hh3cProductId 417 }
hh3c-secpathACG8800-S3-NS21S2MSPB0  OBJECT IDENTIFIER ::= { hh3cProductId 418 }
hh3c-secpathT5000-S3-NS11S2MSPB0    OBJECT IDENTIFIER ::= { hh3cProductId 419 }
hh3c-msr3010                        OBJECT IDENTIFIER ::= { hh3cProductId 420 }
hh3c-msr3011E                       OBJECT IDENTIFIER ::= { hh3cProductId 421 }
hh3c-msr3011F                       OBJECT IDENTIFIER ::= { hh3cProductId 422 }
hh3c-secpathT200-A                  OBJECT IDENTIFIER ::= { hh3cProductId 423 }
hh3c-secpathT200-M                  OBJECT IDENTIFIER ::= { hh3cProductId 424 }
hh3c-secpathF100-C2                 OBJECT IDENTIFIER ::= { hh3cProductId 425 }
hh3c-DPtech-FW1000-GE               OBJECT IDENTIFIER ::= { hh3cProductId 426 }
hh3c-DPtech-FW1000-GA               OBJECT IDENTIFIER ::= { hh3cProductId 427 }
hh3c-DPtech-FW1000-GS               OBJECT IDENTIFIER ::= { hh3cProductId 428 }
hh3c-DPtech-FW1000-ME               OBJECT IDENTIFIER ::= { hh3cProductId 429 }
hh3c-DPtech-FW1000-MA               OBJECT IDENTIFIER ::= { hh3cProductId 430 }
hh3c-DPtech-FW1000-MM               OBJECT IDENTIFIER ::= { hh3cProductId 431 }
hh3c-DPtech-FW1000-MC               OBJECT IDENTIFIER ::= { hh3cProductId 432 }
hh3c-DPtech-UTM2000-MA              OBJECT IDENTIFIER ::= { hh3cProductId 433 }
hh3c-DPtech-UTM2000-MM              OBJECT IDENTIFIER ::= { hh3cProductId 434 }
hh3c-DPtech-UTM2000-MS              OBJECT IDENTIFIER ::= { hh3cProductId 435 }
hh3c-DPtech-IPS2000-GM              OBJECT IDENTIFIER ::= { hh3cProductId 436 }
hh3c-DPtech-IPS2000-MM              OBJECT IDENTIFIER ::= { hh3cProductId 437 }
hh3c-sr6616                         OBJECT IDENTIFIER ::= { hh3cProductId 438 }
hh3c-s3620-28TP-EI                  OBJECT IDENTIFIER ::= { hh3cProductId 439 }
hh3c-s3620-28P-EI                   OBJECT IDENTIFIER ::= { hh3cProductId 440 }
hh3c-s3620-52P-EI                   OBJECT IDENTIFIER ::= { hh3cProductId 441 }
hh3c-s3620-28P-PWR-EI               OBJECT IDENTIFIER ::= { hh3cProductId 442 }
hh3c-s3620-52P-PWR-EI               OBJECT IDENTIFIER ::= { hh3cProductId 443 }
hh3c-s3620-28F-EI                   OBJECT IDENTIFIER ::= { hh3cProductId 444 }
hh3c-s3620-52M                      OBJECT IDENTIFIER ::= { hh3cProductId 445 }
hh3c-s3620-52M-DC                   OBJECT IDENTIFIER ::= { hh3cProductId 446 }
hh3c-s3620-28C-EI                   OBJECT IDENTIFIER ::= { hh3cProductId 447 }
hh3c-wa2210e-ge                     OBJECT IDENTIFIER ::= { hh3cProductId 448 }
hh3c-wa2220x-age                    OBJECT IDENTIFIER ::= { hh3cProductId 449 }
hh3c-wa2210x-ge                     OBJECT IDENTIFIER ::= { hh3cProductId 450 }
hh3c-wb2320x-age                    OBJECT IDENTIFIER ::= { hh3cProductId 451 }
hh3c-neoceanEX1540                  OBJECT IDENTIFIER ::= { hh3cProductId 452 }
hh3c-S5810-50S                      OBJECT IDENTIFIER ::= { hh3cProductId 453 }
hh3c-secBlade-LSQ1IPSSC0            OBJECT IDENTIFIER ::= { hh3cProductId 454 }
hh3c-secBlade-LSB1IPS1A0            OBJECT IDENTIFIER ::= { hh3cProductId 455 }
hh3c-ER5100                         OBJECT IDENTIFIER ::= { hh3cProductId 456 }
hh3c-ER5200                         OBJECT IDENTIFIER ::= { hh3cProductId 457 }
hh3c-wx3010wcm                      OBJECT IDENTIFIER ::= { hh3cProductId 458 }
hh3c-wx3010lsw                      OBJECT IDENTIFIER ::= { hh3cProductId 459 }
hh3c-cc652E                         OBJECT IDENTIFIER ::= { hh3cProductId 460 }
hh3c-S5120-20P-SI                   OBJECT IDENTIFIER ::= { hh3cProductId 461 }
hh3c-S5120-28P-SI                   OBJECT IDENTIFIER ::= { hh3cProductId 462 }
hh3c-S5120-52P-SI                   OBJECT IDENTIFIER ::= { hh3cProductId 463 }
hh3c-S5120-28P-EI                   OBJECT IDENTIFIER ::= { hh3cProductId 464 }
hh3c-S5120-52P-EI                   OBJECT IDENTIFIER ::= { hh3cProductId 465 }
hh3c-S5120-28P-LPWR-EI              OBJECT IDENTIFIER ::= { hh3cProductId 466 }
hh3c-S5120-28P-PWR-EI               OBJECT IDENTIFIER ::= { hh3cProductId 467 }
hh3c-wx6100LSR                      OBJECT IDENTIFIER ::= { hh3cProductId 468 }
hh3c-s7506E-S                       OBJECT IDENTIFIER ::= { hh3cProductId 469 }
hh3c-ICG2000B                       OBJECT IDENTIFIER ::= { hh3cProductId 470 }
hh3c-ICG2000C                       OBJECT IDENTIFIER ::= { hh3cProductId 471 }
hh3c-S1626                          OBJECT IDENTIFIER ::= { hh3cProductId 472 }
hh3c-S1650                          OBJECT IDENTIFIER ::= { hh3cProductId 473 }
hh3c-S1626P                         OBJECT IDENTIFIER ::= { hh3cProductId 474 }
hh3c-neoceanIX3620S                 OBJECT IDENTIFIER ::= { hh3cProductId 475 }
hh3c-neoceanIX3080S                 OBJECT IDENTIFIER ::= { hh3cProductId 476 }
hh3c-ER3280g                        OBJECT IDENTIFIER ::= { hh3cProductId 477 }
hh3c-wa2610-agn                     OBJECT IDENTIFIER ::= { hh3cProductId 478 }
hh3c-wa2612-agn                     OBJECT IDENTIFIER ::= { hh3cProductId 479 }
hh3c-secpathT200-S                  OBJECT IDENTIFIER ::= { hh3cProductId 480 }
hh3c-secpathU200-CS                 OBJECT IDENTIFIER ::= { hh3cProductId 481 }
hh3c-secpathU200-CM                 OBJECT IDENTIFIER ::= { hh3cProductId 482 }
hh3c-secpathU200-CA                 OBJECT IDENTIFIER ::= { hh3cProductId 483 }
hh3c-secBlade-LSR1AFC2A1            OBJECT IDENTIFIER ::= { hh3cProductId 484 }
hh3c-secBlade-LSR1FW2A1             OBJECT IDENTIFIER ::= { hh3cProductId 485 }
hh3c-secBlade-LSR1LB1A1             OBJECT IDENTIFIER ::= { hh3cProductId 486 }
hh3c-secBlade-LSR1NSM1A1            OBJECT IDENTIFIER ::= { hh3cProductId 487 }
hh3c-cc650E                         OBJECT IDENTIFIER ::= { hh3cProductId 488 }
hh3c-LSWM1WCM10                     OBJECT IDENTIFIER ::= { hh3cProductId 489 }
hh3c-LSWM1WCM20                     OBJECT IDENTIFIER ::= { hh3cProductId 490 }
hh3c-EWPXM1WCMC0                    OBJECT IDENTIFIER ::= { hh3cProductId 491 }
hh3c-LSWM1IPS10                     OBJECT IDENTIFIER ::= { hh3cProductId 492 }
hh3c-LSWM1FW10                      OBJECT IDENTIFIER ::= { hh3cProductId 493 }
hh3c-secpathF1000-S-EI              OBJECT IDENTIFIER ::= { hh3cProductId 494 }
hh3c-secpathF1000-A-EI              OBJECT IDENTIFIER ::= { hh3cProductId 495 }
hh3c-msr50-06-V5                    OBJECT IDENTIFIER ::= { hh3cProductId 496 }
hh3c-secBlade-LSR1ACG1A1            OBJECT IDENTIFIER ::= { hh3cProductId 497 }
hh3c-secBlade-LSR1IPS1A1            OBJECT IDENTIFIER ::= { hh3cProductId 498 }
hh3c-S7602-S                        OBJECT IDENTIFIER ::= { hh3cProductId 499 }
hh3c-S7603-S                        OBJECT IDENTIFIER ::= { hh3cProductId 500 }
hh3c-S7606-S                        OBJECT IDENTIFIER ::= { hh3cProductId 501 }
hh3c-SSM-s5500G                     OBJECT IDENTIFIER ::= { hh3cProductId 502 }
hh3c-SSM-FIC                        OBJECT IDENTIFIER ::= { hh3cProductId 503 }
hh3c-SSM-MIM                        OBJECT IDENTIFIER ::= { hh3cProductId 504 }
hh3c-ER8300                         OBJECT IDENTIFIER ::= { hh3cProductId 505 }
hh3c-wa2610x-gnp                    OBJECT IDENTIFIER ::= { hh3cProductId 506 }
hh3c-wb2360x-anp                    OBJECT IDENTIFIER ::= { hh3cProductId 507 }
hh3c-wh2530x-dag                    OBJECT IDENTIFIER ::= { hh3cProductId 508 }
hh3c-wa2620-agn                     OBJECT IDENTIFIER ::= { hh3cProductId 509 }
hh3c-cc610E                         OBJECT IDENTIFIER ::= { hh3cProductId 510 }
hh3c-DPtech-FW1000-GT               OBJECT IDENTIFIER ::= { hh3cProductId 511 }
hh3c-s2008TP-EA-SI                  OBJECT IDENTIFIER ::= { hh3cProductId 512 }
hh3c-s2016TP-EA-SI                  OBJECT IDENTIFIER ::= { hh3cProductId 513 }
hh3c-s2403TP-EA-SI                  OBJECT IDENTIFIER ::= { hh3cProductId 514 }
hh3c-S5120-24P-EI                   OBJECT IDENTIFIER ::= { hh3cProductId 515 }
hh3c-S5120-48P-EI                   OBJECT IDENTIFIER ::= { hh3cProductId 516 }
hh3c-S5120-28C-EI                   OBJECT IDENTIFIER ::= { hh3cProductId 517 }
hh3c-S5120-52C-EI                   OBJECT IDENTIFIER ::= { hh3cProductId 518 }
hh3c-S5120-28C-PWR-EI               OBJECT IDENTIFIER ::= { hh3cProductId 519 }
hh3c-S5120-52C-PWR-EI               OBJECT IDENTIFIER ::= { hh3cProductId 520 }
hh3c-wx3008wcm                      OBJECT IDENTIFIER ::= { hh3cProductId 521 }
hh3c-wx3008lsw                      OBJECT IDENTIFIER ::= { hh3cProductId 522 }
hh3c-msr900                         OBJECT IDENTIFIER ::= { hh3cProductId 523 }
hh3c-msr920                         OBJECT IDENTIFIER ::= { hh3cProductId 524 }
hh3c-secBlade-LSQ1IAGSC0            OBJECT IDENTIFIER ::= { hh3cProductId 525 }
hh3c-WX7306                         OBJECT IDENTIFIER ::= { hh3cProductId 526 }
hh3c-WX7310                         OBJECT IDENTIFIER ::= { hh3cProductId 527 }
hh3c-Blade5310                      OBJECT IDENTIFIER ::= { hh3cProductId 528 }
hh3c-Blade55102                     OBJECT IDENTIFIER ::= { hh3cProductId 529 }
hh3c-Blade5512S                     OBJECT IDENTIFIER ::= { hh3cProductId 530 }
hh3c-Blade55110X                    OBJECT IDENTIFIER ::= { hh3cProductId 531 }
hh3c-wa2610e-gnp                    OBJECT IDENTIFIER ::= { hh3cProductId 532 }
hh3c-s3100-26TP-SI-UM               OBJECT IDENTIFIER ::= { hh3cProductId 533 }
hh3c-s3100-52TP-SI-UM               OBJECT IDENTIFIER ::= { hh3cProductId 534 }
hh3c-s5500-24P-SI                   OBJECT IDENTIFIER ::= { hh3cProductId 535 }
hh3c-s5500-48P-SI                   OBJECT IDENTIFIER ::= { hh3cProductId 536 }
hh3c-ME8000                         OBJECT IDENTIFIER ::= { hh3cProductId 537 }
hh3c-ME8600                         OBJECT IDENTIFIER ::= { hh3cProductId 538 }
hh3c-ME5000                         OBJECT IDENTIFIER ::= { hh3cProductId 539 }
hh3c-MG6060                         OBJECT IDENTIFIER ::= { hh3cProductId 540 }
hh3c-MG6050                         OBJECT IDENTIFIER ::= { hh3cProductId 541 }
hh3c-MG6050S                        OBJECT IDENTIFIER ::= { hh3cProductId 542 }
hh3c-MG9010                         OBJECT IDENTIFIER ::= { hh3cProductId 543 }
hh3c-MG9030                         OBJECT IDENTIFIER ::= { hh3cProductId 544 }
hh3c-MG9060                         OBJECT IDENTIFIER ::= { hh3cProductId 545 }
hh3c-neoceanVX1500-DC               OBJECT IDENTIFIER ::= { hh3cProductId 546 }
hh3c-cc620E                         OBJECT IDENTIFIER ::= { hh3cProductId 547 }
hh3c-SIVX-S3628                     OBJECT IDENTIFIER ::= { hh3cProductId 548 }
hh3c-SIVX-S5528                     OBJECT IDENTIFIER ::= { hh3cProductId 549 }
hh3c-SIVX-VS1500                    OBJECT IDENTIFIER ::= { hh3cProductId 550 }
hh3c-neoceanIX2540                  OBJECT IDENTIFIER ::= { hh3cProductId 551 }
hh3c-neoceanVX2500                  OBJECT IDENTIFIER ::= { hh3cProductId 552 }
hh3c-S5120-28P-PWR-SI               OBJECT IDENTIFIER ::= { hh3cProductId 555 }
hh3c-S5120-28P-HPWR-SI              OBJECT IDENTIFIER ::= { hh3cProductId 556 }
hh3c-F1000-E-DC                     OBJECT IDENTIFIER ::= { hh3cProductId 557 }
hh3c-S5028                          OBJECT IDENTIFIER ::= { hh3cProductId 558 }
hh3c-ET824                          OBJECT IDENTIFIER ::= { hh3cProductId 559 }
hh3c-OSM                            OBJECT IDENTIFIER ::= { hh3cProductId 560 }
hh3c-wx5002-v2                      OBJECT IDENTIFIER ::= { hh3cProductId 561 }
hh3c-wx5004-v2                      OBJECT IDENTIFIER ::= { hh3cProductId 562 }
hh3c-secpathT1000-C                 OBJECT IDENTIFIER ::= { hh3cProductId 563 }
hh3c-secBlade-LST1IPS1A1            OBJECT IDENTIFIER ::= { hh3cProductId 564 }
hh3c-secBlade-LST1FW2A1             OBJECT IDENTIFIER ::= { hh3cProductId 565 }
hh3c-secBlade-LST1LB1A1             OBJECT IDENTIFIER ::= { hh3cProductId 566 }
hh3c-secBlade-LST1NSM1A1            OBJECT IDENTIFIER ::= { hh3cProductId 567 }
hh3c-secBlade-EWPX2IAGSC0           OBJECT IDENTIFIER ::= { hh3cProductId 568 }
hh3c-F1000-A-EI                     OBJECT IDENTIFIER ::= { hh3cProductId 569 }
hh3c-wx6108E                        OBJECT IDENTIFIER ::= { hh3cProductId 570 }
hh3c-wx6112E                        OBJECT IDENTIFIER ::= { hh3cProductId 571 }
hh3c-s5500-34C-HI                   OBJECT IDENTIFIER ::= { hh3cProductId 572 }
hh3c-s5500-58C-HI                   OBJECT IDENTIFIER ::= { hh3cProductId 573 }
hh3c-wa1208e-gp-h20                 OBJECT IDENTIFIER ::= { hh3cProductId 574 }
hh3c-S5120-9P-SI                    OBJECT IDENTIFIER ::= { hh3cProductId 575 }
hh3c-S5120-9P-PWR-SI                OBJECT IDENTIFIER ::= { hh3cProductId 576 }
hh3c-S5120-9P-HPWR-SI               OBJECT IDENTIFIER ::= { hh3cProductId 577 }
hh3c-e528                           OBJECT IDENTIFIER ::= { hh3cProductId 578 }
hh3c-e552                           OBJECT IDENTIFIER ::= { hh3cProductId 579 }
hh3c-s3600V2-28TP-EI                OBJECT IDENTIFIER ::= { hh3cProductId 580 }
hh3c-s3600V2-52TP-EI                OBJECT IDENTIFIER ::= { hh3cProductId 581 }
hh3c-s3600V2-28TP-PWR-EI            OBJECT IDENTIFIER ::= { hh3cProductId 582 }
hh3c-s3600V2-52TP-PWR-EI            OBJECT IDENTIFIER ::= { hh3cProductId 583 }
hh3c-s3600V2-28F-EI                 OBJECT IDENTIFIER ::= { hh3cProductId 584 }
hh3c-s3600V2-28TP-SI                OBJECT IDENTIFIER ::= { hh3cProductId 585 }
hh3c-s3600V2-52TP-SI                OBJECT IDENTIFIER ::= { hh3cProductId 586 }
hh3c-s3600V2-28TP-PWR-SI            OBJECT IDENTIFIER ::= { hh3cProductId 587 }
hh3c-s3600V2-52TP-PWR-SI            OBJECT IDENTIFIER ::= { hh3cProductId 588 }
hh3c-s3500V2-28TP-EA                OBJECT IDENTIFIER ::= { hh3cProductId 589 }
hh3c-s3500V2-52TP-EA                OBJECT IDENTIFIER ::= { hh3cProductId 590 }
hh3c-s3500V2-28F-EA                 OBJECT IDENTIFIER ::= { hh3cProductId 591 }
hh3c-s3500V2-28TP-SI                OBJECT IDENTIFIER ::= { hh3cProductId 592 }
hh3c-s3500V2-52TP-SI                OBJECT IDENTIFIER ::= { hh3cProductId 593 }
hh3c-s9508E                         OBJECT IDENTIFIER ::= { hh3cProductId 594 }
hh3c-s12504                         OBJECT IDENTIFIER ::= { hh3cProductId 595 }
hh3c-ICG2000B-GT                    OBJECT IDENTIFIER ::= { hh3cProductId 596 }
hh3c-ICG3000B                       OBJECT IDENTIFIER ::= { hh3cProductId 597 }
hh3c-ICG3000S                       OBJECT IDENTIFIER ::= { hh3cProductId 598 }
hh3c-ICG5000B                       OBJECT IDENTIFIER ::= { hh3cProductId 599 }
hh3c-wh2640X-agnp                   OBJECT IDENTIFIER ::= { hh3cProductId 600 }
hh3c-wa2620X-agnp                   OBJECT IDENTIFIER ::= { hh3cProductId 601 }
hh3c-s3100-16TP-PWR-EI-F            OBJECT IDENTIFIER ::= { hh3cProductId 602 }
hh3c-cr16018                        OBJECT IDENTIFIER ::= { hh3cProductId 603 }
hh3c-cr16008                        OBJECT IDENTIFIER ::= { hh3cProductId 604 }
hh3c-cr16004                        OBJECT IDENTIFIER ::= { hh3cProductId 605 }
hh3c-F1000-A-SI                     OBJECT IDENTIFIER ::= { hh3cProductId 606 }
hh3c-F1000-E-SI                     OBJECT IDENTIFIER ::= { hh3cProductId 607 }
hh3c-secBlade-LST1ACG1A1            OBJECT IDENTIFIER ::= { hh3cProductId 608 }
hh3c-secBlade-SPE-IPS               OBJECT IDENTIFIER ::= { hh3cProductId 609 }
hh3c-secBlade-SPE-ACG               OBJECT IDENTIFIER ::= { hh3cProductId 610 }
hh3c-wx6103                         OBJECT IDENTIFIER ::= { hh3cProductId 611 }
hh3c-LSQ1WCMD0                      OBJECT IDENTIFIER ::= { hh3cProductId 612 }
hh3c-EWPX2WCMD0                     OBJECT IDENTIFIER ::= { hh3cProductId 613 }
hh3c-LSR1WCM3A1                     OBJECT IDENTIFIER ::= { hh3cProductId 614 }
hh3c-S5830-52SC                     OBJECT IDENTIFIER ::= { hh3cProductId 615 }
hh3c-S5830-106S                     OBJECT IDENTIFIER ::= { hh3cProductId 617 }
hh3c-ET814                          OBJECT IDENTIFIER ::= { hh3cProductId 618 }
hh3c-S5120-28P-LI                   OBJECT IDENTIFIER ::= { hh3cProductId 619 }
hh3c-S5120-52P-LI                   OBJECT IDENTIFIER ::= { hh3cProductId 620 }
hh3c-secBlade-IM-FW-II              OBJECT IDENTIFIER ::= { hh3cProductId 621 }
hh3c-secBlade-IM-LB                 OBJECT IDENTIFIER ::= { hh3cProductId 622 }
hh3c-secBlade-IM-SSL                OBJECT IDENTIFIER ::= { hh3cProductId 623 }
hh3c-ER2210C                        OBJECT IDENTIFIER ::= { hh3cProductId 625 }
hh3c-VCX-Connect-100                OBJECT IDENTIFIER ::= { hh3cProductId 626 }
hh3c-VCX-Connect-200                OBJECT IDENTIFIER ::= { hh3cProductId 627 }
hh3c-VCX-V7005                      OBJECT IDENTIFIER ::= { hh3cProductId 628 }
hh3c-VCX-V7205                      OBJECT IDENTIFIER ::= { hh3cProductId 629 }
hh3c-VCX-MIM                        OBJECT IDENTIFIER ::= { hh3cProductId 630 }
hh3c-VCX-Connect-MIM-Primary        OBJECT IDENTIFIER ::= { hh3cProductId 631 }
hh3c-VCX-Connect-MIM-Secondary      OBJECT IDENTIFIER ::= { hh3cProductId 632 }
hh3c-VCX-V7310                      OBJECT IDENTIFIER ::= { hh3cProductId 633 }
hh3c-secBlade-IM-IPS                OBJECT IDENTIFIER ::= { hh3cProductId 634 }
hh3c-secBlade-IM-ACG                OBJECT IDENTIFIER ::= { hh3cProductId 635 }
hh3c-s7508E-X                       OBJECT IDENTIFIER ::= { hh3cProductId 636 }
hh3c-s10504                         OBJECT IDENTIFIER ::= { hh3cProductId 637 }
hh3c-s10508                         OBJECT IDENTIFIER ::= { hh3cProductId 638 }
hh3c-s10508-V                       OBJECT IDENTIFIER ::= { hh3cProductId 639 }
hh3c-secBlade-SPE-FWM-200           OBJECT IDENTIFIER ::= { hh3cProductId 640 }
hh3c-secpathF1000-S-AI              OBJECT IDENTIFIER ::= { hh3cProductId 641 }
hh3c-wx3024e-wcm                    OBJECT IDENTIFIER ::= { hh3cProductId 642 }
hh3c-wx3024e-lsw                    OBJECT IDENTIFIER ::= { hh3cProductId 643 }
hh3c-ER2100                         OBJECT IDENTIFIER ::= { hh3cProductId 644 }
hh3c-S5820X-34TC                    OBJECT IDENTIFIER ::= { hh3cProductId 645 }
hh3c-S5820X-34SC                    OBJECT IDENTIFIER ::= { hh3cProductId 646 }
hh3c-S5820X-34C                     OBJECT IDENTIFIER ::= { hh3cProductId 647 }
hh3c-S5820X-64SC                    OBJECT IDENTIFIER ::= { hh3cProductId 648 }
hh3c-cc720E                         OBJECT IDENTIFIER ::= { hh3cProductId 649 }
hh3c-S2126T                         OBJECT IDENTIFIER ::= { hh3cProductId 650 }
hh3c-S5800-54S                      OBJECT IDENTIFIER ::= { hh3cProductId 651 }
hh3c-S5820X-26S                     OBJECT IDENTIFIER ::= { hh3cProductId 652 }
hh3c-S3100V2-8TP-SI                 OBJECT IDENTIFIER ::= { hh3cProductId 653 }
hh3c-S3100V2-16TP-SI                OBJECT IDENTIFIER ::= { hh3cProductId 654 }
hh3c-S3100V2-26TP-SI                OBJECT IDENTIFIER ::= { hh3cProductId 655 }
hh3c-E126B                          OBJECT IDENTIFIER ::= { hh3cProductId 656 }
hh3c-S3100V2-8TP-EI                 OBJECT IDENTIFIER ::= { hh3cProductId 657 }
hh3c-S3100V2-16TP-EI                OBJECT IDENTIFIER ::= { hh3cProductId 658 }
hh3c-S3100V2-26TP-EI                OBJECT IDENTIFIER ::= { hh3cProductId 659 }
hh3c-S3100V2-8TP-PWR-EI             OBJECT IDENTIFIER ::= { hh3cProductId 660 }
hh3c-S3100V2-16TP-PWR-EI            OBJECT IDENTIFIER ::= { hh3cProductId 661 }
hh3c-S3100V2-26TP-PWR-EI            OBJECT IDENTIFIER ::= { hh3cProductId 662 }
hh3c-S2008TP-EB                     OBJECT IDENTIFIER ::= { hh3cProductId 663 }
hh3c-S2016TP-EB                     OBJECT IDENTIFIER ::= { hh3cProductId 664 }
hh3c-S2403TP-EB                     OBJECT IDENTIFIER ::= { hh3cProductId 665 }
hh3c-S2008TP-PWR-EB                 OBJECT IDENTIFIER ::= { hh3cProductId 666 }
hh3c-S2016TP-PWR-EB                 OBJECT IDENTIFIER ::= { hh3cProductId 667 }
hh3c-S2403TP-PWR-EB                 OBJECT IDENTIFIER ::= { hh3cProductId 668 }
hh3c-S5800-LSW1FC4P0                OBJECT IDENTIFIER ::= { hh3cProductId 669 }
hh3c-S2403TP-EA-SI-D                OBJECT IDENTIFIER ::= { hh3cProductId 670 }
hh3c-S3528P-EA-D                    OBJECT IDENTIFIER ::= { hh3cProductId 671 }
hh3c-OAP-FIC-V2                     OBJECT IDENTIFIER ::= { hh3cProductId 672 }
hh3c-OAP-MIM-V2                     OBJECT IDENTIFIER ::= { hh3cProductId 673 }
hh3c-OAPS-MIM-V2                    OBJECT IDENTIFIER ::= { hh3cProductId 674 }
hh3c-S2008TP-PWR-EA                 OBJECT IDENTIFIER ::= { hh3cProductId 675 }
hh3c-S2008TP-PWR-EA-DC              OBJECT IDENTIFIER ::= { hh3cProductId 676 }
hh3c-S2016TP-PWR-EA                 OBJECT IDENTIFIER ::= { hh3cProductId 677 }
hh3c-S2403TP-PWR-EA                 OBJECT IDENTIFIER ::= { hh3cProductId 678 }
hh3c-S5120-24P-EI-D                 OBJECT IDENTIFIER ::= { hh3cProductId 679 }
hh3c-S5120-24P-PWR-EI-D             OBJECT IDENTIFIER ::= { hh3cProductId 680 }
hh3c-S5120-48P-EI-D                 OBJECT IDENTIFIER ::= { hh3cProductId 681 }
hh3c-S5024P-EI                      OBJECT IDENTIFIER ::= { hh3cProductId 682 }
hh3c-S5500-28C-EI-D                 OBJECT IDENTIFIER ::= { hh3cProductId 683 }
hh3c-S5500-52C-EI-D                 OBJECT IDENTIFIER ::= { hh3cProductId 684 }
hh3c-S5500-28F-EI-D                 OBJECT IDENTIFIER ::= { hh3cProductId 685 }
hh3c-S5500-28C-EI-DC-D              OBJECT IDENTIFIER ::= { hh3cProductId 686 }
hh3c-MG9050                         OBJECT IDENTIFIER ::= { hh3cProductId 687 }
hh3c-S5120-52SC-HI                  OBJECT IDENTIFIER ::= { hh3cProductId 688 }
hh3c-CE3000-32F-EI                  OBJECT IDENTIFIER ::= { hh3cProductId 689 }
hh3cS5830V224S                      OBJECT IDENTIFIER ::= { hh3cProductId 690 }
hh3cDC1801FH                        OBJECT IDENTIFIER ::= { hh3cProductId 691 }
hh3cDC2004FF                        OBJECT IDENTIFIER ::= { hh3cProductId 692 }
hh3cEC1101HF                        OBJECT IDENTIFIER ::= { hh3cProductId 693 }
hh3cEC1102HF                        OBJECT IDENTIFIER ::= { hh3cProductId 694 }
hh3cEC1501HF                        OBJECT IDENTIFIER ::= { hh3cProductId 695 }
hh3cEC1801HH                        OBJECT IDENTIFIER ::= { hh3cProductId 696 }
hh3cEC2516HF                        OBJECT IDENTIFIER ::= { hh3cProductId 697 }
hh3cEC2016HC                        OBJECT IDENTIFIER ::= { hh3cProductId 698 }
hh3cEC2016HC8CH                     OBJECT IDENTIFIER ::= { hh3cProductId 699 }
hh3cEC2016HC4CH                     OBJECT IDENTIFIER ::= { hh3cProductId 700 }
hh3cEC1504HF                        OBJECT IDENTIFIER ::= { hh3cProductId 701 }
hh3cHIC5421                         OBJECT IDENTIFIER ::= { hh3cProductId 702 }
hh3cHIC5401                         OBJECT IDENTIFIER ::= { hh3cProductId 703 }
hh3cHIC5221H                        OBJECT IDENTIFIER ::= { hh3cProductId 704 }
hh3cHIC5201H                        OBJECT IDENTIFIER ::= { hh3cProductId 705 }
hh3cVM8500                          OBJECT IDENTIFIER ::= { hh3cProductId 706 }
hh3cMS8500                          OBJECT IDENTIFIER ::= { hh3cProductId 707 }
hh3cDM8500                          OBJECT IDENTIFIER ::= { hh3cProductId 708 }
hh3cVX500                           OBJECT IDENTIFIER ::= { hh3cProductId 709 }
hh3cISC3000E                        OBJECT IDENTIFIER ::= { hh3cProductId 710 }
hh3cISC3000S                        OBJECT IDENTIFIER ::= { hh3cProductId 711 }
hh3cCC700E                          OBJECT IDENTIFIER ::= { hh3cProductId 712 }
hh3cDC1001FF                        OBJECT IDENTIFIER ::= { hh3cProductId 713 }
hh3cECR3316HC                       OBJECT IDENTIFIER ::= { hh3cProductId 714 }
hh3cECR3308HD                       OBJECT IDENTIFIER ::= { hh3cProductId 715 }
hh3cECR3316HC8CH                    OBJECT IDENTIFIER ::= { hh3cProductId 716 }
hh3cECR3316HC4CH                    OBJECT IDENTIFIER ::= { hh3cProductId 717 }
hh3cECR3308HD4CH                    OBJECT IDENTIFIER ::= { hh3cProductId 718 }
hh3cHIC65017L                       OBJECT IDENTIFIER ::= { hh3cProductId 719 }
hh3cEC2508HF                        OBJECT IDENTIFIER ::= { hh3cProductId 720 }
hh3cS3528EA                         OBJECT IDENTIFIER ::= { hh3cProductId 721 }
hh3cS3552TPEA                       OBJECT IDENTIFIER ::= { hh3cProductId 722 }
hh3cWP3024                          OBJECT IDENTIFIER ::= { hh3cProductId 723 }
hh3cWP3048                          OBJECT IDENTIFIER ::= { hh3cProductId 724 }
hh3cS3528FPEA                       OBJECT IDENTIFIER ::= { hh3cProductId 725 }
hh3cE328B                           OBJECT IDENTIFIER ::= { hh3cProductId 726 }
hh3cE352B                           OBJECT IDENTIFIER ::= { hh3cProductId 727 }
hh3cE152B                           OBJECT IDENTIFIER ::= { hh3cProductId 728 }
hh3cS3100V252TP                     OBJECT IDENTIFIER ::= { hh3cProductId 729 }
hh3cWP2008                          OBJECT IDENTIFIER ::= { hh3cProductId 730 }
hh3cWP2016                          OBJECT IDENTIFIER ::= { hh3cProductId 731 }
hh3cWP2024                          OBJECT IDENTIFIER ::= { hh3cProductId 732 }
hh3cWP5024                          OBJECT IDENTIFIER ::= { hh3cProductId 733 }
hh3cWP5048                          OBJECT IDENTIFIER ::= { hh3cProductId 734 }
hh3cS2052TPEA                       OBJECT IDENTIFIER ::= { hh3cProductId 735 }
hh3cS7604X                          OBJECT IDENTIFIER ::= { hh3cProductId 736 }
hh3cS7608X                          OBJECT IDENTIFIER ::= { hh3cProductId 737 }
hh3cS7608XV                         OBJECT IDENTIFIER ::= { hh3cProductId 738 }
hh3cWA3620iAGN                      OBJECT IDENTIFIER ::= { hh3cProductId 739 }
hh3cWA3628iAGN                      OBJECT IDENTIFIER ::= { hh3cProductId 740 }
hh3cWA3610iGN                       OBJECT IDENTIFIER ::= { hh3cProductId 741 }
hh3cCC750E                          OBJECT IDENTIFIER ::= { hh3cProductId 742 }
hh3cS5024FSI                        OBJECT IDENTIFIER ::= { hh3cProductId 743 }
hh3cS5820V252QF                     OBJECT IDENTIFIER ::= { hh3cProductId 744 }
hh3cWA2110GN                        OBJECT IDENTIFIER ::= { hh3cProductId 745 }
hh3cMSR2010E                        OBJECT IDENTIFIER ::= { hh3cProductId 746 }
hh3cS10512                          OBJECT IDENTIFIER ::= { hh3cProductId 747 }
hh3cS512028SCHI                     OBJECT IDENTIFIER ::= { hh3cProductId 748 }
hh3cWA1208EGNP                      OBJECT IDENTIFIER ::= { hh3cProductId 749 }
hh3cWA2610EGNPH20                   OBJECT IDENTIFIER ::= { hh3cProductId 750 }
hh3cWA2620iAGN                      OBJECT IDENTIFIER ::= { hh3cProductId 751 }
hh3cWA2610iGN                       OBJECT IDENTIFIER ::= { hh3cProductId 752 }
hh3cWA2612                          OBJECT IDENTIFIER ::= { hh3cProductId 753 }
hh3cWA2620                          OBJECT IDENTIFIER ::= { hh3cProductId 754 }
hh3cWB524                           OBJECT IDENTIFIER ::= { hh3cProductId 755 }
hh3cSecBladeLST1FW3A1               OBJECT IDENTIFIER ::= { hh3cProductId 756 }
hh3cSecBladeLSU1FWCEA0              OBJECT IDENTIFIER ::= { hh3cProductId 757 }
hh3cWX3010eWCM                      OBJECT IDENTIFIER ::= { hh3cProductId 758 }
hh3cWX3010eLSW                      OBJECT IDENTIFIER ::= { hh3cProductId 759 }
hh3cSR6602X1                        OBJECT IDENTIFIER ::= { hh3cProductId 760 }
hh3cSR6602X2                        OBJECT IDENTIFIER ::= { hh3cProductId 761 }
hh3cSecBladeCRIMNAM1A               OBJECT IDENTIFIER ::= { hh3cProductId 762 }
hh3cMSR2630                         OBJECT IDENTIFIER ::= { hh3cProductId 763 }
hh3cMSR3610AC                       OBJECT IDENTIFIER ::= { hh3cProductId 764 }
hh3cMSR3610DC                       OBJECT IDENTIFIER ::= { hh3cProductId 765 }
hh3cMSR3620AC                       OBJECT IDENTIFIER ::= { hh3cProductId 766 }
hh3cMSR3620DC                       OBJECT IDENTIFIER ::= { hh3cProductId 767 }
hh3cMSR3620POE                      OBJECT IDENTIFIER ::= { hh3cProductId 768 }
hh3cMSR3640                         OBJECT IDENTIFIER ::= { hh3cProductId 769 }
hh3cMSR3660                         OBJECT IDENTIFIER ::= { hh3cProductId 770 }
hh3cMSR5660                         OBJECT IDENTIFIER ::= { hh3cProductId 771 }
hh3cMSR5680                         OBJECT IDENTIFIER ::= { hh3cProductId 772 }
hh3cS512058CHI                      OBJECT IDENTIFIER ::= { hh3cProductId 773 }
hh3cS512034CHI                      OBJECT IDENTIFIER ::= { hh3cProductId 774 }
hh3cLSU3WCMD0                       OBJECT IDENTIFIER ::= { hh3cProductId 775 }
hh3cEWPX3WCMD0                      OBJECT IDENTIFIER ::= { hh3cProductId 776 }
hh3cS7612X                          OBJECT IDENTIFIER ::= { hh3cProductId 777 }
hh3cWX6103E                         OBJECT IDENTIFIER ::= { hh3cProductId 778 }
hh3cSecBladeCRIMFW1A                OBJECT IDENTIFIER ::= { hh3cProductId 779 }
hh3cHIC66216C                       OBJECT IDENTIFIER ::= { hh3cProductId 780 }
hh3cHIC66216L                       OBJECT IDENTIFIER ::= { hh3cProductId 781 }
hh3cHIC3401V                        OBJECT IDENTIFIER ::= { hh3cProductId 782 }
hh3cHIC3401VIR                      OBJECT IDENTIFIER ::= { hh3cProductId 783 }
hh3cHIC3421V                        OBJECT IDENTIFIER ::= { hh3cProductId 784 }
hh3cHIC3421VIR                      OBJECT IDENTIFIER ::= { hh3cProductId 785 }
hh3cSIC235IR1                       OBJECT IDENTIFIER ::= { hh3cProductId 786 }
hh3cSIC235IR3                       OBJECT IDENTIFIER ::= { hh3cProductId 787 }
hh3cSIC335EVIR                      OBJECT IDENTIFIER ::= { hh3cProductId 788 }
hh3cHIC5511I                        OBJECT IDENTIFIER ::= { hh3cProductId 789 }
hh3cHIC5521I                        OBJECT IDENTIFIER ::= { hh3cProductId 790 }
hh3cHIC5551I                        OBJECT IDENTIFIER ::= { hh3cProductId 791 }
hh3cHIC5421E                        OBJECT IDENTIFIER ::= { hh3cProductId 792 }
hh3cHIC5401E                        OBJECT IDENTIFIER ::= { hh3cProductId 793 }
hh3cHIC5421D                        OBJECT IDENTIFIER ::= { hh3cProductId 794 }
hh3cHIC5401D                        OBJECT IDENTIFIER ::= { hh3cProductId 795 }
hh3cHIC5621                         OBJECT IDENTIFIER ::= { hh3cProductId 796 }
hh3cHIC5601                         OBJECT IDENTIFIER ::= { hh3cProductId 797 }
hh3cHIC6501E                        OBJECT IDENTIFIER ::= { hh3cProductId 798 }
hh3cHIC6621E                        OBJECT IDENTIFIER ::= { hh3cProductId 799 }
hh3cSIC635                          OBJECT IDENTIFIER ::= { hh3cProductId 800 }
hh3cHIC6501IR                       OBJECT IDENTIFIER ::= { hh3cProductId 801 }
hh3cHIC6621IR                       OBJECT IDENTIFIER ::= { hh3cProductId 802 }
hh3cSIC635IR                        OBJECT IDENTIFIER ::= { hh3cProductId 803 }
hh3cEC2508HF4CH                     OBJECT IDENTIFIER ::= { hh3cProductId 804 }
hh3cEC2516HF8CH                     OBJECT IDENTIFIER ::= { hh3cProductId 805 }
hh3cECR3308HF                       OBJECT IDENTIFIER ::= { hh3cProductId 806 }
hh3cECR3316HF                       OBJECT IDENTIFIER ::= { hh3cProductId 807 }
hh3cISC3500E                        OBJECT IDENTIFIER ::= { hh3cProductId 808 }
hh3cISC3500S                        OBJECT IDENTIFIER ::= { hh3cProductId 809 }
hh3cECR3304HFE                      OBJECT IDENTIFIER ::= { hh3cProductId 810 }
hh3cECR3308HFE                      OBJECT IDENTIFIER ::= { hh3cProductId 811 }
hh3cECR3316HFE                      OBJECT IDENTIFIER ::= { hh3cProductId 812 }
hh3cISC3600                         OBJECT IDENTIFIER ::= { hh3cProductId 813 }
hh3cECR3204HW                       OBJECT IDENTIFIER ::= { hh3cProductId 814 }
hh3cECR3208HW                       OBJECT IDENTIFIER ::= { hh3cProductId 815 }
hh3cECR3216HW                       OBJECT IDENTIFIER ::= { hh3cProductId 816 }
hh3cEC2508HW                        OBJECT IDENTIFIER ::= { hh3cProductId 817 }
hh3cEC2516HW                        OBJECT IDENTIFIER ::= { hh3cProductId 818 }
hh3cISC2600                         OBJECT IDENTIFIER ::= { hh3cProductId 819 }
hh3cDC2808FH                        OBJECT IDENTIFIER ::= { hh3cProductId 820 }
hh3cCE300034C                       OBJECT IDENTIFIER ::= { hh3cProductId 821 }
hh3cCE300058C                       OBJECT IDENTIFIER ::= { hh3cProductId 822 }
hh3cSR6604X                         OBJECT IDENTIFIER ::= { hh3cProductId 823 }
hh3cSR6608X                         OBJECT IDENTIFIER ::= { hh3cProductId 824 }
hh3cSR6616X                         OBJECT IDENTIFIER ::= { hh3cProductId 825 }
hh3csecpathF100AG                   OBJECT IDENTIFIER ::= { hh3cProductId 826 }
hh3csecpathF100CG                   OBJECT IDENTIFIER ::= { hh3cProductId 827 }
hh3csecpathF100EG                   OBJECT IDENTIFIER ::= { hh3cProductId 828 }
hh3csecpathF100MG                   OBJECT IDENTIFIER ::= { hh3cProductId 829 }
hh3csecpathF100SG                   OBJECT IDENTIFIER ::= { hh3cProductId 830 }
hh3cS3100V226TPWiNet                OBJECT IDENTIFIER ::= { hh3cProductId 831 }
hh3cS550024PWiNet                   OBJECT IDENTIFIER ::= { hh3cProductId 832 }
hh3cS512028PPoeWiNet                OBJECT IDENTIFIER ::= { hh3cProductId 833 }
hh3cS512028PWiNet                   OBJECT IDENTIFIER ::= { hh3cProductId 834 }
hh3cS550034CPWRHI                   OBJECT IDENTIFIER ::= { hh3cProductId 835 }
hh3cS550058CPWRHI                   OBJECT IDENTIFIER ::= { hh3cProductId 836 }
hh3cS550034FHI                      OBJECT IDENTIFIER ::= { hh3cProductId 837 }
hh3cMSR930                          OBJECT IDENTIFIER ::= { hh3cProductId 838 }
hh3cMSV50                           OBJECT IDENTIFIER ::= { hh3cProductId 839 }
hh3cMSR930WiNet                     OBJECT IDENTIFIER ::= { hh3cProductId 840 }
hh3cMSR930GU                        OBJECT IDENTIFIER ::= { hh3cProductId 841 }
hh3cMSR930sa                        OBJECT IDENTIFIER ::= { hh3cProductId 842 }
hh3cMSR930GG                        OBJECT IDENTIFIER ::= { hh3cProductId 843 }
hh3cS5820V254QSGE                   OBJECT IDENTIFIER ::= { hh3cProductId 844 }
hh3cS5820V252Q                      OBJECT IDENTIFIER ::= { hh3cProductId 845 }
hh3cCC754E                          OBJECT IDENTIFIER ::= { hh3cProductId 846 }
hh3cWP5008                          OBJECT IDENTIFIER ::= { hh3cProductId 847 }
hh3cSecBladeCRIMLB1A                OBJECT IDENTIFIER ::= { hh3cProductId 848 }
hh3cS550034CHID                     OBJECT IDENTIFIER ::= { hh3cProductId 849 }
hh3cS550058CHID                     OBJECT IDENTIFIER ::= { hh3cProductId 850 }
hh3cS9505EV7                        OBJECT IDENTIFIER ::= { hh3cProductId 851 }
hh3cS9508EV7                        OBJECT IDENTIFIER ::= { hh3cProductId 852 }
hh3cS9508EVV7                       OBJECT IDENTIFIER ::= { hh3cProductId 853 }
hh3cS9512EV7                        OBJECT IDENTIFIER ::= { hh3cProductId 854 }
hh3cS12508V7                        OBJECT IDENTIFIER ::= { hh3cProductId 855 }
hh3cS12518V7                        OBJECT IDENTIFIER ::= { hh3cProductId 856 }
hh3cS12504V7                        OBJECT IDENTIFIER ::= { hh3cProductId 857 }
hh3csecpathF100CAI                  OBJECT IDENTIFIER ::= { hh3cProductId 858 }
hh3csecpathL1000A                   OBJECT IDENTIFIER ::= { hh3cProductId 859 }
hh3cWA2610E                         OBJECT IDENTIFIER ::= { hh3cProductId 860 }
hh3cWA2620E                         OBJECT IDENTIFIER ::= { hh3cProductId 861 }
hh3cWA2620X                         OBJECT IDENTIFIER ::= { hh3cProductId 862 }
hh3cWA2610X                         OBJECT IDENTIFIER ::= { hh3cProductId 863 }
hh3cS6802                           OBJECT IDENTIFIER ::= { hh3cProductId 864 }
hh3cS9804                           OBJECT IDENTIFIER ::= { hh3cProductId 865 }
hh3cSecBladeLSU1IPSBEA0             OBJECT IDENTIFIER ::= { hh3cProductId 866 }
hh3cSecBladeLST1IPS2A1              OBJECT IDENTIFIER ::= { hh3cProductId 867 }
hh3cMSR930W                         OBJECT IDENTIFIER ::= { hh3cProductId 868 }
hh3cMSR930WGU                       OBJECT IDENTIFIER ::= { hh3cProductId 869 }
hh3cSecPathF5000C                   OBJECT IDENTIFIER ::= { hh3cProductId 870 }
hh3cSecPathF5000S                   OBJECT IDENTIFIER ::= { hh3cProductId 871 }
hh3cS12510FDC                       OBJECT IDENTIFIER ::= { hh3cProductId 872 }
hh3cS12510FAC                       OBJECT IDENTIFIER ::= { hh3cProductId 873 }
hh3cS12510XDC                       OBJECT IDENTIFIER ::= { hh3cProductId 874 }
hh3cS12510XAC                       OBJECT IDENTIFIER ::= { hh3cProductId 875 }
hh3cS12508                          OBJECT IDENTIFIER ::= { hh3cProductId 876 }
hh3cS12518                          OBJECT IDENTIFIER ::= { hh3cProductId 877 }
hh3cS12516FDC                       OBJECT IDENTIFIER ::= { hh3cProductId 878 }
hh3cS12516FAC                       OBJECT IDENTIFIER ::= { hh3cProductId 879 }
hh3cS12516XDC                       OBJECT IDENTIFIER ::= { hh3cProductId 880 }
hh3cS12516XAC                       OBJECT IDENTIFIER ::= { hh3cProductId 881 }
hh3cMSR930GT                        OBJECT IDENTIFIER ::= { hh3cProductId 882 }
hh3cMSR2600GTC                      OBJECT IDENTIFIER ::= { hh3cProductId 883 }
hh3cMSR2600GUC                      OBJECT IDENTIFIER ::= { hh3cProductId 884 }
hh3csecpathF1000AG                  OBJECT IDENTIFIER ::= { hh3cProductId 885 }
hh3csecpathF1000CG                  OBJECT IDENTIFIER ::= { hh3cProductId 886 }
hh3csecpathF1000SG                  OBJECT IDENTIFIER ::= { hh3cProductId 887 }
hh3cSecBladeLSQ2FWBSCO              OBJECT IDENTIFIER ::= { hh3cProductId 888 }
hh3cWA2620AGN                       OBJECT IDENTIFIER ::= { hh3cProductId 889 }
hh3cVSR                             OBJECT IDENTIFIER ::= { hh3cProductId 890 }
hh3cVSR1001                         OBJECT IDENTIFIER ::= { hh3cProductId 891 }
hh3cVSR1004                         OBJECT IDENTIFIER ::= { hh3cProductId 892 }
hh3cVSR1008                         OBJECT IDENTIFIER ::= { hh3cProductId 893 }
hh3cS5120S28PEI                     OBJECT IDENTIFIER ::= { hh3cProductId 894 }
hh3cS5120S52PEI                     OBJECT IDENTIFIER ::= { hh3cProductId 895 }
hh3cMSR930WiNetW                    OBJECT IDENTIFIER ::= { hh3cProductId 896 }
hh3cWA3628iAGNX                     OBJECT IDENTIFIER ::= { hh3cProductId 897 }
hh3cS2110                           OBJECT IDENTIFIER ::= { hh3cProductId 898 }
hh3cS2110PWR                        OBJECT IDENTIFIER ::= { hh3cProductId 899 }
hh3cS2126                           OBJECT IDENTIFIER ::= { hh3cProductId 900 }
hh3cS2126PWR                        OBJECT IDENTIFIER ::= { hh3cProductId 901 }
hh3cS2152                           OBJECT IDENTIFIER ::= { hh3cProductId 902 }
hh3cWX5540WCM                       OBJECT IDENTIFIER ::= { hh3cProductId 903 }
hh3cWX5540LSW                       OBJECT IDENTIFIER ::= { hh3cProductId 904 }
hh3cWX5520WCM                       OBJECT IDENTIFIER ::= { hh3cProductId 905 }
hh3cWX5520LSW                       OBJECT IDENTIFIER ::= { hh3cProductId 906 }
hh3cMSR930WGT                       OBJECT IDENTIFIER ::= { hh3cProductId 907 }
hh3cICG5000T                        OBJECT IDENTIFIER ::= { hh3cProductId 908 }
hh3cICG6000                         OBJECT IDENTIFIER ::= { hh3cProductId 909 }
hh3cMSR2630WiNet                    OBJECT IDENTIFIER ::= { hh3cProductId 910 }
hh3cMSR3610WiNet                    OBJECT IDENTIFIER ::= { hh3cProductId 911 }
hh3cMSR3660WiNet                    OBJECT IDENTIFIER ::= { hh3cProductId 912 }
hh3cMSR260010                       OBJECT IDENTIFIER ::= { hh3cProductId 913 }
hh3cMSR260010WiNet                  OBJECT IDENTIFIER ::= { hh3cProductId 914 }
hh3cMSR260017                       OBJECT IDENTIFIER ::= { hh3cProductId 915 }
hh3cICG3000D                        OBJECT IDENTIFIER ::= { hh3cProductId 916 }
hh3cICG3000E                        OBJECT IDENTIFIER ::= { hh3cProductId 917 }
hh3cSecBladeLSU1ADECEA0             OBJECT IDENTIFIER ::= { hh3cProductId 918 }
hh3cSecBladeLST1ADE1A1              OBJECT IDENTIFIER ::= { hh3cProductId 919 }
hh3cSR8804X                         OBJECT IDENTIFIER ::= { hh3cProductId 920 }
hh3cSR8808X                         OBJECT IDENTIFIER ::= { hh3cProductId 921 }
hh3cSR8812X                         OBJECT IDENTIFIER ::= { hh3cProductId 922 }
hh3cCC710E                          OBJECT IDENTIFIER ::= { hh3cProductId 923 }
hh3cCC712E                          OBJECT IDENTIFIER ::= { hh3cProductId 924 }
hh3cS680032Q                        OBJECT IDENTIFIER ::= { hh3cProductId 925 }
hh3cS5008PV2EI                      OBJECT IDENTIFIER ::= { hh3cProductId 926 }
hh3cS5024PV2EI                      OBJECT IDENTIFIER ::= { hh3cProductId 927 }
hh3cS5048PV2EI                      OBJECT IDENTIFIER ::= { hh3cProductId 928 }
hh3cS2610                           OBJECT IDENTIFIER ::= { hh3cProductId 929 }
hh3cS2610PWR                        OBJECT IDENTIFIER ::= { hh3cProductId 930 }
hh3cS2626                           OBJECT IDENTIFIER ::= { hh3cProductId 931 }
hh3cS2626PWR                        OBJECT IDENTIFIER ::= { hh3cProductId 932 }
hh3cS2652                           OBJECT IDENTIFIER ::= { hh3cProductId 933 }
hh3cSimware7BoxCen                  OBJECT IDENTIFIER ::= { hh3cProductId 934 }
hh3cSimware7BoxIRF                  OBJECT IDENTIFIER ::= { hh3cProductId 935 }
hh3cSimware7ChassisDevice           OBJECT IDENTIFIER ::= { hh3cProductId 936 }
hh3cVSR1000                         OBJECT IDENTIFIER ::= { hh3cProductId 937 }
hh3csecpathM9000                    OBJECT IDENTIFIER ::= { hh3cProductId 938 }
hh3csecpathM9006                    OBJECT IDENTIFIER ::= { hh3cProductId 939 }
hh3csecpathM9010                    OBJECT IDENTIFIER ::= { hh3cProductId 940 }
hh3csecpathM9014                    OBJECT IDENTIFIER ::= { hh3cProductId 941 }
hh3cSecBladeIIINSQM1FWCEA0          OBJECT IDENTIFIER ::= { hh3cProductId 942 }
hh3cWB521X                          OBJECT IDENTIFIER ::= { hh3cProductId 943 }
hh3cWB511X                          OBJECT IDENTIFIER ::= { hh3cProductId 944 }
hh3cER3108G                         OBJECT IDENTIFIER ::= { hh3cProductId 945 }
hh3cER3108GW                        OBJECT IDENTIFIER ::= { hh3cProductId 946 }
hh3cS513028SEI                      OBJECT IDENTIFIER ::= { hh3cProductId 947 }
hh3cS513052SEI                      OBJECT IDENTIFIER ::= { hh3cProductId 948 }
hh3cS513028FEI                      OBJECT IDENTIFIER ::= { hh3cProductId 949 }
hh3cS513028SPWREI                   OBJECT IDENTIFIER ::= { hh3cProductId 950 }
hh3cS513052SPWREI                   OBJECT IDENTIFIER ::= { hh3cProductId 951 }
hh3cMSR360028                       OBJECT IDENTIFIER ::= { hh3cProductId 952 }
hh3cMSR360051                       OBJECT IDENTIFIER ::= { hh3cProductId 953 }
hh3cWA2612E                         OBJECT IDENTIFIER ::= { hh3cProductId 954 }
hh3cWA2622                          OBJECT IDENTIFIER ::= { hh3cProductId 955 }
hh3cS511010P                        OBJECT IDENTIFIER ::= { hh3cProductId 956 }
hh3cS511010PPWR                     OBJECT IDENTIFIER ::= { hh3cProductId 957 }
hh3cS511028P                        OBJECT IDENTIFIER ::= { hh3cProductId 958 }
hh3cS511028PPWR                     OBJECT IDENTIFIER ::= { hh3cProductId 959 }
hh3cS511052P                        OBJECT IDENTIFIER ::= { hh3cProductId 960 }
hh3cS511010PD                       OBJECT IDENTIFIER ::= { hh3cProductId 961 }
hh3cS511010PPWRD                    OBJECT IDENTIFIER ::= { hh3cProductId 962 }
hh3cS511028PD                       OBJECT IDENTIFIER ::= { hh3cProductId 963 }
hh3cS511028PPWRD                    OBJECT IDENTIFIER ::= { hh3cProductId 964 }
hh3cS511052PD                       OBJECT IDENTIFIER ::= { hh3cProductId 965 }
hh3cWX5510                          OBJECT IDENTIFIER ::= { hh3cProductId 966 }
hh3cS550028SCHI                     OBJECT IDENTIFIER ::= { hh3cProductId 967 }
hh3cS550052SCHI                     OBJECT IDENTIFIER ::= { hh3cProductId 968 }
hh3cS550028SCHID                    OBJECT IDENTIFIER ::= { hh3cProductId 969 }
hh3cS550052SCHID                    OBJECT IDENTIFIER ::= { hh3cProductId 970 }
hh3cLA2608                          OBJECT IDENTIFIER ::= { hh3cProductId 971 }
hh3cS311010TP                       OBJECT IDENTIFIER ::= { hh3cProductId 972 }
hh3cS311010TPPWR                    OBJECT IDENTIFIER ::= { hh3cProductId 973 }
hh3cS311026TP                       OBJECT IDENTIFIER ::= { hh3cProductId 974 }
hh3cS311026TPPWR                    OBJECT IDENTIFIER ::= { hh3cProductId 975 }
hh3cS311052TP                       OBJECT IDENTIFIER ::= { hh3cProductId 976 }
hh3cWA2610HGN                       OBJECT IDENTIFIER ::= { hh3cProductId 977 }
hh3cWA4620EACN                      OBJECT IDENTIFIER ::= { hh3cProductId 978 }
hh3cWA4620IACN                      OBJECT IDENTIFIER ::= { hh3cProductId 979 }
hh3cEWPX1MAC0                       OBJECT IDENTIFIER ::= { hh3cProductId 980 }
hh3cCRIMMAC1A                       OBJECT IDENTIFIER ::= { hh3cProductId 981 }
hh3cSecBladeIIILST1FW3B1            OBJECT IDENTIFIER ::= { hh3cProductId 982 }
hh3cWA2620iAGNX                     OBJECT IDENTIFIER ::= { hh3cProductId 983 }
hh3cS311010TPSI                     OBJECT IDENTIFIER ::= { hh3cProductId 984 }
hh3cS311026TPSI                     OBJECT IDENTIFIER ::= { hh3cProductId 985 }
hh3cS311052TPSI                     OBJECT IDENTIFIER ::= { hh3cProductId 986 }
hh3cS511010PSI                      OBJECT IDENTIFIER ::= { hh3cProductId 987 }
hh3cS511028PSI                      OBJECT IDENTIFIER ::= { hh3cProductId 988 }
hh3cS511052PSI                      OBJECT IDENTIFIER ::= { hh3cProductId 989 }
hh3cS3100V252TPWiNet                OBJECT IDENTIFIER ::= { hh3cProductId 990 }
hh3cS512052PWiNet                   OBJECT IDENTIFIER ::= { hh3cProductId 991 }
hh3cS550048PWiNet                   OBJECT IDENTIFIER ::= { hh3cProductId 992 }
hh3cS550028FWiNet                   OBJECT IDENTIFIER ::= { hh3cProductId 993 }
hh3CWA2620EX                        OBJECT IDENTIFIER ::= { hh3cProductId 994 }
hh3csecpathL5000S                   OBJECT IDENTIFIER ::= { hh3cProductId 995 }
hh3csecpathL5000C                   OBJECT IDENTIFIER ::= { hh3cProductId 996 }
hh3cCC721E                          OBJECT IDENTIFIER ::= { hh3cProductId 997 }
hh3cS5820V252QFU                    OBJECT IDENTIFIER ::= { hh3cProductId 998 }
hh3csecpathVFW1000                  OBJECT IDENTIFIER ::= { hh3cProductId 999 }
hh3cS7003                           OBJECT IDENTIFIER ::= { hh3cProductId 1000 }
hh3cS7006                           OBJECT IDENTIFIER ::= { hh3cProductId 1001 }
hh3csecpathF100CSI                  OBJECT IDENTIFIER ::= { hh3cProductId 1002 }
hh3cWX3510E                         OBJECT IDENTIFIER ::= { hh3cProductId 1003 }
hh3cWX3540E                         OBJECT IDENTIFIER ::= { hh3cProductId 1004 }
hh3cSecBladeLSU3FWCEA0              OBJECT IDENTIFIER ::= { hh3cProductId 1005 }
hh3cSecBladeLSU1NSCEA0              OBJECT IDENTIFIER ::= { hh3cProductId 1006 }
hh3cSecBladeLST1FW3C1               OBJECT IDENTIFIER ::= { hh3cProductId 1007 }
hh3cSecBladeLST1NSM2C1              OBJECT IDENTIFIER ::= { hh3cProductId 1008 }
hh3cSecBladeLSX1FWCEA1              OBJECT IDENTIFIER ::= { hh3cProductId 1009 }
hh3cSecBladeLSX1NSCEA1              OBJECT IDENTIFIER ::= { hh3cProductId 1010 }
hh3cWA2620AGNC                      OBJECT IDENTIFIER ::= { hh3cProductId 1011 }
hh3cWA2610GN                        OBJECT IDENTIFIER ::= { hh3cProductId 1012 }
hh3cWA2610GNE                       OBJECT IDENTIFIER ::= { hh3cProductId 1013 }
hh3cMSR800                          OBJECT IDENTIFIER ::= { hh3cProductId 1014 }
hh3cMSR800Wlan                      OBJECT IDENTIFIER ::= { hh3cProductId 1015 }
hh3cMSR80010                        OBJECT IDENTIFIER ::= { hh3cProductId 1016 }
hh3cMSR80010Wlan                    OBJECT IDENTIFIER ::= { hh3cProductId 1017 }
hh3cMSR830WiNet                     OBJECT IDENTIFIER ::= { hh3cProductId 1018 }
hh3cMSR83010WiNet                   OBJECT IDENTIFIER ::= { hh3cProductId 1019 }
hh3cMSR93010WiNet                   OBJECT IDENTIFIER ::= { hh3cProductId 1020 }
hh3cS9810                           OBJECT IDENTIFIER ::= { hh3cProductId 1021 }
hh3cFlexNetworkB6300XLG             OBJECT IDENTIFIER ::= { hh3cProductId 1022 }
hh3cFlexNetworkB6300GXG             OBJECT IDENTIFIER ::= { hh3cProductId 1023 }
hh3cMSR900E                         OBJECT IDENTIFIER ::= { hh3cProductId 1024 }
hh3cMSR900EWlan                     OBJECT IDENTIFIER ::= { hh3cProductId 1025 }
hh3cS513028SEID                     OBJECT IDENTIFIER ::= { hh3cProductId 1026 }
hh3cS513052SEID                     OBJECT IDENTIFIER ::= { hh3cProductId 1027 }
hh3cS513028FEID                     OBJECT IDENTIFIER ::= { hh3cProductId 1028 }
hh3cS513028SHPWREID                 OBJECT IDENTIFIER ::= { hh3cProductId 1029 }
hh3cS513052SPWREID                  OBJECT IDENTIFIER ::= { hh3cProductId 1030 }
hh3cS513028SHPWREI                  OBJECT IDENTIFIER ::= { hh3cProductId 1031 }
hh3cE528X                           OBJECT IDENTIFIER ::= { hh3cProductId 1032 }
hh3cE552X                           OBJECT IDENTIFIER ::= { hh3cProductId 1033 }
hh3cLSU1WCME0                       OBJECT IDENTIFIER ::= { hh3cProductId 1034 }
hh3cEWPX1WCME0                      OBJECT IDENTIFIER ::= { hh3cProductId 1035 }
hh3cSR8810XS                        OBJECT IDENTIFIER ::= { hh3cProductId 1036 }
hh3cSR8806XS                        OBJECT IDENTIFIER ::= { hh3cProductId 1037 }
hh3cSR8803XS                        OBJECT IDENTIFIER ::= { hh3cProductId 1038 }
hh3cSR8802XS                        OBJECT IDENTIFIER ::= { hh3cProductId 1039 }
hh3cSecPathF5020                    OBJECT IDENTIFIER ::= { hh3cProductId 1040 }
hh3cSecPathF5040                    OBJECT IDENTIFIER ::= { hh3cProductId 1041 }
hh3cRA100                           OBJECT IDENTIFIER ::= { hh3cProductId 1042 }
hh3cMSR930LM                        OBJECT IDENTIFIER ::= { hh3cProductId 1043 }
hh3cMSR930WLM                       OBJECT IDENTIFIER ::= { hh3cProductId 1044 }
hh3cMSR26005LMC                     OBJECT IDENTIFIER ::= { hh3cProductId 1045 }
hh3cS580032CEI                      OBJECT IDENTIFIER ::= { hh3cProductId 1046 }
hh3cS580056CEI                      OBJECT IDENTIFIER ::= { hh3cProductId 1047 }
hh3cS580032CPWREI                   OBJECT IDENTIFIER ::= { hh3cProductId 1048 }
hh3cS580056CPWREI                   OBJECT IDENTIFIER ::= { hh3cProductId 1049 }
hh3cS580056CEIM                     OBJECT IDENTIFIER ::= { hh3cProductId 1050 }
hh3cWB521XE                         OBJECT IDENTIFIER ::= { hh3cProductId 1051 }
hh3cWB521XH                         OBJECT IDENTIFIER ::= { hh3cProductId 1052 }
hh3cWX2540E                         OBJECT IDENTIFIER ::= { hh3cProductId 1053 }
hh3cWX360                           OBJECT IDENTIFIER ::= { hh3cProductId 1054 }
hh3cWX361                           OBJECT IDENTIFIER ::= { hh3cProductId 1055 }
hh3cWA2610EGNE                      OBJECT IDENTIFIER ::= { hh3cProductId 1056 }
hh3cSR6603F                         OBJECT IDENTIFIER ::= { hh3cProductId 1057 }
hh3cSR6605F                         OBJECT IDENTIFIER ::= { hh3cProductId 1058 }
hh3cSR6609F                         OBJECT IDENTIFIER ::= { hh3cProductId 1059 }
hh3cS556030SEI                      OBJECT IDENTIFIER ::= { hh3cProductId 1060 }
hh3cS556054SEI                      OBJECT IDENTIFIER ::= { hh3cProductId 1061 }
hh3cS556030CEI                      OBJECT IDENTIFIER ::= { hh3cProductId 1062 }
hh3cS556054CEI                      OBJECT IDENTIFIER ::= { hh3cProductId 1063 }
hh3cS556030CPWREI                   OBJECT IDENTIFIER ::= { hh3cProductId 1064 }
hh3cS556054CPWREI                   OBJECT IDENTIFIER ::= { hh3cProductId 1065 }
hh3cS556054QSEI                     OBJECT IDENTIFIER ::= { hh3cProductId 1066 }
hh3cRA200                           OBJECT IDENTIFIER ::= { hh3cProductId 1067 }
hh3cF1000CSI                        OBJECT IDENTIFIER ::= { hh3cProductId 1068 }
hh3cF100MSI                         OBJECT IDENTIFIER ::= { hh3cProductId 1069 }
hh3cF100ASI                         OBJECT IDENTIFIER ::= { hh3cProductId 1070 }
hh3cS5820V248S                      OBJECT IDENTIFIER ::= { hh3cProductId 1071 }
hh3cS630042QT                       OBJECT IDENTIFIER ::= { hh3cProductId 1072 }
hh3cS630042QF                       OBJECT IDENTIFIER ::= { hh3cProductId 1073 }
hh3cS630048S                        OBJECT IDENTIFIER ::= { hh3cProductId 1074 }
hh3cS630052QF                       OBJECT IDENTIFIER ::= { hh3cProductId 1075 }
hh3cFlexNetworkU830048G             OBJECT IDENTIFIER ::= { hh3cProductId 1076 }
hh3cFlexNetworkU830048XLGU          OBJECT IDENTIFIER ::= { hh3cProductId 1077 }
hh3cS5008PV2EIPWR                   OBJECT IDENTIFIER ::= { hh3cProductId 1078 }
hh3cS5024PV2EIPWR                   OBJECT IDENTIFIER ::= { hh3cProductId 1079 }
hh3cS511052PPWR                     OBJECT IDENTIFIER ::= { hh3cProductId 1080 }
hh3cS511052PPWRD                    OBJECT IDENTIFIER ::= { hh3cProductId 1081 }
hh3cNSC1000                         OBJECT IDENTIFIER ::= { hh3cProductId 1082 }
hh3cMS4308                          OBJECT IDENTIFIER ::= { hh3cProductId 1083 }
hh3cMS4308PWR                       OBJECT IDENTIFIER ::= { hh3cProductId 1084 }
hh3cS513028TPEI                     OBJECT IDENTIFIER ::= { hh3cProductId 1085 }
hh3cS513052TPEI                     OBJECT IDENTIFIER ::= { hh3cProductId 1086 }
hh3cS513028TPPWREI                  OBJECT IDENTIFIER ::= { hh3cProductId 1087 }
hh3cS513052TPPWREI                  OBJECT IDENTIFIER ::= { hh3cProductId 1088 }
hh3csecpathF1020                    OBJECT IDENTIFIER ::= { hh3cProductId 1089 }
hh3csecpathF1030                    OBJECT IDENTIFIER ::= { hh3cProductId 1090 }
hh3csecpathF1050                    OBJECT IDENTIFIER ::= { hh3cProductId 1091 }
hh3csecpathF1060                    OBJECT IDENTIFIER ::= { hh3cProductId 1092 }
hh3csecpathF1070                    OBJECT IDENTIFIER ::= { hh3cProductId 1093 }
hh3csecpathF1080                    OBJECT IDENTIFIER ::= { hh3cProductId 1094 }
hh3csecpathVMSGVLB1000              OBJECT IDENTIFIER ::= { hh3cProductId 1095 }
hh3cS5864F                          OBJECT IDENTIFIER ::= { hh3cProductId 1096 }
hh3cS5864UF                         OBJECT IDENTIFIER ::= { hh3cProductId 1097 }
hh3cS5864TF                         OBJECT IDENTIFIER ::= { hh3cProductId 1098 }
hh3cS6348F                          OBJECT IDENTIFIER ::= { hh3cProductId 1099 }
hh3cS6348TF                         OBJECT IDENTIFIER ::= { hh3cProductId 1100 }
hh3cCR16006F                        OBJECT IDENTIFIER ::= { hh3cProductId 1101 }
hh3cCR16010F                        OBJECT IDENTIFIER ::= { hh3cProductId 1102 }
hh3cCR16014F                        OBJECT IDENTIFIER ::= { hh3cProductId 1103 }
hh3cSecPathM9000Context             OBJECT IDENTIFIER ::= { hh3cProductId 1104 }
hh3cICG3000SE                       OBJECT IDENTIFIER ::= { hh3cProductId 1105 }
hh3cS68004C                         OBJECT IDENTIFIER ::= { hh3cProductId 1106 }
hh3cS68002C                         OBJECT IDENTIFIER ::= { hh3cProductId 1107 }
hh3cSR8803F                         OBJECT IDENTIFIER ::= { hh3cProductId 1108 }
hh3cSR8805F                         OBJECT IDENTIFIER ::= { hh3cProductId 1109 }
hh3cSR8808F                         OBJECT IDENTIFIER ::= { hh3cProductId 1110 }
hh3cSR8812F                         OBJECT IDENTIFIER ::= { hh3cProductId 1111 }
hh3cS12516XAFAC                     OBJECT IDENTIFIER ::= { hh3cProductId 1112 }


-- HP A series products
-- OID of hpNetworking is 1.3.6.1.4.1.25506.11
hpSwitch                        OBJECT IDENTIFIER ::= { hpNetworking 1 }
hpRouter                        OBJECT IDENTIFIER ::= { hpNetworking 2 }
hpWireless                      OBJECT IDENTIFIER ::= { hpNetworking 3 }
hpSecurity                      OBJECT IDENTIFIER ::= { hpNetworking 4 }

-- begin hpSwitch
hp7502                          OBJECT IDENTIFIER ::= { hpSwitch 1 }
hp7503S                         OBJECT IDENTIFIER ::= { hpSwitch 2 }
hp7503                          OBJECT IDENTIFIER ::= { hpSwitch 3 }
hp7506                          OBJECT IDENTIFIER ::= { hpSwitch 4 }
hp7506V                         OBJECT IDENTIFIER ::= { hpSwitch 5 }
hp7510                          OBJECT IDENTIFIER ::= { hpSwitch 6 }
hpA36002POLT                    OBJECT IDENTIFIER ::= { hpSwitch 7 }
hpV190524                       OBJECT IDENTIFIER ::= { hpSwitch 8 }
hpV190524POE                    OBJECT IDENTIFIER ::= { hpSwitch 9 }
hpV190548                       OBJECT IDENTIFIER ::= { hpSwitch 10 }
hpA512016GSI                    OBJECT IDENTIFIER ::= { hpSwitch 11 }
hpA512024GSI                    OBJECT IDENTIFIER ::= { hpSwitch 12 }
hpA512048GSI                    OBJECT IDENTIFIER ::= { hpSwitch 13 }
hpA512024GPPOESI                OBJECT IDENTIFIER ::= { hpSwitch 14 }
hpA512024GPOESI                 OBJECT IDENTIFIER ::= { hpSwitch 15 }
hpA580024G                      OBJECT IDENTIFIER ::= { hpSwitch 16 }
hpA580024GPoEPlus               OBJECT IDENTIFIER ::= { hpSwitch 17 }
hpA580048G                      OBJECT IDENTIFIER ::= { hpSwitch 18 }
hpA580048GPoEPlus               OBJECT IDENTIFIER ::= { hpSwitch 19 }
hpA580024GSFP                   OBJECT IDENTIFIER ::= { hpSwitch 20 }
hpA580048GPoEPlus2SLOT          OBJECT IDENTIFIER ::= { hpSwitch 21 }
hpA5820X14XGSFPPlus2SLOT        OBJECT IDENTIFIER ::= { hpSwitch 22 }
hpA5820X24XGSFPPlus             OBJECT IDENTIFIER ::= { hpSwitch 23 }
hpA550024GEI2SLOT               OBJECT IDENTIFIER ::= { hpSwitch 24 }
hpA550048GEI2SLOT               OBJECT IDENTIFIER ::= { hpSwitch 25 }
hpA550024GPoEPlusEI2SLOT        OBJECT IDENTIFIER ::= { hpSwitch 26 }
hpA550048GPoEPlusEI2SLOT        OBJECT IDENTIFIER ::= { hpSwitch 27 }
hpA550024GSFPEI2SLOT            OBJECT IDENTIFIER ::= { hpSwitch 28 }
hpA550024GSI2SLOT               OBJECT IDENTIFIER ::= { hpSwitch 29 }
hpA550048GSI2SLOT               OBJECT IDENTIFIER ::= { hpSwitch 30 }
hpA550024GPoEPlusSI2SLOT        OBJECT IDENTIFIER ::= { hpSwitch 31 }
hpA550048GPoEPlusSI2SLOT        OBJECT IDENTIFIER ::= { hpSwitch 32 }
hpA512024GEI2SLOT               OBJECT IDENTIFIER ::= { hpSwitch 33 }
hpA512048GEI2SLOT               OBJECT IDENTIFIER ::= { hpSwitch 34 }
hpA512024GPoEPlusEI2SLOT        OBJECT IDENTIFIER ::= { hpSwitch 35 }
hpA512048GPoEPlusEI2SLOT        OBJECT IDENTIFIER ::= { hpSwitch 36 }
hpA512024GEI                    OBJECT IDENTIFIER ::= { hpSwitch 37 }
hpA512048GEI                    OBJECT IDENTIFIER ::= { hpSwitch 38 }
hp9505                          OBJECT IDENTIFIER ::= { hpSwitch 39 }
hp9508V                         OBJECT IDENTIFIER ::= { hpSwitch 40 }
hp9508                          OBJECT IDENTIFIER ::= { hpSwitch 41 }
hp9512                          OBJECT IDENTIFIER ::= { hpSwitch 42 }
hp12508                         OBJECT IDENTIFIER ::= { hpSwitch 43 }
hp12518                         OBJECT IDENTIFIER ::= { hpSwitch 44 }
hp12504AC                       OBJECT IDENTIFIER ::= { hpSwitch 45 }
hpA5800AF48G                    OBJECT IDENTIFIER ::= { hpSwitch 46 }
hpA5820AF24XG                   OBJECT IDENTIFIER ::= { hpSwitch 47 }
hp6125GXG                       OBJECT IDENTIFIER ::= { hpSwitch 51 }
hpA31008SI                      OBJECT IDENTIFIER ::= { hpSwitch 52 }
hpA310016SI                     OBJECT IDENTIFIER ::= { hpSwitch 53 }
hpA310024SI                     OBJECT IDENTIFIER ::= { hpSwitch 54 }
hpA31008EI                      OBJECT IDENTIFIER ::= { hpSwitch 55 }
hpA310016EI                     OBJECT IDENTIFIER ::= { hpSwitch 56 }
hpA310024EI                     OBJECT IDENTIFIER ::= { hpSwitch 57 }
hpA31008POEEI                   OBJECT IDENTIFIER ::= { hpSwitch 58 }
hpA310016POEEI                  OBJECT IDENTIFIER ::= { hpSwitch 59 }
hpA310024POEEI                  OBJECT IDENTIFIER ::= { hpSwitch 60 }
hpA580024GTAA                   OBJECT IDENTIFIER ::= { hpSwitch 61 }
hpA580024GPoEPlusTAA            OBJECT IDENTIFIER ::= { hpSwitch 62 }
hpA580024GSFPTAA                OBJECT IDENTIFIER ::= { hpSwitch 63 }
hpA580048GTAA                   OBJECT IDENTIFIER ::= { hpSwitch 64 }
hpA580048GPoEPlusTAA2SLOT       OBJECT IDENTIFIER ::= { hpSwitch 65 }
hpA580048GPoEPlusTAA            OBJECT IDENTIFIER ::= { hpSwitch 66 }
hpA5820X14XGSFPPlusTAA2SLOT     OBJECT IDENTIFIER ::= { hpSwitch 67 }
hpA5820X24XGSFPPlusTAA          OBJECT IDENTIFIER ::= { hpSwitch 68 }
hpA512024GEITAA2SLOT            OBJECT IDENTIFIER ::= { hpSwitch 69 }
hpA512048GEITAA2SLOT            OBJECT IDENTIFIER ::= { hpSwitch 70 }
hpA512024GPoEPlusEITAA2SLOT     OBJECT IDENTIFIER ::= { hpSwitch 71 }
hpA512048GPoEPlusEITAA2SLOT     OBJECT IDENTIFIER ::= { hpSwitch 72 }
hpA550024GSFPEITAA2SLOT         OBJECT IDENTIFIER ::= { hpSwitch 73 }
hpA550024GEITAA2SLOT            OBJECT IDENTIFIER ::= { hpSwitch 74 }
hpA550048GEITAA2SLOT            OBJECT IDENTIFIER ::= { hpSwitch 75 }
hpA550024GPoEPlusEITAA2SLOT     OBJECT IDENTIFIER ::= { hpSwitch 76 }
hpA550048GPoEPlusEITAA2SLOT     OBJECT IDENTIFIER ::= { hpSwitch 77 }
hp5920AF24XG                    OBJECT IDENTIFIER ::= { hpSwitch 78 }
hpA5830AF48G                    OBJECT IDENTIFIER ::= { hpSwitch 79 }
hpA5830AF96G                    OBJECT IDENTIFIER ::= { hpSwitch 80 }
hpV191016G                      OBJECT IDENTIFIER ::= { hpSwitch 81 }
hpV191024G                      OBJECT IDENTIFIER ::= { hpSwitch 82 }
hpV191024GPoE365W               OBJECT IDENTIFIER ::= { hpSwitch 83 }
hpV191024GPoE170W               OBJECT IDENTIFIER ::= { hpSwitch 84 }
hpV191048G                      OBJECT IDENTIFIER ::= { hpSwitch 85 }
hp10504                         OBJECT IDENTIFIER ::= { hpSwitch 86 }
hp10508                         OBJECT IDENTIFIER ::= { hpSwitch 87 }
hp10508V                        OBJECT IDENTIFIER ::= { hpSwitch 88 }
hp10512                         OBJECT IDENTIFIER ::= { hpSwitch 89 }
hpA360024V2EI                   OBJECT IDENTIFIER ::= { hpSwitch 90 }
hpA360048V2EI                   OBJECT IDENTIFIER ::= { hpSwitch 91 }
hpA360024PoEPlusV2EI            OBJECT IDENTIFIER ::= { hpSwitch 92 }
hpA360048PoEPlusV2EI            OBJECT IDENTIFIER ::= { hpSwitch 93 }
hpA360024SFPV2EI                OBJECT IDENTIFIER ::= { hpSwitch 94 }
hpA360024V2SI                   OBJECT IDENTIFIER ::= { hpSwitch 95 }
hpA360048V2SI                   OBJECT IDENTIFIER ::= { hpSwitch 96 }
hpA360024PoEPlusV2SI            OBJECT IDENTIFIER ::= { hpSwitch 97 }
hpA360048PoEPlusV2SI            OBJECT IDENTIFIER ::= { hpSwitch 98 }
hpA310048V2                     OBJECT IDENTIFIER ::= { hpSwitch 99 }
hp5900AF48XG4QSFPPlus           OBJECT IDENTIFIER ::= { hpSwitch 100 }
hpA550024G4SFPHI                OBJECT IDENTIFIER ::= { hpSwitch 101 }
hpA550048G4SFPHI                OBJECT IDENTIFIER ::= { hpSwitch 102 }
hp6125G                         OBJECT IDENTIFIER ::= { hpSwitch 103 }
hpA51208GSI                     OBJECT IDENTIFIER ::= { hpSwitch 104 }
hpA51208GPoEPlusSI              OBJECT IDENTIFIER ::= { hpSwitch 105 }
hpA51208GPPoEPlusSI             OBJECT IDENTIFIER ::= { hpSwitch 106 }
hpA5120AF48GHI                  OBJECT IDENTIFIER ::= { hpSwitch 107 }
hp12504DC                       OBJECT IDENTIFIER ::= { hpSwitch 108 }
hp12508DC                       OBJECT IDENTIFIER ::= { hpSwitch 109 }
hp12518DC                       OBJECT IDENTIFIER ::= { hpSwitch 110 }
hp12508AC                       OBJECT IDENTIFIER ::= { hpSwitch 111 }
hp12518AC                       OBJECT IDENTIFIER ::= { hpSwitch 112 }
hp5900AF48XGT4QSFPPlus          OBJECT IDENTIFIER ::= { hpSwitch 113 }
hp19108G                        OBJECT IDENTIFIER ::= { hpSwitch 114 }
hp19108GPoEPlus65W              OBJECT IDENTIFIER ::= { hpSwitch 115 }
hp19108GPoEPlus180W             OBJECT IDENTIFIER ::= { hpSwitch 116 }
hp5830AF48GTAA                  OBJECT IDENTIFIER ::= { hpSwitch 117 }
hp5830AF96GTAA                  OBJECT IDENTIFIER ::= { hpSwitch 118 }
hp7508H                         OBJECT IDENTIFIER ::= { hpSwitch 119 }
hp5900AF48G4XG2QSFPPlus         OBJECT IDENTIFIER ::= { hpSwitch 120 }
hp550048GPoEPlus4SFPHI          OBJECT IDENTIFIER ::= { hpSwitch 121 }
hp550024GPoEPlus4SFPHI          OBJECT IDENTIFIER ::= { hpSwitch 122 }
hp550024GSFPHI                  OBJECT IDENTIFIER ::= { hpSwitch 123 }
hp12504ACV7                     OBJECT IDENTIFIER ::= { hpSwitch 124 }
hp12504DCV7                     OBJECT IDENTIFIER ::= { hpSwitch 125 }
hp12508ACV7                     OBJECT IDENTIFIER ::= { hpSwitch 126 }
hp12508DCV7                     OBJECT IDENTIFIER ::= { hpSwitch 127 }
hp12518ACV7                     OBJECT IDENTIFIER ::= { hpSwitch 128 }
hp12518DCV7                     OBJECT IDENTIFIER ::= { hpSwitch 129 }
hp5900AF48XG4QSFPPlusTAA        OBJECT IDENTIFIER ::= { hpSwitch 130 }
hp5920AF24XGTAA                 OBJECT IDENTIFIER ::= { hpSwitch 131 }
hpV19108                        OBJECT IDENTIFIER ::= { hpSwitch 132 }
hpV19108PoEPlus                 OBJECT IDENTIFIER ::= { hpSwitch 133 }
hpV191024                       OBJECT IDENTIFIER ::= { hpSwitch 134 }
hpV191024PoEPlus                OBJECT IDENTIFIER ::= { hpSwitch 135 }
hpV191048                       OBJECT IDENTIFIER ::= { hpSwitch 136 }
hp6125XGXLG                     OBJECT IDENTIFIER ::= { hpSwitch 137 }
hp11908V                        OBJECT IDENTIFIER ::= { hpSwitch 138 }
hp550048GPoEPlus4SFPHITAA2Slot  OBJECT IDENTIFIER ::= { hpSwitch 139 }
hp550024GPoEPlus4SFPHITAA2Slot  OBJECT IDENTIFIER ::= { hpSwitch 140 }
hp550024GSFPHITAA2Slot          OBJECT IDENTIFIER ::= { hpSwitch 141 }
hpMoonshot45XGc                 OBJECT IDENTIFIER ::= { hpSwitch 142 }
hp12910AC                       OBJECT IDENTIFIER ::= { hpSwitch 143 }
hpFF593032QSFPPlus              OBJECT IDENTIFIER ::= { hpSwitch 144 }
hpFF593032QSFPPlusTAA           OBJECT IDENTIFIER ::= { hpSwitch 145 }
hpFF7904                        OBJECT IDENTIFIER ::= { hpSwitch 146 }
hp12916AC                       OBJECT IDENTIFIER ::= { hpSwitch 147 }
hp12916DC                       OBJECT IDENTIFIER ::= { hpSwitch 148 }
hpFF5900CP48XG4QSFPPlus         OBJECT IDENTIFIER ::= { hpSwitch 149 }
hp5900CP48XG4QSFPPlus8GbFCBF    OBJECT IDENTIFIER ::= { hpSwitch 150 }
hp6125XLGTAA                    OBJECT IDENTIFIER ::= { hpSwitch 151 }
hp6125GXGTAA                    OBJECT IDENTIFIER ::= { hpSwitch 152 }
hp6125GTAA                      OBJECT IDENTIFIER ::= { hpSwitch 153 }
hp512024G4SFPXI2Slot            OBJECT IDENTIFIER ::= { hpSwitch 154 }
hp512048G4SFPXI2Slot            OBJECT IDENTIFIER ::= { hpSwitch 155 }
hp512024GPoEPlus4SFPXI2Slot     OBJECT IDENTIFIER ::= { hpSwitch 156 }
hp512048GPoEPlus4SFPXI2Slot     OBJECT IDENTIFIER ::= { hpSwitch 157 }
hp512024G4SFPXITAA2Slot         OBJECT IDENTIFIER ::= { hpSwitch 158 }
hp512048G4SFPXITAA2Slot         OBJECT IDENTIFIER ::= { hpSwitch 159 }
hp512024GPoEPlus4SFPXITAA2Slot  OBJECT IDENTIFIER ::= { hpSwitch 160 }
hp512048GPoEPlus4SFPXITAA2Slot  OBJECT IDENTIFIER ::= { hpSwitch 161 }
hp19208G                        OBJECT IDENTIFIER ::= { hpSwitch 162 }
hp19208GPoEPlus65W              OBJECT IDENTIFIER ::= { hpSwitch 163 }
hp19208GPoEPlus180W             OBJECT IDENTIFIER ::= { hpSwitch 164 }
hp192016G                       OBJECT IDENTIFIER ::= { hpSwitch 165 }
hp192024G                       OBJECT IDENTIFIER ::= { hpSwitch 166 }
hp192024GPoEPlus180W            OBJECT IDENTIFIER ::= { hpSwitch 167 }
hp192024GPoEPlus370W            OBJECT IDENTIFIER ::= { hpSwitch 168 }
hp192048G                       OBJECT IDENTIFIER ::= { hpSwitch 169 }
hp192048GPoEPlus370W            OBJECT IDENTIFIER ::= { hpSwitch 170 }
hpFF570040XG2QSFPPlusTAA        OBJECT IDENTIFIER ::= { hpSwitch 171 }
hpFF570040XG2QSFPPlus           OBJECT IDENTIFIER ::= { hpSwitch 172 }
hpFF570032XGT8XG2QSFPPlusTAA    OBJECT IDENTIFIER ::= { hpSwitch 173 }
hpFF570032XGT8XG2QSFPPlus       OBJECT IDENTIFIER ::= { hpSwitch 174 }
hpFF570048G4XG2QSFPPlusTAA      OBJECT IDENTIFIER ::= { hpSwitch 175 }
hpFF570048G4XG2QSFPPlus         OBJECT IDENTIFIER ::= { hpSwitch 176 }
hp16208G                        OBJECT IDENTIFIER ::= { hpSwitch 177 }
hp162024G                       OBJECT IDENTIFIER ::= { hpSwitch 178 }
hp162048G                       OBJECT IDENTIFIER ::= { hpSwitch 179 }
hp195024G2SFPPlus2XGT           OBJECT IDENTIFIER ::= { hpSwitch 180 }
hp195048G2SFPPlus2XGT           OBJECT IDENTIFIER ::= { hpSwitch 181 }
hp195024G2SFPPlus2XGTPoEPlus    OBJECT IDENTIFIER ::= { hpSwitch 182 }
hp195048G2SFPPlus2XGTPoEPlus    OBJECT IDENTIFIER ::= { hpSwitch 183 }
hp513024G4SFPPlusEI             OBJECT IDENTIFIER ::= { hpSwitch 184 }
hp513024GSFP4SFPPlusEI          OBJECT IDENTIFIER ::= { hpSwitch 185 }
hp513048G4SFPPlusEI             OBJECT IDENTIFIER ::= { hpSwitch 186 }
hp513024GPoEPlus4SFPPlus180WEI  OBJECT IDENTIFIER ::= { hpSwitch 187 }
hp513024GPoEPlus4SFPPlus370WEI  OBJECT IDENTIFIER ::= { hpSwitch 188 }
hp513048GPoEPlus4SFPPlus370WEI  OBJECT IDENTIFIER ::= { hpSwitch 189 }
hp513024G2SFPPlus2XGTEI         OBJECT IDENTIFIER ::= { hpSwitch 190 }
hp513048G2SFPPlus2XGTEI         OBJECT IDENTIFIER ::= { hpSwitch 191 }
hp513024GPoEPlus2SFPPlus2XGT370WEI  OBJECT IDENTIFIER ::= { hpSwitch 192 }
hp513048GPoEPlus2SFPPlus2XGT370WEI  OBJECT IDENTIFIER ::= { hpSwitch 193 }
hp513024G4SFPPlusEITAA          OBJECT IDENTIFIER ::= { hpSwitch 194 }
hp513024GSFP4SFPPlusEITAA       OBJECT IDENTIFIER ::= { hpSwitch 195 }
hp513048G4SFPPlusEITAA          OBJECT IDENTIFIER ::= { hpSwitch 196 }
hp513024GPoEPlus4SFPPlus180WEITAA   OBJECT IDENTIFIER ::= { hpSwitch 197 }
hp513024GPoEPlus4SFPPlus370WEITAA   OBJECT IDENTIFIER ::= { hpSwitch 198 }
hp513048GPoEPlus4SFPPlus370WEITAA   OBJECT IDENTIFIER ::= { hpSwitch 199 }
hp513024G2SFPPlus2XGTEITAA      OBJECT IDENTIFIER ::= { hpSwitch 200 }
hp513048G2SFPPlus2XGTEITAA      OBJECT IDENTIFIER ::= { hpSwitch 201 }
hp513024GPoEPlus2SFPPlus2XGT370WEITAA  OBJECT IDENTIFIER ::= { hpSwitch 202 }
hp513048GPoEPlus2SFPPlus2XGT370WEITAA  OBJECT IDENTIFIER ::= { hpSwitch 203 }
hpFF7910                        OBJECT IDENTIFIER ::= { hpSwitch 204 }

-- begin hpRouter
hpAMSR900                       OBJECT IDENTIFIER ::= { hpRouter 1 }
hpAMSR920                       OBJECT IDENTIFIER ::= { hpRouter 2 }
hpAMSR2010                      OBJECT IDENTIFIER ::= { hpRouter 3 }
hpAMSR2011                      OBJECT IDENTIFIER ::= { hpRouter 4 }
hpAMSR2012                      OBJECT IDENTIFIER ::= { hpRouter 5 }
hpAMSR2012T                     OBJECT IDENTIFIER ::= { hpRouter 6 }
hpAMSR2013                      OBJECT IDENTIFIER ::= { hpRouter 7 }
hpAMSR2020                      OBJECT IDENTIFIER ::= { hpRouter 8 }
hpAMSR2021                      OBJECT IDENTIFIER ::= { hpRouter 9 }
hpAMSR2040                      OBJECT IDENTIFIER ::= { hpRouter 10 }
hpAMSR3010                      OBJECT IDENTIFIER ::= { hpRouter 11 }
hpAMSR3011E                     OBJECT IDENTIFIER ::= { hpRouter 12 }
hpAMSR3011F                     OBJECT IDENTIFIER ::= { hpRouter 13 }
hpAMSR3016                      OBJECT IDENTIFIER ::= { hpRouter 14 }
hpAMSR3020                      OBJECT IDENTIFIER ::= { hpRouter 15 }
hpAMSR3040                      OBJECT IDENTIFIER ::= { hpRouter 16 }
hpAMSR3060                      OBJECT IDENTIFIER ::= { hpRouter 17 }
hpAMSR5040                      OBJECT IDENTIFIER ::= { hpRouter 18 }
hpAMSR5060                      OBJECT IDENTIFIER ::= { hpRouter 19 }
hpA6602                         OBJECT IDENTIFIER ::= { hpRouter 20 }
hpA6604                         OBJECT IDENTIFIER ::= { hpRouter 21 }
hpA6608                         OBJECT IDENTIFIER ::= { hpRouter 22 }
hpA6616                         OBJECT IDENTIFIER ::= { hpRouter 23 }
hpAMSR900W                      OBJECT IDENTIFIER ::= { hpRouter 24 }
hpAMSR900WNA                    OBJECT IDENTIFIER ::= { hpRouter 25 }
hpAMSR920W                      OBJECT IDENTIFIER ::= { hpRouter 26 }
hpAMSR920WNA                    OBJECT IDENTIFIER ::= { hpRouter 27 }
hpAMSR2012W                     OBJECT IDENTIFIER ::= { hpRouter 28 }
hpAMSR2012TW                    OBJECT IDENTIFIER ::= { hpRouter 29 }
hpAMSR2012TWNA                  OBJECT IDENTIFIER ::= { hpRouter 30 }
hpAMSR2013W                     OBJECT IDENTIFIER ::= { hpRouter 31 }
hpAMSR2013WNA                   OBJECT IDENTIFIER ::= { hpRouter 32 }
hpAMSR2020S                     OBJECT IDENTIFIER ::= { hpRouter 33 }
hpAMSR2021S                     OBJECT IDENTIFIER ::= { hpRouter 34 }
hpAMSR2040S                     OBJECT IDENTIFIER ::= { hpRouter 35 }
hpAMSR3010DC                    OBJECT IDENTIFIER ::= { hpRouter 36 }
hpAMSR3016POE                   OBJECT IDENTIFIER ::= { hpRouter 37 }
hpAMSR3020AS                    OBJECT IDENTIFIER ::= { hpRouter 38 }
hpAMSR3020POE                   OBJECT IDENTIFIER ::= { hpRouter 39 }
hpAMSR3020DC                    OBJECT IDENTIFIER ::= { hpRouter 40 }
hpAMSR3040AS                    OBJECT IDENTIFIER ::= { hpRouter 41 }
hpAMSR3040POE                   OBJECT IDENTIFIER ::= { hpRouter 42 }
hpAMSR3040DC                    OBJECT IDENTIFIER ::= { hpRouter 43 }
hpAMSR3060AS                    OBJECT IDENTIFIER ::= { hpRouter 44 }
hpAMSR3060POE                   OBJECT IDENTIFIER ::= { hpRouter 45 }
hpAMSR3060DC                    OBJECT IDENTIFIER ::= { hpRouter 46 }
hpAMSR5040DC                    OBJECT IDENTIFIER ::= { hpRouter 47 }
hpAMSR5060DC                    OBJECT IDENTIFIER ::= { hpRouter 48 }
hpA8805                         OBJECT IDENTIFIER ::= { hpRouter 49 }
hpA8808                         OBJECT IDENTIFIER ::= { hpRouter 50 }
hpA8812                         OBJECT IDENTIFIER ::= { hpRouter 51 }
hpAOAPFICV2                     OBJECT IDENTIFIER ::= { hpRouter 52 }
hpAOAPMIMV2                     OBJECT IDENTIFIER ::= { hpRouter 53 }
hpAOAPSMIMV2                    OBJECT IDENTIFIER ::= { hpRouter 54 }
hpMSR2003AC                     OBJECT IDENTIFIER ::= { hpRouter 55 }
hpMSR3012AC                     OBJECT IDENTIFIER ::= { hpRouter 56 }
hpMSR3012DC                     OBJECT IDENTIFIER ::= { hpRouter 57 }
hpMSR3024AC                     OBJECT IDENTIFIER ::= { hpRouter 58 }
hpMSR3024DC                     OBJECT IDENTIFIER ::= { hpRouter 59 }
hpMSR3024POE                    OBJECT IDENTIFIER ::= { hpRouter 60 }
hpMSR3044                       OBJECT IDENTIFIER ::= { hpRouter 61 }
hpMSR3064                       OBJECT IDENTIFIER ::= { hpRouter 62 }
hpMSR4060                       OBJECT IDENTIFIER ::= { hpRouter 63 }
hpMSR4080                       OBJECT IDENTIFIER ::= { hpRouter 64 }
hpHSR6602G                      OBJECT IDENTIFIER ::= { hpRouter 65 }
hpHSR6602XG                     OBJECT IDENTIFIER ::= { hpRouter 66 }
hpHSR6802                       OBJECT IDENTIFIER ::= { hpRouter 67 }
hpHSR6804                       OBJECT IDENTIFIER ::= { hpRouter 68 }
hpHSR6808                       OBJECT IDENTIFIER ::= { hpRouter 69 }
hpMSR930                        OBJECT IDENTIFIER ::= { hpRouter 70 }
hpMSR930G                       OBJECT IDENTIFIER ::= { hpRouter 71 }
hpMSR931                        OBJECT IDENTIFIER ::= { hpRouter 72 }
hpMSR931G                       OBJECT IDENTIFIER ::= { hpRouter 73 }
hpMSR931GG                      OBJECT IDENTIFIER ::= { hpRouter 74 }
hpMSR930W                       OBJECT IDENTIFIER ::= { hpRouter 75 }
hpMSR9304GLTEV                  OBJECT IDENTIFIER ::= { hpRouter 76 }
hpMSR933                        OBJECT IDENTIFIER ::= { hpRouter 77 }
hpMSR933G                       OBJECT IDENTIFIER ::= { hpRouter 78 }
hpMSR935                        OBJECT IDENTIFIER ::= { hpRouter 79 }
hpMSR935W                       OBJECT IDENTIFIER ::= { hpRouter 80 }
hpMSR935G                       OBJECT IDENTIFIER ::= { hpRouter 81 }
hpMSR936W                       OBJECT IDENTIFIER ::= { hpRouter 82 }
hpMSR9304GLTEG                  OBJECT IDENTIFIER ::= { hpRouter 83 }
hpMSR930LE                      OBJECT IDENTIFIER ::= { hpRouter 84 }
hpMSR930GLE                     OBJECT IDENTIFIER ::= { hpRouter 85 }
hpMSR931LE                      OBJECT IDENTIFIER ::= { hpRouter 86 }
hpMSR931GLE                     OBJECT IDENTIFIER ::= { hpRouter 87 }
hpMSR931DGLE                    OBJECT IDENTIFIER ::= { hpRouter 88 }
hpMSR930WLE                     OBJECT IDENTIFIER ::= { hpRouter 89 }
hpMSR9304GLTEA                  OBJECT IDENTIFIER ::= { hpRouter 90 }
hpMSR933GLE                     OBJECT IDENTIFIER ::= { hpRouter 91 }
hpMSR935LE                      OBJECT IDENTIFIER ::= { hpRouter 92 }
hpMSR935WLE                     OBJECT IDENTIFIER ::= { hpRouter 93 }
hpMSR935GLE                     OBJECT IDENTIFIER ::= { hpRouter 94 }
hpMSR9304GLTEGLE                OBJECT IDENTIFIER ::= { hpRouter 95 }
hpVSR                           OBJECT IDENTIFIER ::= { hpRouter 96 }
hpVSR1001                       OBJECT IDENTIFIER ::= { hpRouter 97 }
hpVSR1004                       OBJECT IDENTIFIER ::= { hpRouter 98 }
hpVSR1008                       OBJECT IDENTIFIER ::= { hpRouter 99 }
hpMSR10038                      OBJECT IDENTIFIER ::= { hpRouter 100 }
hpMSR100414                     OBJECT IDENTIFIER ::= { hpRouter 101 }
hpVSR1000                       OBJECT IDENTIFIER ::= { hpRouter 102 }
hpMSR200424                     OBJECT IDENTIFIER ::= { hpRouter 103 }
hpMSR200448                     OBJECT IDENTIFIER ::= { hpRouter 104 }
hpHSR6602GTAA                   OBJECT IDENTIFIER ::= { hpRouter 105 }
hpHSR6602XGTAA                  OBJECT IDENTIFIER ::= { hpRouter 106 }
hpMSR10024                      OBJECT IDENTIFIER ::= { hpRouter 107 }
hpNSC1000                       OBJECT IDENTIFIER ::= { hpRouter 108 }
hpMSR930WNA                     OBJECT IDENTIFIER ::= { hpRouter 109 }
hpMSR935WNA                     OBJECT IDENTIFIER ::= { hpRouter 110 }
hpMSR2003TAA                    OBJECT IDENTIFIER ::= { hpRouter 111 }
hpMSR3024TAA                    OBJECT IDENTIFIER ::= { hpRouter 112 }
hpMSR3044TAA                    OBJECT IDENTIFIER ::= { hpRouter 113 }
hpMSR935TI                      OBJECT IDENTIFIER ::= { hpRouter 114 }
hpMSR933TI                      OBJECT IDENTIFIER ::= { hpRouter 115 }
hpMSR931TI                      OBJECT IDENTIFIER ::= { hpRouter 116 }
hpMSR10038S                     OBJECT IDENTIFIER ::= { hpRouter 117 }

-- begin hpWireless
hpAWA2610EAGNFAT                OBJECT IDENTIFIER ::= { hpWireless 1 }
hpAWA2620EAGNFAT                OBJECT IDENTIFIER ::= { hpWireless 2 }
hpAWA2620AGNFAT                 OBJECT IDENTIFIER ::= { hpWireless 3 }
hpA7500LSQM3WCMB0               OBJECT IDENTIFIER ::= { hpWireless 4 }
hpA9500LSRM2WCM2A1              OBJECT IDENTIFIER ::= { hpWireless 5 }
hpA5800LSWM2WCM10               OBJECT IDENTIFIER ::= { hpWireless 6 }
hpA5800LSWM2WCM20               OBJECT IDENTIFIER ::= { hpWireless 7 }
hpAWX5004EWPXZ65004             OBJECT IDENTIFIER ::= { hpWireless 8 }
hpAWX5002EWPXZ75002             OBJECT IDENTIFIER ::= { hpWireless 9 }
hpA3000E                        OBJECT IDENTIFIER ::= { hpWireless 10 }
hpA3000ELSW                     OBJECT IDENTIFIER ::= { hpWireless 11 }
hpAWA3620AGN                    OBJECT IDENTIFIER ::= { hpWireless 12 }
hpAWA3622AGN                    OBJECT IDENTIFIER ::= { hpWireless 13 }
hpAWA3610GN                     OBJECT IDENTIFIER ::= { hpWireless 14 }
hpAWA2620XAGN                   OBJECT IDENTIFIER ::= { hpWireless 15 }
hpLSU3WCMD0                     OBJECT IDENTIFIER ::= { hpWireless 16 }
hpWX3024EWCM                    OBJECT IDENTIFIER ::= { hpWireless 17 }
hpWX3024ELSW                    OBJECT IDENTIFIER ::= { hpWireless 18 }
hpWX3010EWCM                    OBJECT IDENTIFIER ::= { hpWireless 19 }
hpWX3010ELSW                    OBJECT IDENTIFIER ::= { hpWireless 20 }
hpLSU3WCMD0TAA                  OBJECT IDENTIFIER ::= { hpWireless 21 }
hpWX3024ETAAWCM                 OBJECT IDENTIFIER ::= { hpWireless 22 }
hpWX3024ETAALSW                 OBJECT IDENTIFIER ::= { hpWireless 23 }
hpWX3010ETAAWCM                 OBJECT IDENTIFIER ::= { hpWireless 24 }
hpWX3010ETAALSW                 OBJECT IDENTIFIER ::= { hpWireless 25 }

-- begin hpSecurity
hpSecBladeIMFWII                OBJECT IDENTIFIER ::= { hpSecurity 1 }
hpSecBladeIMSSL                 OBJECT IDENTIFIER ::= { hpSecurity 2 }
hpSecBladeIMLB                  OBJECT IDENTIFIER ::= { hpSecurity 3 }
hpSecBladeLSQ1FWBSC0            OBJECT IDENTIFIER ::= { hpSecurity 4 }
hpSecBladeLSQM1LBC0             OBJECT IDENTIFIER ::= { hpSecurity 5 }
hpSecBladeLSQ1NSMSC0            OBJECT IDENTIFIER ::= { hpSecurity 6 }
hpSecBladeLSR1FW2A1             OBJECT IDENTIFIER ::= { hpSecurity 7 }
hpSecBladeLSR1LB1A1             OBJECT IDENTIFIER ::= { hpSecurity 8 }
hpSecBladeLSR1NSM1A1            OBJECT IDENTIFIER ::= { hpSecurity 9 }
hpSecBladeLST1FW2A1             OBJECT IDENTIFIER ::= { hpSecurity 10 }
hpSecBladeLST1LB1A1             OBJECT IDENTIFIER ::= { hpSecurity 11 }
hpSecBladeLST1NSM1A1            OBJECT IDENTIFIER ::= { hpSecurity 12 }
hpSecBladeLSWM1FW10             OBJECT IDENTIFIER ::= { hpSecurity 13 }
hpSecBladeSPEFWM200             OBJECT IDENTIFIER ::= { hpSecurity 14 }
hpAF5000                        OBJECT IDENTIFIER ::= { hpSecurity 15 }
hpAF1000E                       OBJECT IDENTIFIER ::= { hpSecurity 16 }
hpAU200S                        OBJECT IDENTIFIER ::= { hpSecurity 17 }
hpAU200A                        OBJECT IDENTIFIER ::= { hpSecurity 18 }
hpAF1000SEI                     OBJECT IDENTIFIER ::= { hpSecurity 19 }
hpAF1000AEI                     OBJECT IDENTIFIER ::= { hpSecurity 20 }
hpSecBladeLST1FW3A1             OBJECT IDENTIFIER ::= { hpSecurity 21 }
hpSecBladeLSU1FWCEA0            OBJECT IDENTIFIER ::= { hpSecurity 22 }
hpF5000C                        OBJECT IDENTIFIER ::= { hpSecurity 23 }
hpF5000S                        OBJECT IDENTIFIER ::= { hpSecurity 24 }
hpVFW1000                       OBJECT IDENTIFIER ::= { hpSecurity 25 }
hpSecBladeLSX1FWCEA1            OBJECT IDENTIFIER ::= { hpSecurity 26 }
hpVMSGVLB1000                   OBJECT IDENTIFIER ::= { hpSecurity 27 }

END
