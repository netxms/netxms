-- vim: syntax=mib
--
-- WS-INFRA-FILE-MGMT-MIB.my
-- MIB generated by MG-SOFT Visual MIB Builder Version 6.0  Build 88
-- Friday, October 06, 2006 at 11:14:57
--

	WS-INFRA-FILE-MGMT-MIB DEFINITIONS ::= BEGIN
 
		IMPORTS
			OBJECT-GROUP, MODULE-COMPLIANCE			
				FROM SNMPv2-CONF			
			Integer32, Counter32, OBJECT-TYPE, MODULE-IDENTITY			
				FROM SNMPv2-SMI			
			DisplayString, TruthValue, DateAndTime			
				FROM SNMPv2-TC			
			wsInfraFileMgmt			
				FROM WS-INFRA-SMI-MIB;
	
	
		-- 1.3.6.1.4.1.388.14.1.2.1
		wsInfraFileMgmtModule MODULE-IDENTITY 
			LAST-UPDATED "200610061114Z"		-- October 06, 2006 at 11:14 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200610061114Z"		-- October 06, 2006 at 11:14 GMT
			DESCRIPTION 
				"01a24"
			REVISION "200607061149Z"		-- July 06, 2006 at 11:49 GMT
			DESCRIPTION 
				"01a23"
			REVISION "200606261857Z"		-- June 26, 2006 at 18:57 GMT
			DESCRIPTION 
				"01a22"
			REVISION "200605261452Z"		-- May 26, 2006 at 14:52 GMT
			DESCRIPTION 
				"01a21"
			REVISION "200605241044Z"		-- May 24, 2006 at 10:44 GMT
			DESCRIPTION 
				"01a20"
			REVISION "200511141548Z"		-- November 14, 2005 at 15:48 GMT
			DESCRIPTION 
				"01a19"
			REVISION "200511031014Z"		-- November 03, 2005 at 10:14 GMT
			DESCRIPTION 
				"01a18"
			REVISION "200510181612Z"		-- October 18, 2005 at 16:12 GMT
			DESCRIPTION 
				"01a17"
			REVISION "200510121410Z"		-- October 12, 2005 at 14:10 GMT
			DESCRIPTION 
				"01a16"
			REVISION "200510121355Z"		-- October 12, 2005 at 13:55 GMT
			DESCRIPTION 
				"01a15"
			REVISION "200510121103Z"		-- October 12, 2005 at 11:03 GMT
			DESCRIPTION 
				"01a14"
			REVISION "200510111733Z"		-- October 11, 2005 at 17:33 GMT
			DESCRIPTION 
				"01a13"
			REVISION "200508041018Z"		-- August 04, 2005 at 10:18 GMT
			DESCRIPTION 
				"01a12"
			REVISION "200507061149Z"		-- July 06, 2005 at 11:49 GMT
			DESCRIPTION 
				"01a11"
			REVISION "200506281158Z"		-- June 28, 2005 at 11:58 GMT
			DESCRIPTION 
				"01a10"
			REVISION "200506271434Z"		-- June 27, 2005 at 14:34 GMT
			DESCRIPTION 
				"01a09"
			REVISION "200506241207Z"		-- June 24, 2005 at 12:07 GMT
			DESCRIPTION 
				"01a08"
			REVISION "200506231317Z"		-- June 23, 2005 at 13:17 GMT
			DESCRIPTION 
				"01a07"
			REVISION "200506221034Z"		-- June 22, 2005 at 10:34 GMT
			DESCRIPTION 
				"01a06"
			REVISION "200506201105Z"		-- June 20, 2005 at 11:05 GMT
			DESCRIPTION 
				"01a05"
			REVISION "200506091524Z"		-- June 09, 2005 at 15:24 GMT
			DESCRIPTION 
				"01a04"
			REVISION "200506071843Z"		-- June 07, 2005 at 18:43 GMT
			DESCRIPTION 
				"01a03"
			REVISION "200505041613Z"		-- May 04, 2005 at 16:13 GMT
			DESCRIPTION 
				"01a02"
			REVISION "200505041058Z"		-- May 04, 2005 at 10:58 GMT
			DESCRIPTION 
				"01a01"
			::= { wsInfraFileMgmt 1 }

		
	
--
-- Type definitions
--
	
		DoActionState ::= INTEGER
			{
			success(1),
			failure(2),
			inProgress(3)
			}

	
	
--
-- Node definitions
--
	
		-- 1.3.6.1.4.1.388.14.1.2.1.1
		wsInfraFileMgmtDir OBJECT IDENTIFIER ::= { wsInfraFileMgmtModule 1 }

		
		-- 1.3.6.1.4.1.388.14.1.2.1.1.1
		wsInfraFileMgmtDirString OBJECT-TYPE
			SYNTAX DisplayString
			MAX-ACCESS read-write
			STATUS current
			DESCRIPTION
				"current working directory"
			::= { wsInfraFileMgmtDir 1 }

		
		-- 1.3.6.1.4.1.388.14.1.2.1.1.2
		wsInfraFIleMgmtDirError OBJECT-TYPE
			SYNTAX DisplayString
			MAX-ACCESS read-only
			STATUS current
			DESCRIPTION
				"error of changing the current working directory"
			::= { wsInfraFileMgmtDir 2 }

		
		-- 1.3.6.1.4.1.388.14.1.2.1.2
		wsInfraFileTable OBJECT-TYPE
			SYNTAX SEQUENCE OF WsInfraFileEntry
			MAX-ACCESS not-accessible
			STATUS current
			DESCRIPTION
				"local file table"
			::= { wsInfraFileMgmtModule 2 }

		
		-- 1.3.6.1.4.1.388.14.1.2.1.2.1
		wsInfraFileEntry OBJECT-TYPE
			SYNTAX WsInfraFileEntry
			MAX-ACCESS not-accessible
			STATUS current
			DESCRIPTION
				"local file table entry"
			INDEX { wsInfraFileIndex }
			::= { wsInfraFileTable 1 }

		
		WsInfraFileEntry ::=
			SEQUENCE { 
				wsInfraFileIndex
					INTEGER,
				wsInfraFileName
					DisplayString,
				wsInfraFileType
					INTEGER,
				wsInfraFileSize
					Integer32,
				wsInfraFilePerm
					DisplayString,
				wsInfraFileCreateDate
					DateAndTime,
				wsInfraFileModDate
					DateAndTime
			 }

		-- 1.3.6.1.4.1.388.14.1.2.1.2.1.1
		wsInfraFileIndex OBJECT-TYPE
			SYNTAX INTEGER (1..100)
			MAX-ACCESS accessible-for-notify
			STATUS current
			DESCRIPTION
				"simple index for file table"
			::= { wsInfraFileEntry 1 }

		
		-- 1.3.6.1.4.1.388.14.1.2.1.2.1.2
		wsInfraFileName OBJECT-TYPE
			SYNTAX DisplayString (SIZE (1..128))
			MAX-ACCESS read-only
			STATUS current
			DESCRIPTION
				"file name"
			::= { wsInfraFileEntry 2 }

		
		-- 1.3.6.1.4.1.388.14.1.2.1.2.1.3
		wsInfraFileType OBJECT-TYPE
			SYNTAX INTEGER
				{
				binary(1),
				text(2),
				unknown(3),
				directory(4),
				symlink(5),
				emptyFile(6),
				unReadableFile(7),
				logFile(8),
				historyFile(9),
				configFile(10),
				licFile(11),
				certFile(12),
				coreFile(13),
				panicFile(14),
				dumpFile(15),
				pcapFile(16)
				}
			MAX-ACCESS read-only
			STATUS current
			DESCRIPTION
				"file type"
			::= { wsInfraFileEntry 3 }

		
		-- 1.3.6.1.4.1.388.14.1.2.1.2.1.4
		wsInfraFileSize OBJECT-TYPE
			SYNTAX Integer32
			UNITS "byte"
			MAX-ACCESS read-only
			STATUS current
			DESCRIPTION
				"file size"
			::= { wsInfraFileEntry 4 }

		
		-- 1.3.6.1.4.1.388.14.1.2.1.2.1.5
		wsInfraFilePerm OBJECT-TYPE
			SYNTAX DisplayString (SIZE (1..16))
			MAX-ACCESS read-only
			STATUS current
			DESCRIPTION
				"permission of the file"
			::= { wsInfraFileEntry 5 }

		
		-- 1.3.6.1.4.1.388.14.1.2.1.2.1.6
		wsInfraFileCreateDate OBJECT-TYPE
			SYNTAX DateAndTime
			MAX-ACCESS read-only
			STATUS current
			DESCRIPTION
				"file creation date"
			::= { wsInfraFileEntry 6 }

		
		-- 1.3.6.1.4.1.388.14.1.2.1.2.1.7
		wsInfraFileModDate OBJECT-TYPE
			SYNTAX DateAndTime
			MAX-ACCESS read-only
			STATUS current
			DESCRIPTION
				"file modification date"
			::= { wsInfraFileEntry 7 }

		
		-- 1.3.6.1.4.1.388.14.1.2.1.3
		wsInfraFileMgmtImageTable OBJECT-TYPE
			SYNTAX SEQUENCE OF WsInfraFileMgmtImageEntry
			MAX-ACCESS not-accessible
			STATUS current
			DESCRIPTION
				"Description."
			::= { wsInfraFileMgmtModule 3 }

		
		-- 1.3.6.1.4.1.388.14.1.2.1.3.1
		wsInfraFileMgmtImageEntry OBJECT-TYPE
			SYNTAX WsInfraFileMgmtImageEntry
			MAX-ACCESS not-accessible
			STATUS current
			DESCRIPTION
				"Description."
			INDEX { wsInfraFileMgmtImageIndex }
			::= { wsInfraFileMgmtImageTable 1 }

		
		WsInfraFileMgmtImageEntry ::=
			SEQUENCE { 
				wsInfraFileMgmtImageIndex
					INTEGER,
				wsInfraFileMgmtImageVersion
					DisplayString,
				wsInfraFileMgmtImageUseNow
					TruthValue,
				wsInfraFileMgmtImageUseOnBoot
					TruthValue,
				wsInfraFileMgmtImageBuildTime
					DateAndTime,
				wsInfraFileMgmtImageInstallTime
					DateAndTime
			 }

		-- 1.3.6.1.4.1.388.14.1.2.1.3.1.1
		wsInfraFileMgmtImageIndex OBJECT-TYPE
			SYNTAX INTEGER (1..2)
			MAX-ACCESS accessible-for-notify
			STATUS current
			DESCRIPTION
				"simple index of image table"
			::= { wsInfraFileMgmtImageEntry 1 }

		
		-- 1.3.6.1.4.1.388.14.1.2.1.3.1.2
		wsInfraFileMgmtImageVersion OBJECT-TYPE
			SYNTAX DisplayString
			MAX-ACCESS read-only
			STATUS current
			DESCRIPTION
				"version of the image"
			::= { wsInfraFileMgmtImageEntry 2 }

		
		-- 1.3.6.1.4.1.388.14.1.2.1.3.1.3
		wsInfraFileMgmtImageUseNow OBJECT-TYPE
			SYNTAX TruthValue
			MAX-ACCESS read-only
			STATUS current
			DESCRIPTION
				"indicate if it is used by the system"
			::= { wsInfraFileMgmtImageEntry 3 }

		
		-- 1.3.6.1.4.1.388.14.1.2.1.3.1.4
		wsInfraFileMgmtImageUseOnBoot OBJECT-TYPE
			SYNTAX TruthValue
			MAX-ACCESS read-write
			STATUS current
			DESCRIPTION
				"indicate if it is used on the reboot"
			::= { wsInfraFileMgmtImageEntry 4 }

		
		-- 1.3.6.1.4.1.388.14.1.2.1.3.1.5
		wsInfraFileMgmtImageBuildTime OBJECT-TYPE
			SYNTAX DateAndTime
			MAX-ACCESS read-only
			STATUS current
			DESCRIPTION
				"image build time"
			::= { wsInfraFileMgmtImageEntry 5 }

		
		-- 1.3.6.1.4.1.388.14.1.2.1.3.1.6
		wsInfraFileMgmtImageInstallTime OBJECT-TYPE
			SYNTAX DateAndTime
			MAX-ACCESS read-only
			STATUS current
			DESCRIPTION
				"image install time"
			::= { wsInfraFileMgmtImageEntry 6 }

		
		-- 1.3.6.1.4.1.388.14.1.2.1.4
		wsInfraImgUpd OBJECT IDENTIFIER ::= { wsInfraFileMgmtModule 4 }
-- the scalar objects below will do the network ile transfer
-- and firmware image update feature. If it is a firmware image
-- update, the switchFile and switchFileLocation will be ignored.
		
		-- 1.3.6.1.4.1.388.14.1.2.1.4.1
		wsInfraImgUpdFile OBJECT-TYPE
			SYNTAX DisplayString
			MAX-ACCESS read-write
			STATUS current
			DESCRIPTION
				"image update file, The location can be specified as
				tftp://<hostname or IP>/path/imgfile or
				ftp://<user>:<passwd>@<hostname or IP>/path/imgfile"
			::= { wsInfraImgUpd 1 }

		
		-- 1.3.6.1.4.1.388.14.1.2.1.4.2
		wsInfraImgUpdStart OBJECT-TYPE
			SYNTAX INTEGER
				{
				imgUpdate(1),
				abortUpdate(2),
				idle(3),
				removePatch(4)
				}
			MAX-ACCESS read-write
			STATUS current
			DESCRIPTION
				"network file transfer start, set this value to 1 means starting
				imgUpdate, set to 2 means aborting img update. If there is no imgUpdate,
				the back end will set this value to idle."
			::= { wsInfraImgUpd 2 }

		
		-- 1.3.6.1.4.1.388.14.1.2.1.4.3
		wsInfraImgUpdStatus OBJECT-TYPE
			SYNTAX DoActionState
			MAX-ACCESS read-only
			STATUS current
			DESCRIPTION
				"status of the file transfer, the possible values are
				success(1), failure(2) and inProgress. We may need to add
				more failure return codes in the future.
				"
			::= { wsInfraImgUpd 3 }

		
		-- 1.3.6.1.4.1.388.14.1.2.1.4.4
		wsInfraImgUpdLastFailedReason OBJECT-TYPE
			SYNTAX DisplayString
			MAX-ACCESS read-only
			STATUS current
			DESCRIPTION
				"last fileTransfer/imageUpdate failed reason"
			::= { wsInfraImgUpd 4 }

		
		-- 1.3.6.1.4.1.388.14.1.2.1.4.5
		wsInfraImgUpdCounter OBJECT-TYPE
			SYNTAX Counter32
			MAX-ACCESS read-only
			STATUS current
			DESCRIPTION
				"it is a gauge counter which will be increased by every file
				trasfer action"
			::= { wsInfraImgUpd 5 }

		
		-- 1.3.6.1.4.1.388.14.1.2.1.5
		wsInfraFileManage OBJECT IDENTIFIER ::= { wsInfraFileMgmtModule 5 }
-- local file management
		
		-- 1.3.6.1.4.1.388.14.1.2.1.5.1
		wsInfraFileManageSrc OBJECT-TYPE
			SYNTAX DisplayString
			MAX-ACCESS read-write
			STATUS current
			DESCRIPTION
				"name of the src file"
			::= { wsInfraFileManage 1 }

		
		-- 1.3.6.1.4.1.388.14.1.2.1.5.2
		wsInfraFileManageDest OBJECT-TYPE
			SYNTAX DisplayString (SIZE (0..128))
			MAX-ACCESS read-write
			STATUS current
			DESCRIPTION
				"name of the dest file"
			::= { wsInfraFileManage 2 }

		
		-- 1.3.6.1.4.1.388.14.1.2.1.5.3
		wsInfraFileManageStart OBJECT-TYPE
			SYNTAX INTEGER
				{
				copy(1),
				delete(2),
				rename(3),
				rmDir(4),
				mkDir(5),
				importKey(6),
				importCACert(7),
				importServerCert(8),
				importTrustPoint(9),
				exportKey(10),
				exportCert(11),
				exportReq(12),
				exportTrustPoint(13),
				idle(14),
				computeSavedCfgChkSum(15),
				computeRunningCfgChkSum(16),
				abort(17),
				expand(18)
				}
			MAX-ACCESS read-write
			STATUS current
			DESCRIPTION
				"local file management start, setting this value to 1 means copy,
				2 means delete, 3 means rename, 4 means rmdir, 5 mean mkdir, and
				when there is no local file management, the back end
				will set this value to idle.
				copy/rename, both src and dest need to be specified
				delete/rmdir/mkdir, only src needs to be specified
				
				Files: flash:/path/file
				       nvram:startup-config
				       system:running-config
				
				URLs: tftp://<hostname or IP>/path/file
				      ftp://<user>:<passwd>@<hostname or IP>/path/file
				      scp://<user>@<hostname or IP>/path/file
				
				"
			::= { wsInfraFileManage 3 }

		
		-- 1.3.6.1.4.1.388.14.1.2.1.5.4
		wsInfraFileManageStatus OBJECT-TYPE
			SYNTAX DoActionState
			MAX-ACCESS read-only
			STATUS current
			DESCRIPTION
				"state of the file manage, success,failure, or inProgress"
			::= { wsInfraFileManage 4 }

		
		-- 1.3.6.1.4.1.388.14.1.2.1.5.5
		wsInfraFileManageLastFailedReason OBJECT-TYPE
			SYNTAX DisplayString
			MAX-ACCESS read-only
			STATUS current
			DESCRIPTION
				"file manage last failed reason."
			::= { wsInfraFileManage 5 }

		
		-- 1.3.6.1.4.1.388.14.1.2.1.5.6
		wsInfraFileManageCounter OBJECT-TYPE
			SYNTAX Counter32
			MAX-ACCESS read-only
			STATUS current
			DESCRIPTION
				"a guage counter which will be increased by the file manager
				action"
			::= { wsInfraFileManage 6 }

		
		-- 1.3.6.1.4.1.388.14.1.2.1.6
		wsInfraFileImgUpdFailOver OBJECT-TYPE
			SYNTAX TruthValue
			MAX-ACCESS read-write
			STATUS current
			DESCRIPTION
				"if there is an error in img reboot, this attribute instucts
				the system to do failover or not.It is simply a truth value."
			::= { wsInfraFileMgmtModule 6 }

		
		-- 1.3.6.1.4.1.388.14.1.2.1.7
		wsInfraCfgManage OBJECT IDENTIFIER ::= { wsInfraFileMgmtModule 7 }

		
		-- 1.3.6.1.4.1.388.14.1.2.1.7.1
		wsInfraCfgManageRunningCfgChangedFlag OBJECT-TYPE
			SYNTAX TruthValue
			MAX-ACCESS read-only
			STATUS current
			DESCRIPTION
				"This is a Boolean variable indicating if the Running Config is different from the 
				Saved Config. It indicates that there are pending changes that have not been saved 
				yet, but the switch is functioning with a config that is different from Saved 
				Config.
				"
			::= { wsInfraCfgManage 1 }

		
		-- 1.3.6.1.4.1.388.14.1.2.1.7.2
		wsInfraCfgManageSavedCfgChecksum OBJECT-TYPE
			SYNTAX OCTET STRING
			MAX-ACCESS read-only
			STATUS current
			DESCRIPTION
				"The checksum of the Saved Config text."
			::= { wsInfraCfgManage 2 }

		
		-- 1.3.6.1.4.1.388.14.1.2.1.7.3
		wsInfraCfgManageRunningCfgChecksum OBJECT-TYPE
			SYNTAX OCTET STRING
			MAX-ACCESS read-only
			STATUS current
			DESCRIPTION
				"The checksum of the Running Config text."
			::= { wsInfraCfgManage 3 }

		
		-- 1.3.6.1.4.1.388.14.1.2.1.7.4
		wsInfraCfgManageResultantChecksum OBJECT-TYPE
			SYNTAX OCTET STRING
			MAX-ACCESS read-only
			STATUS current
			DESCRIPTION
				"When FileManageStart is set to compute Saved Config or Running Config Checksum, this 
				variable holds the resultant checksum when the computation is done"
			::= { wsInfraCfgManage 4 }

		
		-- 1.3.6.1.4.1.388.14.1.2.1.8
		wsInfraFileMgmtPatchTable OBJECT-TYPE
			SYNTAX SEQUENCE OF WsInfraFileMgmtPatchEntry
			MAX-ACCESS not-accessible
			STATUS current
			DESCRIPTION
				"Table of patch names applied to build."
			::= { wsInfraFileMgmtModule 8 }

		
		-- 1.3.6.1.4.1.388.14.1.2.1.8.1
		wsInfraFileMgmtPatchEntry OBJECT-TYPE
			SYNTAX WsInfraFileMgmtPatchEntry
			MAX-ACCESS not-accessible
			STATUS current
			DESCRIPTION
				"Patch table entry."
			INDEX { wsInfraFileMgmtPatchIndex }
			::= { wsInfraFileMgmtPatchTable 1 }

		
		WsInfraFileMgmtPatchEntry ::=
			SEQUENCE { 
				wsInfraFileMgmtPatchIndex
					DisplayString,
				wsInfraFileMgmtPatchName
					DisplayString,
				wsInfraFileMgmtPatchVersion
					DisplayString
			 }

		-- 1.3.6.1.4.1.388.14.1.2.1.8.1.1
		wsInfraFileMgmtPatchIndex OBJECT-TYPE
			SYNTAX DisplayString (SIZE (1..32))
			MAX-ACCESS accessible-for-notify
			STATUS current
			DESCRIPTION
				"Index using same value as wsInfraFileMgmtPatchName."
			::= { wsInfraFileMgmtPatchEntry 1 }

		
		-- 1.3.6.1.4.1.388.14.1.2.1.8.1.2
		wsInfraFileMgmtPatchName OBJECT-TYPE
			SYNTAX DisplayString (SIZE (1..32))
			MAX-ACCESS read-write
			STATUS current
			DESCRIPTION
				"Name of patch."
			::= { wsInfraFileMgmtPatchEntry 2 }

		
		-- 1.3.6.1.4.1.388.14.1.2.1.8.1.3
		wsInfraFileMgmtPatchVersion OBJECT-TYPE
			SYNTAX DisplayString
			MAX-ACCESS read-write
			STATUS current
			DESCRIPTION
				"Version of patch in regex format [0-9]*\.[0-9]*"
			::= { wsInfraFileMgmtPatchEntry 3 }

		
		-- 1.3.6.1.4.1.388.14.1.2.1.100
		wsInfraFileMgmtMIBConformance OBJECT IDENTIFIER ::= { wsInfraFileMgmtModule 100 }

		
		-- 1.3.6.1.4.1.388.14.1.2.1.100.1
		wsInfraFileMgmtMIBGroups OBJECT IDENTIFIER ::= { wsInfraFileMgmtMIBConformance 1 }

		
		-- 1.3.6.1.4.1.388.14.1.2.1.100.1.1
		wsInfraFileMgmtGroup OBJECT-GROUP
			OBJECTS { wsInfraFileName, wsInfraFileType, wsInfraFileSize, wsInfraFileCreateDate, wsInfraFileModDate, 
				wsInfraFileManageSrc, wsInfraFileManageDest, wsInfraFileManageStatus, wsInfraFileManageLastFailedReason, wsInfraFileManageCounter, 
				wsInfraFileIndex, wsInfraFileImgUpdFailOver, wsInfraFileManageStart, wsInfraFilePerm, wsInfraFileMgmtDirString, 
				wsInfraFIleMgmtDirError, wsInfraFileMgmtImageIndex, wsInfraFileMgmtImageVersion, wsInfraFileMgmtImageUseNow, wsInfraFileMgmtImageUseOnBoot, 
				wsInfraCfgManageRunningCfgChecksum, wsInfraCfgManageSavedCfgChecksum, wsInfraCfgManageRunningCfgChangedFlag, wsInfraFileMgmtPatchVersion, wsInfraFileMgmtPatchName, 
				wsInfraFileMgmtPatchIndex, wsInfraFileMgmtImageInstallTime, wsInfraFileMgmtImageBuildTime, wsInfraImgUpdFile, wsInfraImgUpdStart, 
				wsInfraImgUpdStatus, wsInfraImgUpdLastFailedReason, wsInfraImgUpdCounter, wsInfraCfgManageResultantChecksum }
			STATUS current
			DESCRIPTION 
				"Description."
			::= { wsInfraFileMgmtMIBGroups 1 }

		
		-- 1.3.6.1.4.1.388.14.1.2.1.100.2
		wsInfraFileMgmtMIBCompliances OBJECT IDENTIFIER ::= { wsInfraFileMgmtMIBConformance 2 }

		
		-- 1.3.6.1.4.1.388.14.1.2.1.100.2.1
		wsInfraFileMgmtMIBCompliance MODULE-COMPLIANCE
			STATUS current
			DESCRIPTION 
				"Description."
			MODULE -- this module
				MANDATORY-GROUPS { wsInfraFileMgmtGroup }
			::= { wsInfraFileMgmtMIBCompliances 1 }

		
	
	END

--
-- WS-INFRA-FILE-MGMT-MIB.my
--
