-- vim: syntax=mib
--
-- WS-SW-IP-MIB.my
-- MIB generated by MG-SOFT Visual MIB Builder Version 6.0  Build 88
-- Wednesday, May 24, 2006 at 17:07:01
--

	WS-SW-IP-MIB DEFINITIONS ::= BEGIN
 
		IMPORTS
			OBJECT-GROUP, MODULE-COMPLIANCE			
				FROM SNMPv2-CONF			
			IpAddress, Unsigned32, OBJECT-TYPE, MODULE-IDENTITY			
				FROM SNMPv2-SMI			
			RowStatus, TruthValue			
				FROM SNMPv2-TC			
			wsSwIp			
				FROM WS-SW-SMI;
	
	
		-- 1.3.6.1.4.1.388.14.2.5.1
		wsSwIpModule MODULE-IDENTITY 
			LAST-UPDATED "200505121346Z"		-- May 12, 2005 at 13:46 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Switching IP module"
			REVISION "200605241706Z"		-- May 24, 2006 at 17:06 GMT
			DESCRIPTION 
				"01a07"
			REVISION "200510131546Z"		-- October 13, 2005 at 15:46 GMT
			DESCRIPTION 
				"01a06"
			REVISION "200508031132Z"		-- August 03, 2005 at 11:32 GMT
			DESCRIPTION 
				"01a05"
			REVISION "200505160948Z"		-- May 16, 2005 at 09:48 GMT
			DESCRIPTION 
				"01a04"
			REVISION "200505131717Z"		-- May 13, 2005 at 17:17 GMT
			DESCRIPTION 
				"01a03"
			REVISION "200505121812Z"		-- May 12, 2005 at 18:12 GMT
			DESCRIPTION 
				"01a02"
			REVISION "200505121346Z"		-- May 12, 2005 at 13:46 GMT
			DESCRIPTION 
				"01a01"
			::= { wsSwIp 1 }

		
	
	
--
-- Node definitions
--
	
		-- 1.3.6.1.4.1.388.14.2.5.1.1
		wsSwIpTable OBJECT-TYPE
			SYNTAX SEQUENCE OF WsSwIpEntry
			MAX-ACCESS not-accessible
			STATUS current
			DESCRIPTION
				"Switching Ip table"
			::= { wsSwIpModule 1 }

		
		-- 1.3.6.1.4.1.388.14.2.5.1.1.1
		wsSwIpEntry OBJECT-TYPE
			SYNTAX WsSwIpEntry
			MAX-ACCESS not-accessible
			STATUS current
			DESCRIPTION
				"Switching Ip table entry"
			INDEX { wsSwIpIfIndex, wsSwIpAddress, wsSwIpMask }
			::= { wsSwIpTable 1 }

		
		WsSwIpEntry ::=
			SEQUENCE { 
				wsSwIpIfIndex
					Unsigned32,
				wsSwIpAddress
					IpAddress,
				wsSwIpMask
					IpAddress,
				wsSwIpRowStatus
					RowStatus
			 }

		-- 1.3.6.1.4.1.388.14.2.5.1.1.1.1
		wsSwIpIfIndex OBJECT-TYPE
			SYNTAX Unsigned32 (1..4096)
			MAX-ACCESS read-only
			STATUS current
			DESCRIPTION
				"Vlan IfIndex number"
			::= { wsSwIpEntry 1 }

		
		-- 1.3.6.1.4.1.388.14.2.5.1.1.1.2
		wsSwIpAddress OBJECT-TYPE
			SYNTAX IpAddress
			MAX-ACCESS read-only
			STATUS current
			DESCRIPTION
				"Ip address"
			::= { wsSwIpEntry 2 }

		
		-- 1.3.6.1.4.1.388.14.2.5.1.1.1.3
		wsSwIpMask OBJECT-TYPE
			SYNTAX IpAddress
			MAX-ACCESS read-only
			STATUS current
			DESCRIPTION
				"Ip mask"
			::= { wsSwIpEntry 3 }

		
		-- 1.3.6.1.4.1.388.14.2.5.1.1.1.4
		wsSwIpRowStatus OBJECT-TYPE
			SYNTAX RowStatus
			MAX-ACCESS read-create
			STATUS current
			DESCRIPTION
				"Row status, only creatAndGo, destroy are supported in setting
				this attribute"
			::= { wsSwIpEntry 4 }

		
		-- 1.3.6.1.4.1.388.14.2.5.1.2
		wsSwIpRouteEnable OBJECT-TYPE
			SYNTAX TruthValue
			MAX-ACCESS read-write
			STATUS current
			DESCRIPTION
				"Enable/disable Ip Routing"
			::= { wsSwIpModule 2 }

		
		-- 1.3.6.1.4.1.388.14.2.5.1.100
		wsSwIpConformance OBJECT IDENTIFIER ::= { wsSwIpModule 100 }

		
		-- 1.3.6.1.4.1.388.14.2.5.1.100.1
		wsSwIpCompliances OBJECT IDENTIFIER ::= { wsSwIpConformance 1 }

		
		-- 1.3.6.1.4.1.388.14.2.5.1.100.1.1
		wsSwIpCompliance MODULE-COMPLIANCE
			STATUS current
			DESCRIPTION 
				"SW-IP module compliance"
			MODULE -- this module
				MANDATORY-GROUPS { wsSwIpMibGroup }
			::= { wsSwIpCompliances 1 }

		
		-- 1.3.6.1.4.1.388.14.2.5.1.100.2
		wsSwIpGroups OBJECT IDENTIFIER ::= { wsSwIpConformance 2 }

		
		-- 1.3.6.1.4.1.388.14.2.5.1.100.2.1
		wsSwIpMibGroup OBJECT-GROUP
			OBJECTS { wsSwIpRowStatus, wsSwIpRouteEnable }
			STATUS current
			DESCRIPTION 
				"SW-IP mib group"
			::= { wsSwIpGroups 1 }

		
	
	END

--
-- WS-SW-IP-MIB.my
--
