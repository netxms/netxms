DNOS-SFLOW-MIB DEFINITIONS ::= BEGIN

-- Dell Networking OS SFLOW MIB
-- Copyright Dell (2003-2009) All rights reserved.

-- This SNMP Management Information Specification
-- embodies Dell's confidential and proprietary
-- intellectual property. Dell retains all title
-- and ownership in the Specification including any revisions.

-- This Specification is supplied "AS IS", Dell
-- makes no warranty, either expressed or implied,
-- as to the use, operation, condition, or performance of the
-- Specification.

IMPORTS
    MODULE-IDENTITY, OBJECT-TYPE,
    Integer32                           FROM SNMPv2-SMI
    dnOS                            FROM DELL-REF-MIB
    InterfaceIndexOrZero                FROM IF-MIB;

    fastPathSflow                MODULE-IDENTITY
        LAST-UPDATED "201201120000Z" -- 12 Jan 2012 12:00:00 GMT
        ORGANIZATION "Dell, Inc."
        CONTACT-INFO ""
        DESCRIPTION
          "The Dell Networking Private MIB for SFLOW"

    ::= { dnOS 59 }

    --***********************************************************************
    -- MIB Objects
    --***********************************************************************


    agentFastPathSflowObjects  OBJECT IDENTIFIER  ::= { fastPathSflow 1 }

    --**************************************************************************************
    -- agentSflowSourceInterface
    --
    --**************************************************************************************
  agentSflowSourceInterface OBJECT-TYPE
         SYNTAX      InterfaceIndexOrZero
         MAX-ACCESS  read-write
         STATUS      current
         DESCRIPTION
              "A source-interface selection on an Interface Index (like vlan based
              routing interface, port based routing interface, loopback interface,
              tunnel interface). A non-zero value indicates ifIndex for the
              corresponding interface entry in the ifTable is selected.
              A zero value indicates source-interface is un-configured."
         ::= { agentFastPathSflowObjects 1 }

END
