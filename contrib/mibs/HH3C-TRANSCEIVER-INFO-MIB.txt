--===========================================================
-- Copyright (c) 2004-2013 Hangzhou H3C Tech. Co., Ltd.  All rights reserved.
--
-- Description:  Transceiver MIB
-- Reference:  IF-MIB
-- Version:  V1.4
-- History:
-- V1.0 created by liuhongxu and zoudian.
--   Initial version 2006-01-10
-- V1.1 2006-06-08 Updated by chenzhaojie
--   Change description of hh3cTransceiverWaveLength
-- V1.2 2009-12-29 Updated by jinyi
--   Add the objects of hh3cTransceiverDiagnostic, hh3cTransceiverCurTXPower,
--   hh3cTransceiverMaxTXPower, hh3cTransceiverMinTXPower, hh3cTransceiverCurRXPower,
--   hh3cTransceiverMaxRXPower, hh3cTransceiverMinRXPower, hh3cTransceiverTemperature,
--   hh3cTransceiverVoltage, hh3cTransceiverBiasCurrent
-- V1.3 2012-06-06 Updated by jixugang
--   Add the objects of hh3cTransceiverTempHiAlarm, hh3cTransceiverTempLoAlarm,
--   hh3cTransceiverTempHiWarn, hh3cTransceiverTempLoWarn, hh3cTransceiverVccHiAlarm,
--   hh3cTransceiverVccLoAlarm, hh3cTransceiverVccHiWarn, hh3cTransceiverVccLoWarn,
--   hh3cTransceiverBiasHiAlarm, hh3cTransceiverBiasLoAlarm, hh3cTransceiverBiasHiWarn,
--   hh3cTransceiverBiasLoWarn, hh3cTransceiverPwrOutHiAlarm, hh3cTransceiverPwrOutLoAlarm,
--   hh3cTransceiverPwrOutHiWarn, hh3cTransceiverPwrOutLoWarn, hh3cTransceiverRcvPwrHiAlarm,
--   hh3cTransceiverRcvPwrLoAlarm, hh3cTransceiverRcvPwrHiWarn, hh3cTransceiverRcvPwrLoWarn,
--   hh3cTransceiverErrors
-- V1.4 2012-06-06 Updated by chenyixian
--   Add hh3cTransceiverChannelTable to transceiver channel statistics.
--=================================================================
HH3C-TRANSCEIVER-INFO-MIB DEFINITIONS ::= BEGIN
IMPORTS
    MODULE-IDENTITY, OBJECT-TYPE, Integer32
        FROM SNMPv2-SMI
    TruthValue
        FROM SNMPv2-TC
    ifIndex
        FROM IF-MIB
    hh3cCommon
        FROM HH3C-OID-MIB;

    hh3cTransceiver MODULE-IDENTITY
        LAST-UPDATED "201307231650Z"
        ORGANIZATION
            "Hangzhou H3C Technologies Co., Ltd."
        CONTACT-INFO
            "Platform Team Hangzhou H3C Technologies Co., Ltd.
            Hai-Dian District Beijing P.R. China
            http://www.h3c.com
            Zip:100085"
        DESCRIPTION
            "The objects in this MIB module are used to display the
            information of transceiver on interface."
        REVISION "201307231650Z"
        DESCRIPTION
            " Add hh3cTransceiverChannelTable."
        REVISION "200912291650Z"
        DESCRIPTION
            "The initial revision of this MIB module."
            ::= { hh3cCommon 70 }

    hh3cTransceiverInfoAdm OBJECT IDENTIFIER ::= { hh3cTransceiver 1 }

    hh3cTransceiverInfoTable OBJECT-TYPE
        SYNTAX SEQUENCE OF Hh3cTransceiverInfoEntry
        MAX-ACCESS not-accessible
        STATUS current
        DESCRIPTION
            "This table show the information of transceiver on interface."
        ::= { hh3cTransceiverInfoAdm 1 }

    hh3cTransceiverInfoEntry OBJECT-TYPE
        SYNTAX Hh3cTransceiverInfoEntry
        MAX-ACCESS not-accessible
        STATUS current
        DESCRIPTION
            "The entry of the hh3cTransceiverInfoTable."
        INDEX { ifIndex }
        ::= { hh3cTransceiverInfoTable 1 }

    Hh3cTransceiverInfoEntry ::=
        SEQUENCE {
            hh3cTransceiverHardwareType      OCTET STRING,
            hh3cTransceiverType              OCTET STRING,
            hh3cTransceiverWaveLength        Integer32,
            hh3cTransceiverVendorName        OCTET STRING,
            hh3cTransceiverSerialNumber      OCTET STRING,
            hh3cTransceiverFiberDiameterType INTEGER,
            hh3cTransceiverTransferDistance  Integer32,
            hh3cTransceiverDiagnostic        TruthValue,
            hh3cTransceiverCurTXPower        Integer32,
            hh3cTransceiverMaxTXPower        Integer32,
            hh3cTransceiverMinTXPower        Integer32,
            hh3cTransceiverCurRXPower        Integer32,
            hh3cTransceiverMaxRXPower        Integer32,
            hh3cTransceiverMinRXPower        Integer32,
            hh3cTransceiverTemperature       Integer32,
            hh3cTransceiverVoltage           Integer32,
            hh3cTransceiverBiasCurrent       Integer32,
            hh3cTransceiverTempHiAlarm       Integer32,
            hh3cTransceiverTempLoAlarm       Integer32,
            hh3cTransceiverTempHiWarn        Integer32,
            hh3cTransceiverTempLoWarn        Integer32,
            hh3cTransceiverVccHiAlarm        Integer32,
            hh3cTransceiverVccLoAlarm        Integer32,
            hh3cTransceiverVccHiWarn         Integer32,
            hh3cTransceiverVccLoWarn         Integer32,
            hh3cTransceiverBiasHiAlarm       Integer32,
            hh3cTransceiverBiasLoAlarm       Integer32,
            hh3cTransceiverBiasHiWarn        Integer32,
            hh3cTransceiverBiasLoWarn        Integer32,
            hh3cTransceiverPwrOutHiAlarm     Integer32,
            hh3cTransceiverPwrOutLoAlarm     Integer32,
            hh3cTransceiverPwrOutHiWarn      Integer32,
            hh3cTransceiverPwrOutLoWarn      Integer32,
            hh3cTransceiverRcvPwrHiAlarm     Integer32,
            hh3cTransceiverRcvPwrLoAlarm     Integer32,
            hh3cTransceiverRcvPwrHiWarn      Integer32,
            hh3cTransceiverRcvPwrLoWarn      Integer32,
            hh3cTransceiverErrors            BITS
        }

    hh3cTransceiverHardwareType OBJECT-TYPE
        SYNTAX OCTET STRING
        MAX-ACCESS read-only
        STATUS current
        DESCRIPTION
            "Hardware type of the interface, such as SM(single mode)."
        ::= { hh3cTransceiverInfoEntry 1 }

    hh3cTransceiverType OBJECT-TYPE
        SYNTAX OCTET STRING
        MAX-ACCESS read-only
        STATUS current
        DESCRIPTION
            "Type of the interface, such as SFP/XFP/GBIC."
        ::= { hh3cTransceiverInfoEntry 2 }

    hh3cTransceiverWaveLength OBJECT-TYPE
        SYNTAX Integer32
        MAX-ACCESS read-only
        STATUS current
        DESCRIPTION
            "Wave length of the interface, measured in nanometer."
        ::= { hh3cTransceiverInfoEntry 3 }

    hh3cTransceiverVendorName OBJECT-TYPE
        SYNTAX OCTET STRING
        MAX-ACCESS read-only
        STATUS current
        DESCRIPTION
            "Vendor name of the interface."
        ::= { hh3cTransceiverInfoEntry 4 }

    hh3cTransceiverSerialNumber OBJECT-TYPE
        SYNTAX OCTET STRING
        MAX-ACCESS read-only
        STATUS current
        DESCRIPTION
            "Serial number of the interface."
        ::= { hh3cTransceiverInfoEntry 5 }

    hh3cTransceiverFiberDiameterType OBJECT-TYPE
        SYNTAX INTEGER
            {
              fiber9(1),
              fiber50(2),
              fiber625(3),
              copper(4),
              unknown(65535)
            }
        MAX-ACCESS read-only
        STATUS current
        DESCRIPTION
            "The diameter of the fiber, measured in micron.
            fiber9 - 9 micron multi-mode fiber
            fiber50 - 50 micron multi-mode fiber
            fiber625 - 62.5 micron multi-mode fiber
            copper - copper cable."
        ::= { hh3cTransceiverInfoEntry 6 }

    hh3cTransceiverTransferDistance OBJECT-TYPE
        SYNTAX Integer32
        MAX-ACCESS read-only
        STATUS current
        DESCRIPTION
            "The maximal distance which the interface could transmit,
            measured in meter."
        ::= { hh3cTransceiverInfoEntry 7 }

    hh3cTransceiverDiagnostic OBJECT-TYPE
        SYNTAX      TruthValue
        MAX-ACCESS  read-only
        STATUS      current
        DESCRIPTION
            "Indicating the digital diagnostic monitoring function ."
        ::= { hh3cTransceiverInfoEntry 8 }

    hh3cTransceiverCurTXPower OBJECT-TYPE
        SYNTAX      Integer32
        MAX-ACCESS  read-only
        STATUS      current
        DESCRIPTION
            "Indicating the current transmitted power .
            The unit is in hundredths of dBM."
        ::= { hh3cTransceiverInfoEntry 9 }

    hh3cTransceiverMaxTXPower OBJECT-TYPE
        SYNTAX      Integer32
        MAX-ACCESS  read-only
        STATUS      current
        DESCRIPTION
            "Indicating the maximal transmitted power .
            The unit is in hundredths of dBM."
        ::= { hh3cTransceiverInfoEntry 10 }

    hh3cTransceiverMinTXPower OBJECT-TYPE
        SYNTAX      Integer32
        MAX-ACCESS  read-only
        STATUS      current
        DESCRIPTION
            "Indicating the minimal transmitted power .
            The unit is in hundredths of dBM."
        ::= { hh3cTransceiverInfoEntry 11 }

    hh3cTransceiverCurRXPower OBJECT-TYPE
        SYNTAX      Integer32
        MAX-ACCESS  read-only
        STATUS      current
        DESCRIPTION
            "Indicating the current received power .
            The unit is in hundredths of dBM."
        ::= { hh3cTransceiverInfoEntry 12 }

    hh3cTransceiverMaxRXPower OBJECT-TYPE
        SYNTAX      Integer32
        MAX-ACCESS  read-only
        STATUS      current
        DESCRIPTION
            "Indicating the maximal received power .
            The unit is in hundredths of dBM."
        ::= { hh3cTransceiverInfoEntry 13 }

    hh3cTransceiverMinRXPower OBJECT-TYPE
        SYNTAX      Integer32
        MAX-ACCESS  read-only
        STATUS      current
        DESCRIPTION
            "Indicating the minimal received power .
            The unit is in hundredths of dBM."
        ::= { hh3cTransceiverInfoEntry 14 }

    hh3cTransceiverTemperature OBJECT-TYPE
        SYNTAX      Integer32
        MAX-ACCESS  read-only
        STATUS      current
        DESCRIPTION
            "Indicating the current temperature.
             The unit is Celsius centigrade."
        ::= { hh3cTransceiverInfoEntry 15 }

    hh3cTransceiverVoltage OBJECT-TYPE
        SYNTAX      Integer32
        MAX-ACCESS  read-only
        STATUS      current
        DESCRIPTION
            "Indicating the current voltage .
            The unit is in hundredths of V"
        ::= { hh3cTransceiverInfoEntry 16 }

    hh3cTransceiverBiasCurrent OBJECT-TYPE
        SYNTAX      Integer32
        MAX-ACCESS  read-only
        STATUS      current
        DESCRIPTION
            "Indicating the current bias electric current .
            The unit is in hundredths of mA"
        ::= { hh3cTransceiverInfoEntry 17 }

    hh3cTransceiverTempHiAlarm OBJECT-TYPE
        SYNTAX      Integer32
        MAX-ACCESS  read-only
        STATUS      current
        DESCRIPTION
            "Transceiver temperature high alarm threshold
             limit in thousandths of degrees Celsius.
             As an example: 49120 is 49.120 degrees Celsius."
        ::= { hh3cTransceiverInfoEntry 18 }

    hh3cTransceiverTempLoAlarm OBJECT-TYPE
        SYNTAX      Integer32
        MAX-ACCESS  read-only
        STATUS      current
        DESCRIPTION
            "Transceiver temperature low alarm threshold
             limit in thousandths of degrees Celsius.
             As an example: 49120 is 49.120 degrees Celsius."
        ::= { hh3cTransceiverInfoEntry 19 }

    hh3cTransceiverTempHiWarn OBJECT-TYPE
        SYNTAX      Integer32
        MAX-ACCESS  read-only
        STATUS      current
        DESCRIPTION
            "Transceiver temperature high warning threshold
             limit in thousandths of degrees Celsius.
             As an example: 49120 is 49.120 degrees Celsius."
        ::= { hh3cTransceiverInfoEntry 20 }

    hh3cTransceiverTempLoWarn OBJECT-TYPE
        SYNTAX      Integer32
        MAX-ACCESS  read-only
        STATUS      current
        DESCRIPTION
            "Transceiver temperature low warning threshold
             limit in thousandths of degrees Celsius.
             As an example: 49120 is 49.120 degrees Celsius."
        ::= { hh3cTransceiverInfoEntry 21 }

    hh3cTransceiverVccHiAlarm OBJECT-TYPE
        SYNTAX      Integer32
        MAX-ACCESS  read-only
        STATUS      current
        DESCRIPTION
            "Transceiver VCC high alarm threshold
             limit in hundreds of microvolts.
             As an example: 32928 is 3.2928 volts.
             Returns zero if not supported on the transceiver."
        ::= { hh3cTransceiverInfoEntry 22 }

    hh3cTransceiverVccLoAlarm OBJECT-TYPE
        SYNTAX      Integer32
        MAX-ACCESS  read-only
        STATUS      current
        DESCRIPTION
            "Transceiver VCC low alarm threshold
             limit in hundreds of microvolts.
             As an example: 32928 is 3.2928 volts.
             Returns zero if not supported on the transceiver."
        ::= { hh3cTransceiverInfoEntry 23 }

    hh3cTransceiverVccHiWarn OBJECT-TYPE
        SYNTAX      Integer32
        MAX-ACCESS  read-only
        STATUS      current
        DESCRIPTION
            "Transceiver VCC high warning threshold
             limit in hundreds of microvolts.
             As an example: 32928 is 3.2928 volts.
             Returns zero if not supported on the transceiver."
        ::= { hh3cTransceiverInfoEntry 24 }

    hh3cTransceiverVccLoWarn OBJECT-TYPE
        SYNTAX      Integer32
        MAX-ACCESS  read-only
        STATUS      current
        DESCRIPTION
            "Transceiver VCC low warning threshold
             limit in hundreds of microvolts.
             As an example: 32928 is 3.2928 volts.
             Returns zero if not supported on the transceiver."
        ::= { hh3cTransceiverInfoEntry 25 }

    hh3cTransceiverBiasHiAlarm OBJECT-TYPE
        SYNTAX      Integer32
        MAX-ACCESS  read-only
        STATUS      current
        DESCRIPTION
            "Transceiver bias high alarm threshold limit in microamps."
        ::= { hh3cTransceiverInfoEntry 26 }

    hh3cTransceiverBiasLoAlarm OBJECT-TYPE
        SYNTAX      Integer32
        MAX-ACCESS  read-only
        STATUS      current
        DESCRIPTION
            "Transceiver bias low alarm threshold limit in microamps."
        ::= { hh3cTransceiverInfoEntry 27 }

    hh3cTransceiverBiasHiWarn OBJECT-TYPE
        SYNTAX      Integer32
        MAX-ACCESS  read-only
        STATUS      current
        DESCRIPTION
            "Transceiver bias high warning threshold limit in microamps."
        ::= { hh3cTransceiverInfoEntry 28 }

    hh3cTransceiverBiasLoWarn OBJECT-TYPE
        SYNTAX      Integer32
        MAX-ACCESS  read-only
        STATUS      current
        DESCRIPTION
            "Transceiver bias low warning threshold limit in microamps."
        ::= { hh3cTransceiverInfoEntry 29 }

    hh3cTransceiverPwrOutHiAlarm OBJECT-TYPE
        SYNTAX      Integer32
        MAX-ACCESS  read-only
        STATUS      current
        DESCRIPTION
            "Transceiver transmit power high alarm
             threshold limit in tenths of microwatts.
             As an example: 10000 is 1 milliwatt."
        ::= { hh3cTransceiverInfoEntry 30 }

    hh3cTransceiverPwrOutLoAlarm OBJECT-TYPE
        SYNTAX      Integer32
        MAX-ACCESS  read-only
        STATUS      current
        DESCRIPTION
            "Transceiver transmit power low alarm
             threshold limit in tenths of microwatts.
             As an example: 10000 is 1 milliwatt."
        ::= { hh3cTransceiverInfoEntry 31 }

    hh3cTransceiverPwrOutHiWarn OBJECT-TYPE
        SYNTAX      Integer32
        MAX-ACCESS  read-only
        STATUS      current
        DESCRIPTION
            "Transceiver transmit power high warning
             threshold limit in tenths of microwatts
             As an example: 10000 is 1 milliwatt."
        ::= { hh3cTransceiverInfoEntry 32 }

    hh3cTransceiverPwrOutLoWarn OBJECT-TYPE
        SYNTAX      Integer32
        MAX-ACCESS  read-only
        STATUS      current
        DESCRIPTION
            "Transceiver transmit power low warning
             threshold limit in tenths of microwatts.
             As an example: 10000 is 1 milliwatt."
        ::= { hh3cTransceiverInfoEntry 33 }

    hh3cTransceiverRcvPwrHiAlarm OBJECT-TYPE
        SYNTAX      Integer32
        MAX-ACCESS  read-only
        STATUS      current
        DESCRIPTION
            "Transceiver receive power high alarm
             threshold limit in tenths of microwatts.
             As an example: 10000 is 1 milliwatt."
        ::= { hh3cTransceiverInfoEntry 34 }

    hh3cTransceiverRcvPwrLoAlarm OBJECT-TYPE
        SYNTAX      Integer32
        MAX-ACCESS  read-only
        STATUS      current
        DESCRIPTION
            "Transceiver receive power low alarm
             threshold limit in tenths of microwatts.
             As an example: 10000 is 1 milliwatt."
        ::= { hh3cTransceiverInfoEntry 35 }

    hh3cTransceiverRcvPwrHiWarn OBJECT-TYPE
        SYNTAX      Integer32
        MAX-ACCESS  read-only
        STATUS      current
        DESCRIPTION
            "Transceiver receive power high warning
             threshold limit in tenths of microwatts.
             As an example: 10000 is 1 milliwatt."
        ::= { hh3cTransceiverInfoEntry 36 }

    hh3cTransceiverRcvPwrLoWarn OBJECT-TYPE
        SYNTAX      Integer32
        MAX-ACCESS  read-only
        STATUS      current
        DESCRIPTION
            "Transceiver receive power low warning
             threshold limit in tenths of microwatts.
             As an example: 10000 is 1 milliwatt."
        ::= { hh3cTransceiverInfoEntry 37 }

    hh3cTransceiverErrors OBJECT-TYPE
        SYNTAX      BITS
            {
                xcvrIOError(0),
                xcvrChecksum(1),
                xcvrTypeAndPortConfigMismatch(2),
                xcvrTypeNotSupported(3),
                wisLocalFault(4),
                rcvOpticalPowerFault(5),
                pmapmdReceiverLocalFault(6),
                pcsReceiveLocalFault(7),
                phyXSReceiveLocalFault(8),
                laserBiasCurrentFault(9),
                laserTemperatureFault(10),
                laserOutputPowerFault(11),
                txFault(12),
                pmapmdTransmitterLocalFault(13),
                pcsTransmitLocalFault(14),
                phyXSTransmitLocalFault(15),
                rxLossOfSignal(16)
            }
        MAX-ACCESS  read-only
        STATUS      current
        DESCRIPTION
            "Bitmask indicating transceiver errors.
             Transceiver information I/O error(0)
             Transceiver information checksum error(1)
             Transceiver type and port configuration mismatch(2)
             Transceiver type not supported by port hardware(3)
             WIS local fault(4)
             Receive optical power fault(5)
             PMA/PMD receiver local fault(6)
             PCS receive local fault(7)
             PHY XS receive local fault(8)
             Laser bias current fault(9)
             Laser temperature fault(10)
             Laser output power fault(11)
             TX fault(12)
             PMA/PMD transmitter local fault(13)
             PCS transmit local fault(14)
             PHY XS Transmit Local Fault(15)
             RX loss of signal(16)
             Unused(17-31)"
        ::= { hh3cTransceiverInfoEntry 38 }

-- Transceiver Channel Table

    hh3cTransceiverChannelTable OBJECT-TYPE
        SYNTAX SEQUENCE OF Hh3cTransceiverChannelEntry
        MAX-ACCESS not-accessible
        STATUS current
        DESCRIPTION
            "This table provides statistics about transceiver with multi-channel."
        ::= { hh3cTransceiverInfoAdm 2 }

    hh3cTransceiverChannelEntry OBJECT-TYPE
        SYNTAX Hh3cTransceiverChannelEntry
        MAX-ACCESS not-accessible
        STATUS current
        DESCRIPTION
            "The entry of the hh3cTransceiverChannelTable."
        INDEX { ifIndex, hh3cTransceiverChannelIndex }
        ::= { hh3cTransceiverChannelTable 1 }

    Hh3cTransceiverChannelEntry ::=
        SEQUENCE {
            hh3cTransceiverChannelIndex             Integer32,
            hh3cTransceiverChannelCurTXPower        Integer32,
            hh3cTransceiverChannelCurRXPower        Integer32,
            hh3cTransceiverChannelTemperature       Integer32,
            hh3cTransceiverChannelBiasCurrent       Integer32
        }

    hh3cTransceiverChannelIndex OBJECT-TYPE
        SYNTAX      Integer32(1..2147483647)
        MAX-ACCESS  not-accessible
        STATUS      current
        DESCRIPTION
            "The channel index of transceiver.
            Indicating one channel of the interface."
        ::= { hh3cTransceiverChannelEntry 1 }

    hh3cTransceiverChannelCurTXPower OBJECT-TYPE
        SYNTAX      Integer32
        MAX-ACCESS  read-only
        STATUS      current
        DESCRIPTION
            "Indicating the current transmission power.
            The unit is in hundredths of dBM."
        ::= { hh3cTransceiverChannelEntry 2 }

    hh3cTransceiverChannelCurRXPower OBJECT-TYPE
        SYNTAX      Integer32
        MAX-ACCESS  read-only
        STATUS      current
        DESCRIPTION
            "Indicating the current received power.
            The unit is in hundredths of dBM."
        ::= { hh3cTransceiverChannelEntry 3 }

    hh3cTransceiverChannelTemperature OBJECT-TYPE
        SYNTAX      Integer32
        MAX-ACCESS  read-only
        STATUS      current
        DESCRIPTION
            "Indicating the current temperature.
            The unit is Celsius centigrade."
        ::= { hh3cTransceiverChannelEntry 4 }

    hh3cTransceiverChannelBiasCurrent OBJECT-TYPE
        SYNTAX      Integer32
        MAX-ACCESS  read-only
        STATUS      current
        DESCRIPTION
            "Indicating the current bias electric current.
            The unit is in hundredths of mA."
        ::= { hh3cTransceiverChannelEntry 5 }

END
