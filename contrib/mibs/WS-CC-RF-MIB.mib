-- vim: syntax=mib
--
-- WS-CC-RF-MIB.my
-- MIB generated by MG-SOFT Visual MIB Builder Version 6.0  Build 88
-- Wednesday, January 17, 2007 at 17:52:19
--

WS-CC-RF-MIB DEFINITIONS ::= BEGIN

		IMPORTS
			OBJECT-GROUP, MODULE-COMPLIANCE
				FROM SNMPv2-CONF
			TimeTicks, IpAddress, Integer32, Unsigned32, Counter32,
			OBJECT-TYPE, MODULE-IDENTITY
				FROM SNMPv2-SMI
			TEXTUAL-CONVENTION, PhysAddress, DisplayString, TruthValue, RowStatus
				FROM SNMPv2-TC
			wsCcRf
				FROM WS-CC-SMI
			DoActionNow, MultiPointer64
				FROM WS-TYPE-MIB;


		-- 1.3.6.1.4.1.388.14.3.2.1
		wsCcRfMIB MODULE-IDENTITY
			LAST-UPDATED "200610231605Z"		-- October 23, 2006 at 16:05 GMT
			ORGANIZATION
				"Symbol Technologies, Inc"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"Mib for wireless features"
			REVISION "200701171750Z"		-- January 17, 2007 at 17:50 GMT
			DESCRIPTION
				"02a22"
			REVISION "200701041207Z"		-- January 04, 2007 at 12:07 GMT
			DESCRIPTION
				"02a21"
			REVISION "200610231605Z"		-- October 23, 2006 at 16:05 GMT
			DESCRIPTION
				"02a20"
			REVISION "200610041540Z"		-- October 04, 2006 at 15:40 GMT
			DESCRIPTION
				"02a19"
			REVISION "200609272348Z"		-- September 27, 2006 at 23:48 GMT
			DESCRIPTION
				"02a18"
			REVISION "200609261100Z"		-- September 26, 2006 at 11:00 GMT
			DESCRIPTION
				"02a17"
			REVISION "200609091137Z"		-- September 09, 2006 at 11:37 GMT
			DESCRIPTION
				"02a16"
			REVISION "200609081710Z"		-- September 08, 2006 at 17:10 GMT
			DESCRIPTION
				"02a15"
			REVISION "200609061104Z"		-- September 06, 2006 at 11:04 GMT
			DESCRIPTION
				"02a14"
			REVISION "200609051650Z"		-- September 05, 2006 at 16:50 GMT
			DESCRIPTION
				"02a13"
			REVISION "200607211004Z"		-- July 21, 2006 at 10:04 GMT
			DESCRIPTION
				"02a12"
			REVISION "200607171856Z"		-- July 17, 2006 at 18:56 GMT
			DESCRIPTION
				"02a11"
			REVISION "200607141646Z"		-- July 14, 2006 at 16:46 GMT
			DESCRIPTION
				"02a10"
			REVISION "200607121602Z"		-- July 12, 2006 at 16:02 GMT
			DESCRIPTION
				"02a09"
			REVISION "200606161144Z"		-- June 16, 2006 at 11:44 GMT
			DESCRIPTION
				"02a08"
			REVISION "200606151520Z"		-- June 15, 2006 at 15:20 GMT
			DESCRIPTION
				"02a07"
			REVISION "200606131309Z"		-- June 13, 2006 at 13:09 GMT
			DESCRIPTION
				"02a06"
			REVISION "200606100850Z"		-- June 10, 2006 at 08:50 GMT
			DESCRIPTION
				"02a05"
			REVISION "200606061431Z"		-- June 06, 2006 at 14:31 GMT
			DESCRIPTION
				"02a04"
			REVISION "200605161226Z"		-- May 16, 2006 at 12:26 GMT
			DESCRIPTION
				"02a03"
			REVISION "200605151137Z"		-- May 15, 2006 at 11:37 GMT
			DESCRIPTION
				"02a02"
			REVISION "200604061244Z"		-- April 06, 2006 at 12:44 GMT
			DESCRIPTION
				"02a01"
			REVISION "200601121604Z"		-- January 12, 2006 at 16:04 GMT
			DESCRIPTION
				"01a51"
			::= { wsCcRf 1 }



--
-- Type definitions
--

		SinglePointer ::= INTEGER (0..255)

		AbbrevRowStatus ::= INTEGER
			{
			createAndGo(4),
			destroy(6)
			}

		DoActionShowProgress ::= INTEGER
			{
			doActionRightNow(1),
			idleState(2)
			}

		Password ::= OCTET STRING (SIZE (0..255))

		StaticRowEnable ::= INTEGER
			{
			enable(1),
			disable(2)
			}

		ApType ::= INTEGER
			{
			ap100(1),
			ap200(2),
			ap300(3),
			ap4131(4)
			}

		RadioModel ::= INTEGER
			{
			ap100dot11B(1),
			ap200dot11A(2),
			ap200dot11B(3),
			ap300dot11A(4),
			ap300dot11BG(5)
			}

		RadioType ::= INTEGER
			{
			radio802dot11A(1),
			radio802dot11B(2),
			radio802dot11BG(3),
			radio802dot11FH(4)
			}

		AuthType ::= INTEGER
			{
			authNone(1),
			auth802dot1xEap(2),
			authKerberos(3),
			authHotspot(4),
			authMac(5)
			}

		EncType ::= INTEGER
			{
			cryptoNone(1),
			cryptoWep64(2),
			cryptoWep128(3),
			cryptoKeyguardMcm(4),
			cryptoWpaWpa2Tkip(5),
			cryptoWpa2Ccmp(6)
			}

		EncMap ::= BITS
			{
			cryptoNone(0),
			cryptoWep64(1),
			cryptoWep128(2),
			cryptoKeyguardMcm(3),
			cryptoWpaTkip(4),
			cryptoWpa2Ccmp(5)
			}

		AccCatType ::= INTEGER
			{
			acBestEffort(1),
			acBackground(2),
			acVideo(3),
			acVoice(4)
			}

		PassphraseType ::= INTEGER
			{
			ascii(1),
			hash(2)
			}

		RadioChannel ::= BITS
			{
			null(0),
			bchannel01(1),
			bchannel02(2),
			bchannel03(3),
			bchannel04(4),
			bchannel05(5),
			bchannel06(6),
			bchannel07(7),
			bchannel08(8),
			bchannel09(9),
			bchannel10(10),
			bchannel11(11),
			bchannel12(12),
			bchannel13(13),
			bchannel14(14),
			achannel34(15),
			achannel36(16),
			achannel38(17),
			achannel40(18),
			achannel42(19),
			achannel44(20),
			achannel46(21),
			achannel48(22),
			achannel52(23),
			achannel56(24),
			achannel60(25),
			achannel64(26),
			achannel149(27),
			achannel153(28),
			achannel157(29),
			achannel161(30),
			achannel165(31),
			achannel169(32)
			}

		TransmitRate ::= BITS
			{
			rate1Mb(0),
			rate2Mb(1),
			rate5pt5Mb(2),
			rate6Mb(3),
			rate9Mb(4),
			rate11Mb(5),
			rate12Mb(6),
			rate18Mb(7),
			rate22Mb(8),
			rate24Mb(9),
			rate36Mb(10),
			rate48Mb(11),
			rate54Mb(12)
			}

		IdsViolationType ::= INTEGER
			{
			violExcessProbe(1),
			violExcessAuthAssoc(2),
			violExcessDisassoc(3),
			violExcessAuthFail(4),
			violExcessCryptoReplay(5),
			violExcess80211Replay(6),
			violExcessDecryptFail(7),
			violExcessUnassocTraf(8),
			violExcessEapStart(9),
			violFilterNullDst(10),
			violFilterSameSrcDst(11),
			violFilterMcastSrc(12),
			violFilterWeakWebIv(13),
			violFilterCntrMeas(14),
			violFilterInvalidLen(15)
			}



--
-- Node definitions
--

		-- 1.3.6.1.4.1.388.14.3.2.1.1
		wsCcRfCountryCode OBJECT-TYPE
			SYNTAX DisplayString (SIZE (0 | 2))
			MAX-ACCESS read-write
			STATUS current
			DESCRIPTION
				"This value is a two-character representation of the country
				code.

				Note: when changing this _CountrySelection, the current
				channel and power levels are NOT changed.  The prior
				settings for these values may or may not be valid/legal
				for the new country selected.  It is up to the network
				management software to ensure that channel and/or power
				settings are changed BEFORE changing the country selection
				so that no such invalid/illegal state is reached, even for
				a short interim.

				country code:

					Argentina:            ar
					Australia:            au
					Austria:              at
					Bahrain:              bh
					Belarus:              by
					Belgium:              be
					Brazil:               br
					Bulgaria:             bg
					Canada:               ca
					Chile:                cl
					China:                cn
					Colombia:             co
					Costa Rica:           cr
					Croatia:              hr
					Czech Republic:       cz
					Denmark:              dk
					Ecuador:              ec
					Egypt:                eg
					Estonia:              ee
					Finland:              fi
					France:               fr
					Germany:              de
					Greece:               gr
					Hong Kong:            hk
					Hungary:              hu
					Iceland:              is
					India:                in
					Indonesia:            id
					Ireland:              ie
					Israel:               il
					Italy:                it
					Japan:                jp
					Jordan:               jo
					Kazakhstan:           kz
					Kuwait:               kw
					Latvia:               lv
					Liechtenstein:        li
					Lithuania:            lt
					Luxembourg:           lu
					Malaysia:             my
					Mexico:               mx
					Morocco:              ma
					Netherlands:          nl
					New Zealand:          nz
					Norway:               no
					Oman:                 om
					Peru:                 pe
					Philippines:          ph
					Poland:               pl
					Portugal:             pt
					Qatar:                qa
					Romania:              ro
					Russia:               ru
					Saudi Arabia:         sa
					Singapore:            sg
					Slovak Republic:      sk
					Slovenia:             si
					South Africa:         za
					South Korea:          kr
					Spain:                es
					Sri Lanka:            lk
					Sweden:               se
					Switzerland:          ch
					Taiwan:               tw
					Thailand:             th
					Turkey:               tr
					Ukraine:              ua
					United Arab Emirates: ae
					United Kingdom:       uk
					United States:        us
					Uruguay:              uy
					Venezuela:            ve
					Vietnam:              vn"
			::= { wsCcRfMIB 1 }


		-- 1.3.6.1.4.1.388.14.3.2.1.2
		wsCcRfSnmpSetDelay OBJECT-TYPE
			SYNTAX INTEGER
				{
				immediate(1),
				hold(2)
				}
			MAX-ACCESS read-write
			STATUS current
			DESCRIPTION
				"NOT Implemented in this release: this would cause
				any configuration change to be held in a cache
				until this variable is toggled again. It will be
				useful if we need to apply some changes in a
				batch-mode."
			::= { wsCcRfMIB 2 }


		-- 1.3.6.1.4.1.388.14.3.2.1.3
		wsCcRfClusterIndex OBJECT-TYPE
			SYNTAX Unsigned32
			MAX-ACCESS read-write
			STATUS current
			DESCRIPTION
				"The cluster index of the switch."
			::= { wsCcRfMIB 3 }


		-- 1.3.6.1.4.1.388.14.3.2.1.4
		wsCcRfProxyRespMuArpReq OBJECT-TYPE
			SYNTAX TruthValue
			MAX-ACCESS read-write
			STATUS current
			DESCRIPTION
				"Causes the switch to respond to an ARP Request
				on behalf of an MU. Since a lot of traffic is ARP,
				 this helps to save battery life on the MUs."
			::= { wsCcRfMIB 4 }


		-- 1.3.6.1.4.1.388.14.3.2.1.5
		wsCcRfOversizedFrameEnable OBJECT-TYPE
			SYNTAX TruthValue
			MAX-ACCESS read-write
			STATUS current
			DESCRIPTION
				"Enable over-sized frame."
			::= { wsCcRfMIB 5 }


		-- 1.3.6.1.4.1.388.14.3.2.1.6
		wsCcRfWlanPriorityEnable OBJECT-TYPE
			SYNTAX TruthValue
			MAX-ACCESS read-write
			STATUS current
			DESCRIPTION
				"Use wlan priority weights to determine packet queueing
				order."
			::= { wsCcRfMIB 6 }


		-- 1.3.6.1.4.1.388.14.3.2.1.7
		wsCcRfAdvancedConfigEnable OBJECT-TYPE
			SYNTAX INTEGER
				{
				true(1),
				false(2),
				forcedFalse(3)
				}
			MAX-ACCESS read-write
			STATUS current
			DESCRIPTION
				"Enable or disable Advanced-Config functionality
				on the switch.

				Disabling of Advanced-Config will fail when the current
				setting is not compatible with Auto-Config rules.  If user
				wishes to force the disable action, he/she should use the
				forcedFalse option instead.

				Note: After setting with forcedFalse, the object will
				return false(2) on a snmp-get.  "
			::= { wsCcRfMIB 7 }


		-- 1.3.6.1.4.1.388.14.3.2.1.8
		wsCcRfLastError OBJECT-TYPE
			SYNTAX DisplayString
			MAX-ACCESS read-only
			STATUS current
			DESCRIPTION
				"Error string of the last failed attempt snmp set"
			::= { wsCcRfMIB 8 }


		-- 1.3.6.1.4.1.388.14.3.2.1.9
		wsCcRfAp OBJECT IDENTIFIER ::= { wsCcRfMIB 9 }


		-- 1.3.6.1.4.1.388.14.3.2.1.9.1
		wsCcRfApCount OBJECT-TYPE
			SYNTAX Integer32
			MAX-ACCESS read-only
			STATUS current
			DESCRIPTION
				"Number of Acess Ports adopted"
			::= { wsCcRfAp 1 }


		-- 1.3.6.1.4.1.388.14.3.2.1.9.2
		wsCcRfApTable OBJECT-TYPE
			SYNTAX SEQUENCE OF WsCcRfApEntry
			MAX-ACCESS not-accessible
			STATUS current
			DESCRIPTION
				"This table lists all Access Ports that contain
				at least one radio that has been adopted by this
				wireless switch"
			::= { wsCcRfAp 2 }


		-- 1.3.6.1.4.1.388.14.3.2.1.9.2.1
		wsCcRfApEntry OBJECT-TYPE
			SYNTAX WsCcRfApEntry
			MAX-ACCESS not-accessible
			STATUS current
			DESCRIPTION
				" "
			INDEX { wsCcRfApIndex }
			::= { wsCcRfApTable 1 }


		WsCcRfApEntry ::=
			SEQUENCE {
				wsCcRfApIndex
					INTEGER,
				wsCcRfApNicMac
					PhysAddress,
				wsCcRfApModelNumber
					DisplayString,
				wsCcRfApSerialNumber
					DisplayString,
				wsCcRfApPcbRevision
					DisplayString,
				wsCcRfApBootLoaderRev
					DisplayString,
				wsCcRfApWispVersion
					DisplayString,
				wsCcRfApRuntimeFwVersion
					DisplayString,
				wsCcRfApNumRadios
					Unsigned32,
				wsCcRfApRadio1
					Integer32,
				wsCcRfApRadio2
					Integer32,
				wsCcRfApAddress
					IpAddress
			 }

		-- 1.3.6.1.4.1.388.14.3.2.1.9.2.1.1
		wsCcRfApIndex OBJECT-TYPE
			SYNTAX INTEGER (1..500)
			MAX-ACCESS accessible-for-notify
			STATUS current
			DESCRIPTION
				"Small, arbitrary integer index."
			::= { wsCcRfApEntry 1 }


		-- 1.3.6.1.4.1.388.14.3.2.1.9.2.1.2
		wsCcRfApNicMac OBJECT-TYPE
			SYNTAX PhysAddress
			MAX-ACCESS read-only
			STATUS current
			DESCRIPTION
				"MAC address of this Access Port."
			::= { wsCcRfApEntry 2 }


		-- 1.3.6.1.4.1.388.14.3.2.1.9.2.1.3
		wsCcRfApModelNumber OBJECT-TYPE
			SYNTAX DisplayString
			MAX-ACCESS read-only
			STATUS current
			DESCRIPTION
				"Model number of the Access Port."
			::= { wsCcRfApEntry 3 }


		-- 1.3.6.1.4.1.388.14.3.2.1.9.2.1.4
		wsCcRfApSerialNumber OBJECT-TYPE
			SYNTAX DisplayString
			MAX-ACCESS read-only
			STATUS current
			DESCRIPTION
				"Serial Number of this Access Port."
			::= { wsCcRfApEntry 4 }


		-- 1.3.6.1.4.1.388.14.3.2.1.9.2.1.5
		wsCcRfApPcbRevision OBJECT-TYPE
			SYNTAX DisplayString
			MAX-ACCESS read-only
			STATUS current
			DESCRIPTION
				"Revision of the printed circuit board for this
				Access Port."
			::= { wsCcRfApEntry 5 }


		-- 1.3.6.1.4.1.388.14.3.2.1.9.2.1.6
		wsCcRfApBootLoaderRev OBJECT-TYPE
			SYNTAX DisplayString
			MAX-ACCESS read-only
			STATUS current
			DESCRIPTION
				"Revision of the boot loader code in this Access
				Port."
			::= { wsCcRfApEntry 6 }


		-- 1.3.6.1.4.1.388.14.3.2.1.9.2.1.7
		wsCcRfApWispVersion OBJECT-TYPE
			SYNTAX DisplayString
			MAX-ACCESS read-only
			STATUS current
			DESCRIPTION
				"Version of the WISP (AP-switch) protocol
				implemented by this Access Port."
			::= { wsCcRfApEntry 7 }


		-- 1.3.6.1.4.1.388.14.3.2.1.9.2.1.8
		wsCcRfApRuntimeFwVersion OBJECT-TYPE
			SYNTAX DisplayString
			MAX-ACCESS read-only
			STATUS current
			DESCRIPTION
				"Version of run-time code on this Access Port."
			::= { wsCcRfApEntry 8 }


		-- 1.3.6.1.4.1.388.14.3.2.1.9.2.1.9
		wsCcRfApNumRadios OBJECT-TYPE
			SYNTAX Unsigned32
			MAX-ACCESS read-only
			STATUS current
			DESCRIPTION
				"The number of radios implemented on this
				Access Port."
			::= { wsCcRfApEntry 9 }


		-- 1.3.6.1.4.1.388.14.3.2.1.9.2.1.10
		wsCcRfApRadio1 OBJECT-TYPE
			SYNTAX Integer32
			MAX-ACCESS read-only
			STATUS current
			DESCRIPTION
				"Index of the first radio.  0 will be returned if the radio
				is not adopted."
			::= { wsCcRfApEntry 10 }


		-- 1.3.6.1.4.1.388.14.3.2.1.9.2.1.11
		wsCcRfApRadio2 OBJECT-TYPE
			SYNTAX Integer32
			MAX-ACCESS read-only
			STATUS current
			DESCRIPTION
				"Index of the second radio. 0 will be returned if the radio
				is not adopted."
			::= { wsCcRfApEntry 11 }


		-- 1.3.6.1.4.1.388.14.3.2.1.9.2.1.12
		wsCcRfApAddress OBJECT-TYPE
			SYNTAX IpAddress
			MAX-ACCESS read-only
			STATUS current
			DESCRIPTION
				"The IP address of the L3 AP. This field is empty for L2 AP."
			::= { wsCcRfApEntry 12 }


		-- 1.3.6.1.4.1.388.14.3.2.1.9.3
		wsCcRfApImageVersionTable OBJECT-TYPE
			SYNTAX SEQUENCE OF WsCcRfApImageVersionEntry
			MAX-ACCESS not-accessible
			STATUS current
			DESCRIPTION
				"Table displaying Access Ports image version info."
			::= { wsCcRfAp 3 }


		-- 1.3.6.1.4.1.388.14.3.2.1.9.3.1
		wsCcRfApImageVersionEntry OBJECT-TYPE
			SYNTAX WsCcRfApImageVersionEntry
			MAX-ACCESS not-accessible
			STATUS current
			DESCRIPTION
				" "
			INDEX { wsCcRfApImageVersionIndex }
			::= { wsCcRfApImageVersionTable 1 }


		WsCcRfApImageVersionEntry ::=
			SEQUENCE {
				wsCcRfApImageVersionIndex
					Integer32,
				wsCcRfApImageVersionApType
					ApType,
				wsCcRfApImageVersionModel
					DisplayString,
				wsCcRfApImageVersionName
					DisplayString,
				wsCcRfApImageVersionReleaseDate
					DisplayString,
				wsCcRfApImageVersionImageSize
					Integer32
			 }

		-- 1.3.6.1.4.1.388.14.3.2.1.9.3.1.1
		wsCcRfApImageVersionIndex OBJECT-TYPE
			SYNTAX Integer32 (1..20)
			MAX-ACCESS accessible-for-notify
			STATUS current
			DESCRIPTION
				"Simple index."
			::= { wsCcRfApImageVersionEntry 1 }


		-- 1.3.6.1.4.1.388.14.3.2.1.9.3.1.2
		wsCcRfApImageVersionApType OBJECT-TYPE
			SYNTAX ApType
			MAX-ACCESS read-only
			STATUS current
			DESCRIPTION
				"Ap type that the image applies to."
			::= { wsCcRfApImageVersionEntry 2 }


		-- 1.3.6.1.4.1.388.14.3.2.1.9.3.1.3
		wsCcRfApImageVersionModel OBJECT-TYPE
			SYNTAX DisplayString
			MAX-ACCESS read-only
			STATUS current
			DESCRIPTION
				"Model string of the Access Port image."
			::= { wsCcRfApImageVersionEntry 3 }


		-- 1.3.6.1.4.1.388.14.3.2.1.9.3.1.4
		wsCcRfApImageVersionName OBJECT-TYPE
			SYNTAX DisplayString
			MAX-ACCESS read-only
			STATUS current
			DESCRIPTION
				"Version name of the Access Port image."
			::= { wsCcRfApImageVersionEntry 4 }


		-- 1.3.6.1.4.1.388.14.3.2.1.9.3.1.5
		wsCcRfApImageVersionReleaseDate OBJECT-TYPE
			SYNTAX DisplayString
			MAX-ACCESS read-only
			STATUS current
			DESCRIPTION
				"Release date of the Access Port image."
			::= { wsCcRfApImageVersionEntry 5 }


		-- 1.3.6.1.4.1.388.14.3.2.1.9.3.1.6
		wsCcRfApImageVersionImageSize OBJECT-TYPE
			SYNTAX Integer32
			UNITS "byte"
			MAX-ACCESS read-only
			STATUS current
			DESCRIPTION
				"Size in bytes of the Access Port image."
			::= { wsCcRfApImageVersionEntry 6 }


		-- 1.3.6.1.4.1.388.14.3.2.1.9.4
		wsCcRfApUnadoptedTable OBJECT-TYPE
			SYNTAX SEQUENCE OF WsCcRfApUnadoptedEntry
			MAX-ACCESS not-accessible
			STATUS current
			DESCRIPTION
				"Table of detected but unadopted access ports.  "
			::= { wsCcRfAp 4 }


		-- 1.3.6.1.4.1.388.14.3.2.1.9.4.1
		wsCcRfApUnadoptedEntry OBJECT-TYPE
			SYNTAX WsCcRfApUnadoptedEntry
			MAX-ACCESS not-accessible
			STATUS current
			DESCRIPTION
				" "
			INDEX { wsCcRfApUnadoptedIndex }
			::= { wsCcRfApUnadoptedTable 1 }


		WsCcRfApUnadoptedEntry ::=
			SEQUENCE {
				wsCcRfApUnadoptedIndex
					Integer32,
				wsCcRfApUnadoptedMac
					PhysAddress,
				wsCcRfApUnadoptedApType
					ApType,
				wsCcRfApUnadoptedLastSeen
					Unsigned32
			 }

		-- 1.3.6.1.4.1.388.14.3.2.1.9.4.1.1
		wsCcRfApUnadoptedIndex OBJECT-TYPE
			SYNTAX Integer32 (1..1000)
			MAX-ACCESS accessible-for-notify
			STATUS current
			DESCRIPTION
				"Simple index."
			::= { wsCcRfApUnadoptedEntry 1 }


		-- 1.3.6.1.4.1.388.14.3.2.1.9.4.1.2
		wsCcRfApUnadoptedMac OBJECT-TYPE
			SYNTAX PhysAddress
			MAX-ACCESS read-only
			STATUS current
			DESCRIPTION
				"Mac address of detected but unadopted AP."
			::= { wsCcRfApUnadoptedEntry 2 }


		-- 1.3.6.1.4.1.388.14.3.2.1.9.4.1.3
		wsCcRfApUnadoptedApType OBJECT-TYPE
			SYNTAX ApType
			MAX-ACCESS read-only
			STATUS current
			DESCRIPTION
				"Ap type of detected but unadopted access port."
			::= { wsCcRfApUnadoptedEntry 3 }


		-- 1.3.6.1.4.1.388.14.3.2.1.9.4.1.4
		wsCcRfApUnadoptedLastSeen OBJECT-TYPE
			SYNTAX Unsigned32
			MAX-ACCESS read-only
			STATUS current
			DESCRIPTION
				"The unadopted-ap was last seen
				wsCcRfApUnadoptedLastSeen seconds ago."
			::= { wsCcRfApUnadoptedEntry 4 }


		-- 1.3.6.1.4.1.388.14.3.2.1.9.5
		wsCcRfApHistoryTable OBJECT-TYPE
			SYNTAX SEQUENCE OF WsCcRfApHistoryEntry
			MAX-ACCESS not-accessible
			STATUS current
			DESCRIPTION
				"Description."
			::= { wsCcRfAp 5 }


		-- 1.3.6.1.4.1.388.14.3.2.1.9.5.1
		wsCcRfApHistoryEntry OBJECT-TYPE
			SYNTAX WsCcRfApHistoryEntry
			MAX-ACCESS not-accessible
			STATUS current
			DESCRIPTION
				"Description."
			INDEX { wsCcRfApHistoryIndex, wsCcRfApHistoryMac }
			::= { wsCcRfApHistoryTable 1 }


		WsCcRfApHistoryEntry ::=
			SEQUENCE {
				wsCcRfApHistoryIndex
					INTEGER,
				wsCcRfApHistoryMac
					PhysAddress,
				wsCcRfApHistoryRadioType
					INTEGER,
				wsCcRfApHistoryTimestamp
					DisplayString,
				wsCcRfApHistoryEvent
					INTEGER,
				wsCcRfApHistoryReason
					DisplayString
			 }

		-- 1.3.6.1.4.1.388.14.3.2.1.9.5.1.1
		wsCcRfApHistoryIndex OBJECT-TYPE
			SYNTAX INTEGER (1..255)
			MAX-ACCESS read-only
			STATUS current
			DESCRIPTION
				"Simple Index"
			::= { wsCcRfApHistoryEntry 1 }


		-- 1.3.6.1.4.1.388.14.3.2.1.9.5.1.2
		wsCcRfApHistoryMac OBJECT-TYPE
			SYNTAX PhysAddress
			MAX-ACCESS read-only
			STATUS current
			DESCRIPTION
				"MAC Address of the AP"
			::= { wsCcRfApHistoryEntry 2 }


		-- 1.3.6.1.4.1.388.14.3.2.1.9.5.1.3
		wsCcRfApHistoryRadioType OBJECT-TYPE
			SYNTAX INTEGER
				{
				elevenA(1),
				elevenB(2),
				elevenG(3),
				na(4)
				}
			MAX-ACCESS read-only
			STATUS current
			DESCRIPTION
				"Radio Type: 11a, 11b, 11g or N/A"
			::= { wsCcRfApHistoryEntry 3 }


		-- 1.3.6.1.4.1.388.14.3.2.1.9.5.1.4
		wsCcRfApHistoryTimestamp OBJECT-TYPE
			SYNTAX DisplayString (SIZE (18..32))
			MAX-ACCESS read-only
			STATUS current
			DESCRIPTION
				"Date and Time"
			::= { wsCcRfApHistoryEntry 4 }


		-- 1.3.6.1.4.1.388.14.3.2.1.9.5.1.5
		wsCcRfApHistoryEvent OBJECT-TYPE
			SYNTAX INTEGER
				{
				adoption(1),
				unadoption(2),
				selfHealing(3)
				}
			MAX-ACCESS read-only
			STATUS current
			DESCRIPTION
				"Adoption/unadoption/self-healing event"
			::= { wsCcRfApHistoryEntry 5 }


		-- 1.3.6.1.4.1.388.14.3.2.1.9.5.1.6
		wsCcRfApHistoryReason OBJECT-TYPE
			SYNTAX DisplayString (SIZE (1..128))
			MAX-ACCESS read-only
			STATUS current
			DESCRIPTION
				"AP History reason for occurence of event"
			::= { wsCcRfApHistoryEntry 6 }


		-- 1.3.6.1.4.1.388.14.3.2.1.9.6
		wsCcRfApHistoryEnable OBJECT-TYPE
			SYNTAX INTEGER
				{
				disable(1),
				enable(2)
				}
			MAX-ACCESS read-write
			STATUS current
			DESCRIPTION
				"Enable / disable AP history data collection"
			::= { wsCcRfAp 6 }


		-- 1.3.6.1.4.1.388.14.3.2.1.9.7
		wsCcRfApHistoryClear OBJECT-TYPE
			SYNTAX TruthValue
			MAX-ACCESS read-write
			STATUS current
			DESCRIPTION
				"Clears the entries in the AP History table."
			::= { wsCcRfAp 7 }


		-- 1.3.6.1.4.1.388.14.3.2.1.11
		wsCcRfRadio OBJECT IDENTIFIER ::= { wsCcRfMIB 11 }


		-- 1.3.6.1.4.1.388.14.3.2.1.11.1
		wsCcRfRadioAutoAdopt OBJECT-TYPE
			SYNTAX TruthValue
			MAX-ACCESS read-write
			STATUS current
			DESCRIPTION
				"Enable or disable the switch to auto-adopt radios.  "
			::= { wsCcRfRadio 1 }


		-- 1.3.6.1.4.1.388.14.3.2.1.11.2
		wsCcRfRadioCnt OBJECT-TYPE
			SYNTAX Unsigned32
			MAX-ACCESS read-only
			STATUS current
			DESCRIPTION
				"Number of radios adopted by the switch. This is a count of the number of rows in wsCcRfRadioStatusTable"
			::= { wsCcRfRadio 2 }


		-- 1.3.6.1.4.1.388.14.3.2.1.11.3
		wsCcRfRadioLastMac OBJECT-TYPE
			SYNTAX PhysAddress
			MAX-ACCESS read-only
			STATUS current
			DESCRIPTION
				"This scalar records the MAC address of the most
				recent radio to be Adopted, UnAdopted, or Denied."
			::= { wsCcRfRadio 3 }


		-- 1.3.6.1.4.1.388.14.3.2.1.11.4
		wsCcRfRadioLastReason OBJECT-TYPE
			SYNTAX DisplayString
			MAX-ACCESS read-only
			STATUS current
			DESCRIPTION
				"This value notes the reason for the most-recent
				radio UnAdoption or Denial."
			::= { wsCcRfRadio 4 }


		-- 1.3.6.1.4.1.388.14.3.2.1.11.5
		wsCcRfRadioTable OBJECT-TYPE
			SYNTAX SEQUENCE OF WsCcRfRadioEntry
			MAX-ACCESS not-accessible
			STATUS current
			DESCRIPTION
				"This table lists all radios adopted by this wireless
				switch.  "
			::= { wsCcRfRadio 5 }


		-- 1.3.6.1.4.1.388.14.3.2.1.11.5.1
		wsCcRfRadioEntry OBJECT-TYPE
			SYNTAX WsCcRfRadioEntry
			MAX-ACCESS not-accessible
			STATUS current
			DESCRIPTION
				" "
			INDEX { wsCcRfRadioIndex }
			::= { wsCcRfRadioTable 1 }


		WsCcRfRadioEntry ::=
			SEQUENCE {
				wsCcRfRadioIndex
					Integer32,
				wsCcRfRadioApMac
					PhysAddress,
				wsCcRfRadioDescr
					DisplayString,
				wsCcRfRadioType
					RadioType,
				wsCcRfRadioApType
					ApType,
				wsCcRfRadioBssWlanMap
					OCTET STRING,
				wsCcRfRadioAntDiversity
					INTEGER,
				wsCcRfRadioShortPreamble
					TruthValue,
				wsCcRfRadioRtsThresh
					Integer32,
				wsCcRfRadioBeaconInt
					Integer32,
				wsCcRfRadioDtimPrd
					Integer32,
				wsCcRfRadioBasicRates
					TransmitRate,
				wsCcRfRadioSupportedRates
					TransmitRate,
				wsCcRfRadioRapDetector
					TruthValue,
				wsCcRfRadioClusterIndex
					Unsigned32,
				wsCcRfRadioMaxMu
					Unsigned32,
				wsCcRfRadioSelfHealingAction
					INTEGER,
				wsCcRfRadioSelfHealingPwrOffset
					Unsigned32,
				wsCcRfRadioRunAcsNow
					DoActionNow,
				wsCcRfRadioResetParentAp
					DoActionNow,
				wsCcRfRadioReset
					DoActionNow,
				wsCcRfRadioRowStatus
					RowStatus,
				wsCcRfRadioCcaLevel
					INTEGER,
				wsCcRfRadioCcaMode
					INTEGER,
				wsCcRfRadioRapSingleChannelScan
					TruthValue,
				wsCcRfRadioBssDtim
					OCTET STRING,
				wsCcRfRadioCfgMethod
					INTEGER
			 }

		-- 1.3.6.1.4.1.388.14.3.2.1.11.5.1.1
		wsCcRfRadioIndex OBJECT-TYPE
			SYNTAX Integer32 (1..1000)
			MAX-ACCESS accessible-for-notify
			STATUS current
			DESCRIPTION
				"Small, arbitrary integer index."
			::= { wsCcRfRadioEntry 1 }


		-- 1.3.6.1.4.1.388.14.3.2.1.11.5.1.2
		wsCcRfRadioApMac OBJECT-TYPE
			SYNTAX PhysAddress
			MAX-ACCESS read-create
			STATUS current
			DESCRIPTION
				"MAC address of the Access Port that this radio
				resides within."
			DEFVAL { 'FFFFFFFFFFFF'h }
			::= { wsCcRfRadioEntry 2 }


		-- 1.3.6.1.4.1.388.14.3.2.1.11.5.1.3
		wsCcRfRadioDescr OBJECT-TYPE
			SYNTAX DisplayString
			MAX-ACCESS read-create
			STATUS current
			DESCRIPTION
				"Description of the radio."
			DEFVAL { "" }
			::= { wsCcRfRadioEntry 3 }


		-- 1.3.6.1.4.1.388.14.3.2.1.11.5.1.4
		wsCcRfRadioType OBJECT-TYPE
			SYNTAX RadioType
			MAX-ACCESS read-create
			STATUS current
			DESCRIPTION
				"Radio model.  Changing this value will result in all
				parameters getting defaulted for this radio."
			DEFVAL { radio802dot11BG }
			::= { wsCcRfRadioEntry 4 }


		-- 1.3.6.1.4.1.388.14.3.2.1.11.5.1.5
		wsCcRfRadioApType OBJECT-TYPE
			SYNTAX ApType
			MAX-ACCESS read-create
			STATUS current
			DESCRIPTION
				"Model of the Access Port this radio resides in."
			DEFVAL { ap300 }
			::= { wsCcRfRadioEntry 5 }


		-- 1.3.6.1.4.1.388.14.3.2.1.11.5.1.6
		wsCcRfRadioBssWlanMap OBJECT-TYPE
			SYNTAX OCTET STRING
			MAX-ACCESS read-create
			STATUS current
			DESCRIPTION
				"The mapping of WLANs to BSSIDs. Each radio
				supports 4 BSSIDs and 16 WLANs. The user can map
				any number of WLANs to each of the BSSIDs. Each
				BSSID forms a virtual ap. "
			DEFVAL { '00'h }
			::= { wsCcRfRadioEntry 6 }


		-- 1.3.6.1.4.1.388.14.3.2.1.11.5.1.7
		wsCcRfRadioAntDiversity OBJECT-TYPE
			SYNTAX INTEGER
				{
				fullDiversity(1),
				primaryOnly(2),
				secondaryOnly(3)
				}
			MAX-ACCESS read-create
			STATUS current
			DESCRIPTION
				"The antenna diversity setting for the Access Port."
			DEFVAL { 1 }
			::= { wsCcRfRadioEntry 7 }


		-- 1.3.6.1.4.1.388.14.3.2.1.11.5.1.8
		wsCcRfRadioShortPreamble OBJECT-TYPE
			SYNTAX TruthValue
			MAX-ACCESS read-create
			STATUS current
			DESCRIPTION
				"Enable support for Short Preamble when MUs
				associate with the Access Port.  Enabling Short
				Preamble may cause incompatibility with some older
				clients.

				Applies only to b/g radios."
			DEFVAL { 1 }
			::= { wsCcRfRadioEntry 8 }


		-- 1.3.6.1.4.1.388.14.3.2.1.11.5.1.9
		wsCcRfRadioRtsThresh OBJECT-TYPE
			SYNTAX Integer32
			MAX-ACCESS read-create
			STATUS current
			DESCRIPTION
				"The Request To Send(RTS) threshold(in bytes) for use
				by this radio."
			DEFVAL { 2300 }
			::= { wsCcRfRadioEntry 9 }


		-- 1.3.6.1.4.1.388.14.3.2.1.11.5.1.10
		wsCcRfRadioBeaconInt OBJECT-TYPE
			SYNTAX Integer32 (50..200)
			MAX-ACCESS read-create
			STATUS current
			DESCRIPTION
				"Specify a beacon interval in units of 1,000
				microseconds (K-us). This is a multiple of the DTIM
				(wsCcRfRadioDtimPrd) value, for example,
				100 : 10. "
			DEFVAL { 100 }
			::= { wsCcRfRadioEntry 10 }


		-- 1.3.6.1.4.1.388.14.3.2.1.11.5.1.11
		wsCcRfRadioDtimPrd OBJECT-TYPE
			SYNTAX Integer32 (1..50)
			MAX-ACCESS read-create
			STATUS current
			DESCRIPTION
				"Specify a period for the Delivery Traffic Indication
				Message (DTIM). This is a divisor of the beacon
				interval (in milliseconds), for example, 10 : 100. "
			DEFVAL { 10 }
			::= { wsCcRfRadioEntry 11 }


		-- 1.3.6.1.4.1.388.14.3.2.1.11.5.1.12
		wsCcRfRadioBasicRates OBJECT-TYPE
			SYNTAX TransmitRate
			MAX-ACCESS read-create
			STATUS current
			DESCRIPTION
				"List of basic rates for the radio."
			DEFVAL { { rate1Mb, rate2Mb, rate5pt5Mb, rate11Mb } }
			::= { wsCcRfRadioEntry 12 }


		-- 1.3.6.1.4.1.388.14.3.2.1.11.5.1.13
		wsCcRfRadioSupportedRates OBJECT-TYPE
			SYNTAX TransmitRate
			MAX-ACCESS read-create
			STATUS current
			DESCRIPTION
				"List of supported rates for the radio."
			DEFVAL { { rate1Mb, rate2Mb, rate5pt5Mb, rate6Mb, rate9Mb, rate11Mb, rate12Mb, rate18Mb, rate24Mb, rate36Mb, rate48Mb, rate54Mb } }
			::= { wsCcRfRadioEntry 13 }


		-- 1.3.6.1.4.1.388.14.3.2.1.11.5.1.14
		wsCcRfRadioRapDetector OBJECT-TYPE
			SYNTAX TruthValue
			MAX-ACCESS read-create
			STATUS current
			DESCRIPTION
				"If this radio is a Rogue AP detector."
			DEFVAL { 1 }
			::= { wsCcRfRadioEntry 14 }


		-- 1.3.6.1.4.1.388.14.3.2.1.11.5.1.15
		wsCcRfRadioClusterIndex OBJECT-TYPE
			SYNTAX Unsigned32 (0..65535)
			MAX-ACCESS read-create
			STATUS current
			DESCRIPTION
				"The preferred group of Cluster"
			::= { wsCcRfRadioEntry 15 }


		-- 1.3.6.1.4.1.388.14.3.2.1.11.5.1.16
		wsCcRfRadioMaxMu OBJECT-TYPE
			SYNTAX Unsigned32 (1..1024)
			MAX-ACCESS read-create
			STATUS current
			DESCRIPTION
				"Max number of Mu a radio can associate."
			DEFVAL { 32 }
			::= { wsCcRfRadioEntry 16 }


		-- 1.3.6.1.4.1.388.14.3.2.1.11.5.1.17
		wsCcRfRadioSelfHealingAction OBJECT-TYPE
			SYNTAX INTEGER
				{
				none(1),
				both(2),
				raisePower(3),
				openRates(4)
				}
			MAX-ACCESS read-create
			STATUS current
			DESCRIPTION
				"Action taken by this radio when neighbor radios go down"
			DEFVAL { none }
			::= { wsCcRfRadioEntry 17 }


		-- 1.3.6.1.4.1.388.14.3.2.1.11.5.1.18
		wsCcRfRadioSelfHealingPwrOffset OBJECT-TYPE
			SYNTAX Unsigned32 (0..30)
			MAX-ACCESS read-create
			STATUS current
			DESCRIPTION
				"Self-healing power offset for this radio"
			::= { wsCcRfRadioEntry 18 }


		-- 1.3.6.1.4.1.388.14.3.2.1.11.5.1.19
		wsCcRfRadioRunAcsNow OBJECT-TYPE
			SYNTAX DoActionNow
			MAX-ACCESS read-create
			STATUS current
			DESCRIPTION
				"Set wsCcRfRadioRunAcsNow to 1 to run Acs."
			DEFVAL { 2 }
			::= { wsCcRfRadioEntry 19 }


		-- 1.3.6.1.4.1.388.14.3.2.1.11.5.1.20
		wsCcRfRadioResetParentAp OBJECT-TYPE
			SYNTAX DoActionNow
			MAX-ACCESS read-create
			STATUS current
			DESCRIPTION
				"Set wsCcRfRadioResetParentAp to 1 to reset the
				parent Access Port of this radio."
			DEFVAL { 2 }
			::= { wsCcRfRadioEntry 20 }


		-- 1.3.6.1.4.1.388.14.3.2.1.11.5.1.21
		wsCcRfRadioReset OBJECT-TYPE
			SYNTAX DoActionNow
			MAX-ACCESS read-create
			STATUS current
			DESCRIPTION
				"Set wsCcRfRadioReset to 1 to reset the Radio."
			DEFVAL { 2 }
			::= { wsCcRfRadioEntry 21 }


		-- 1.3.6.1.4.1.388.14.3.2.1.11.5.1.22
		wsCcRfRadioRowStatus OBJECT-TYPE
			SYNTAX RowStatus
			MAX-ACCESS read-create
			STATUS current
			DESCRIPTION
				"Rows status of the wsCcRfRadioTable"
			::= { wsCcRfRadioEntry 22 }


		-- 1.3.6.1.4.1.388.14.3.2.1.11.5.1.23
		wsCcRfRadioCcaLevel OBJECT-TYPE
			SYNTAX INTEGER (1..31)
			MAX-ACCESS read-create
			STATUS deprecated
			DESCRIPTION
				"Description."
			DEFVAL { 1 }
			::= { wsCcRfRadioEntry 23 }


		-- 1.3.6.1.4.1.388.14.3.2.1.11.5.1.24
		wsCcRfRadioCcaMode OBJECT-TYPE
			SYNTAX INTEGER (1..3)
			MAX-ACCESS read-create
			STATUS deprecated
			DESCRIPTION
				"Description."
			DEFVAL { 1 }
			::= { wsCcRfRadioEntry 24 }


		-- 1.3.6.1.4.1.388.14.3.2.1.11.5.1.25
		wsCcRfRadioRapSingleChannelScan OBJECT-TYPE
			SYNTAX TruthValue
			MAX-ACCESS read-create
			STATUS current
			DESCRIPTION
				"Enable or disable single-channel scan for Rogue AP."
			::= { wsCcRfRadioEntry 25 }


		-- 1.3.6.1.4.1.388.14.3.2.1.11.5.1.26
		wsCcRfRadioBssDtim OBJECT-TYPE
			SYNTAX OCTET STRING
			MAX-ACCESS read-create
			STATUS current
			DESCRIPTION
				"Set DTIM per BSS."
			::= { wsCcRfRadioEntry 26 }


		-- 1.3.6.1.4.1.388.14.3.2.1.11.5.1.27
		wsCcRfRadioCfgMethod OBJECT-TYPE
			SYNTAX INTEGER
				{
				userConfigured(1),
				switchConfigured(2)
				}
			MAX-ACCESS read-only
			STATUS current
			DESCRIPTION
				"The radio can be configured by user before being adopted
				or by the switch while adoption"
			::= { wsCcRfRadioEntry 27 }


		-- 1.3.6.1.4.1.388.14.3.2.1.11.6
		wsCcRfRadioChannelPowerTable OBJECT-TYPE
			SYNTAX SEQUENCE OF WsCcRfRadioChannelPowerEntry
			MAX-ACCESS not-accessible
			STATUS current
			DESCRIPTION
				"Use wsCcRfRadioChannelPower table to view and
				set the channel/power/placement properties of
				the radios.

				The process can be broken down into the following steps:
				1. Set wsCcRfRadioCpReset to TRUE.
				2. Set wsCcRfRadioCpPlacement
				3. Get wsCcRfRadioCpPosChannel
				4. Set wsCcRfRadioCpDesChannel
				5. Get wsCcRfRadioCpPosPowerLevel
				6. Set wsCcRfRadioCpDesPowerLevel
				7. Get wsCcRfRadioCpPowerInMW
				8. Set wsCcRfRadioCpSet


				"
			::= { wsCcRfRadio 6 }


		-- 1.3.6.1.4.1.388.14.3.2.1.11.6.1
		wsCcRfRadioChannelPowerEntry OBJECT-TYPE
			SYNTAX WsCcRfRadioChannelPowerEntry
			MAX-ACCESS not-accessible
			STATUS current
			DESCRIPTION
				" "
			INDEX { wsCcRfRadioIndex }
			::= { wsCcRfRadioChannelPowerTable 1 }


		WsCcRfRadioChannelPowerEntry ::=
			SEQUENCE {
				wsCcRfRadioCpPlacement
					INTEGER,
				wsCcRfRadioCpChannelMode
					INTEGER,
				wsCcRfRadioCpPosChannel
					MultiPointer64,
				wsCcRfRadioCpDesChannel
					Unsigned32,
				wsCcRfRadioCpPosPowerDb
					Integer32,
				wsCcRfRadioCpDesPowerDb
					Integer32,
				wsCcRfRadioCpDesPowerMw
					Integer32,
				wsCcRfRadioCpSet
					DoActionShowProgress,
				wsCcRfRadioCpReset
					DoActionShowProgress
			 }

		-- 1.3.6.1.4.1.388.14.3.2.1.11.6.1.1
		wsCcRfRadioCpPlacement OBJECT-TYPE
			SYNTAX INTEGER
				{
				indoor(1),
				outdoor(2)
				}
			MAX-ACCESS read-write
			STATUS current
			DESCRIPTION
				"The placement for radio."
			::= { wsCcRfRadioChannelPowerEntry 1 }


		-- 1.3.6.1.4.1.388.14.3.2.1.11.6.1.2
		wsCcRfRadioCpChannelMode OBJECT-TYPE
			SYNTAX INTEGER
				{
				fixed(1),
				random(2),
				acs(3)
				}
			MAX-ACCESS read-write
			STATUS current
			DESCRIPTION
				"fixed mode: apply user selected channel
				random mode: random channel selection
				acs mode: auto channel selection (radio will scan for the
				least congested channel at startup or reconfiguration)"
			::= { wsCcRfRadioChannelPowerEntry 2 }


		-- 1.3.6.1.4.1.388.14.3.2.1.11.6.1.3
		wsCcRfRadioCpPosChannel OBJECT-TYPE
			SYNTAX MultiPointer64
			MAX-ACCESS read-only
			STATUS current
			DESCRIPTION
				"The possible channels that can be set when
				placement = wsCcRfRadioCpPlacement."
			::= { wsCcRfRadioChannelPowerEntry 3 }


		-- 1.3.6.1.4.1.388.14.3.2.1.11.6.1.4
		wsCcRfRadioCpDesChannel OBJECT-TYPE
			SYNTAX Unsigned32
			MAX-ACCESS read-write
			STATUS current
			DESCRIPTION
				"The desired channel for radio."
			::= { wsCcRfRadioChannelPowerEntry 4 }


		-- 1.3.6.1.4.1.388.14.3.2.1.11.6.1.5
		wsCcRfRadioCpPosPowerDb OBJECT-TYPE
			SYNTAX Integer32
			MAX-ACCESS read-only
			STATUS current
			DESCRIPTION
				"The max possible power level (dBm) that can be set when
				channel= wsCcRfRadioCpDesChannel."
			::= { wsCcRfRadioChannelPowerEntry 5 }


		-- 1.3.6.1.4.1.388.14.3.2.1.11.6.1.6
		wsCcRfRadioCpDesPowerDb OBJECT-TYPE
			SYNTAX Integer32
			MAX-ACCESS read-write
			STATUS current
			DESCRIPTION
				"The desired power level (dBm) for radio."
			::= { wsCcRfRadioChannelPowerEntry 6 }


		-- 1.3.6.1.4.1.388.14.3.2.1.11.6.1.7
		wsCcRfRadioCpDesPowerMw OBJECT-TYPE
			SYNTAX Integer32
			MAX-ACCESS read-only
			STATUS current
			DESCRIPTION
				"wsCcRfRadioCpDesPowerLevel in mW."
			::= { wsCcRfRadioChannelPowerEntry 7 }


		-- 1.3.6.1.4.1.388.14.3.2.1.11.6.1.8
		wsCcRfRadioCpSet OBJECT-TYPE
			SYNTAX DoActionShowProgress
			MAX-ACCESS read-write
			STATUS current
			DESCRIPTION
				"Validate values in wsCcRfRadioCpDes fields.  If it is
				a valid combination, configure the switch with this
				combination and set wsCcRfRadioCp_ to these values."
			::= { wsCcRfRadioChannelPowerEntry 8 }


		-- 1.3.6.1.4.1.388.14.3.2.1.11.6.1.9
		wsCcRfRadioCpReset OBJECT-TYPE
			SYNTAX DoActionShowProgress
			MAX-ACCESS read-write
			STATUS current
			DESCRIPTION
				"Reset the following OIDs.

				wsCcRfRadioCpDesPlacement
				wsCcRfRadioCpDesChannel
				wsCcRfRadioCpDesPowerLevel
				wsCcRfRadioCpPosChannel
				wsCcRfRadioCpPosPowerLevel
				wsCcRfRadioCpPowerInMW
				"
			::= { wsCcRfRadioChannelPowerEntry 9 }


		-- 1.3.6.1.4.1.388.14.3.2.1.11.7
		wsCcRfRadioWmmTable OBJECT-TYPE
			SYNTAX SEQUENCE OF WsCcRfRadioWmmEntry
			MAX-ACCESS not-accessible
			STATUS current
			DESCRIPTION
				"Configuration parameters for 802.11e / Wireless
				MultiMedia, which control the Quality of
				Service between the wireless devices on
				the network"
			::= { wsCcRfRadio 7 }


		-- 1.3.6.1.4.1.388.14.3.2.1.11.7.1
		wsCcRfRadioWmmEntry OBJECT-TYPE
			SYNTAX WsCcRfRadioWmmEntry
			MAX-ACCESS not-accessible
			STATUS current
			DESCRIPTION
				" "
			INDEX { wsCcRfRadioIndex, wsCcRfRadioWmmAccessCategory }
			::= { wsCcRfRadioWmmTable 1 }


		WsCcRfRadioWmmEntry ::=
			SEQUENCE {
				wsCcRfRadioWmmAccessCategory
					INTEGER,
				wsCcRfRadioWmmAdmissionCtrl
					TruthValue,
				wsCcRfRadioWmmAifsn
					Unsigned32,
				wsCcRfRadioWmmTxOp
					Unsigned32,
				wsCcRfRadioWmmCwMin
					Unsigned32,
				wsCcRfRadioWmmCwMax
					Integer32,
				wsCcRfRadioWmmAdmissionDeviceMax
					Integer32
			 }

		-- 1.3.6.1.4.1.388.14.3.2.1.11.7.1.1
		wsCcRfRadioWmmAccessCategory OBJECT-TYPE
			SYNTAX INTEGER
				{
				acBestEffort(1),
				acBackground(2),
				acVideo(3),
				acVoice(4)
				}
			MAX-ACCESS accessible-for-notify
			STATUS current
			DESCRIPTION
				"A label for a particular QoS category of traffic in
				an 802.11e network. WMM defines 4 Access Categories
				(Voice, Video, Best Effort, Background)."
			::= { wsCcRfRadioWmmEntry 1 }


		-- 1.3.6.1.4.1.388.14.3.2.1.11.7.1.2
		wsCcRfRadioWmmAdmissionCtrl OBJECT-TYPE
			SYNTAX TruthValue
			MAX-ACCESS read-write
			STATUS current
			DESCRIPTION
				" "
			::= { wsCcRfRadioWmmEntry 2 }


		-- 1.3.6.1.4.1.388.14.3.2.1.11.7.1.3
		wsCcRfRadioWmmAifsn OBJECT-TYPE
			SYNTAX Unsigned32 (0..15)
			MAX-ACCESS read-write
			STATUS current
			DESCRIPTION
				"The Arbitration Inter-Frame Spacing is the wait time
				in milliSeconds between data frames. A smaller
				number leads to greater priority for medium access."
			::= { wsCcRfRadioWmmEntry 3 }


		-- 1.3.6.1.4.1.388.14.3.2.1.11.7.1.4
		wsCcRfRadioWmmTxOp OBJECT-TYPE
			SYNTAX Unsigned32 (0..65535)
			UNITS "millisecond"
			MAX-ACCESS read-write
			STATUS current
			DESCRIPTION
				"An interval of time where an 802.11e station
				(MU/AP) has the right to initiate transmissions
				on the wireless medium."
			::= { wsCcRfRadioWmmEntry 4 }


		-- 1.3.6.1.4.1.388.14.3.2.1.11.7.1.5
		wsCcRfRadioWmmCwMin OBJECT-TYPE
			SYNTAX Unsigned32 (0..15)
			MAX-ACCESS read-write
			STATUS current
			DESCRIPTION
				"If the medium is busy, or a transmitted frame
				collides, the AP or MU choose a random number
				between 0 and this minimum contention window size,
				to decide how long to wait before attempting
				(re)-transmission. For ease of use this value is
				configured as a number between 0 and 10; the
				actual window is calculated using 2**x -1 where
				x is the value configured."
			::= { wsCcRfRadioWmmEntry 5 }


		-- 1.3.6.1.4.1.388.14.3.2.1.11.7.1.6
		wsCcRfRadioWmmCwMax OBJECT-TYPE
			SYNTAX Integer32 (0..15)
			MAX-ACCESS read-write
			STATUS current
			DESCRIPTION
				"On each collision the AP or MU doubles its
				initial contention window wait time, until that
				number is as large as this maximum contention
				window size. For ease of use this value is
				configured as a number between 0 and 10; the
				actual window is calculated using 2**x -1 where
				x is the value configured."
			::= { wsCcRfRadioWmmEntry 6 }


		-- 1.3.6.1.4.1.388.14.3.2.1.11.7.1.7
		wsCcRfRadioWmmAdmissionDeviceMax OBJECT-TYPE
			SYNTAX Integer32 (1..256)
			MAX-ACCESS read-write
			STATUS current
			DESCRIPTION
				"Description."
			::= { wsCcRfRadioWmmEntry 7 }


		-- 1.3.6.1.4.1.388.14.3.2.1.11.8
		wsCcRfRadioDefaultTable OBJECT-TYPE
			SYNTAX SEQUENCE OF WsCcRfRadioDefaultEntry
			MAX-ACCESS not-accessible
			STATUS current
			DESCRIPTION
				"This table lists the default setting for all supported
				radio for this switch.  Please refer to wsCcRfRadioTable
				for column descriptions."
			::= { wsCcRfRadio 8 }


		-- 1.3.6.1.4.1.388.14.3.2.1.11.8.1
		wsCcRfRadioDefaultEntry OBJECT-TYPE
			SYNTAX WsCcRfRadioDefaultEntry
			MAX-ACCESS not-accessible
			STATUS current
			DESCRIPTION
				" "
			INDEX { wsCcRfRadioDefaultIndex }
			::= { wsCcRfRadioDefaultTable 1 }


		WsCcRfRadioDefaultEntry ::=
			SEQUENCE {
				wsCcRfRadioDefaultIndex
					Integer32,
				wsCcRfRadioDefaultType
					RadioType,
				wsCcRfRadioDefaultApType
					ApType,
				wsCcRfRadioDefaultBssWlanMap
					OCTET STRING,
				wsCcRfRadioDefaultAntDiversity
					INTEGER,
				wsCcRfRadioDefaultShortPreamble
					TruthValue,
				wsCcRfRadioDefaultRtsThresh
					Integer32,
				wsCcRfRadioDefaultBeaconInt
					Integer32,
				wsCcRfRadioDefaultDtimPrd
					Integer32,
				wsCcRfRadioDefaultBasicRates
					TransmitRate,
				wsCcRfRadioDefaultSupportedRates
					TransmitRate,
				wsCcRfRadioDefaultRapDetector
					TruthValue,
				wsCcRfRadioDefaultClusterIndex
					Unsigned32,
				wsCcRfRadioDefaultMaxMu
					Unsigned32,
				wsCcRfRadioDefaultSelfHealingAction
					INTEGER,
				wsCcRfRadioDefaultSelfHealingPwrOffset
					Unsigned32,
				wsCcRfRadioDefaultRapSingleChannelScan
					TruthValue
			 }

		-- 1.3.6.1.4.1.388.14.3.2.1.11.8.1.1
		wsCcRfRadioDefaultIndex OBJECT-TYPE
			SYNTAX Integer32 (1..100)
			MAX-ACCESS accessible-for-notify
			STATUS current
			DESCRIPTION
				" "
			::= { wsCcRfRadioDefaultEntry 1 }


		-- 1.3.6.1.4.1.388.14.3.2.1.11.8.1.2
		wsCcRfRadioDefaultType OBJECT-TYPE
			SYNTAX RadioType
			MAX-ACCESS read-only
			STATUS current
			DESCRIPTION
				" "
			::= { wsCcRfRadioDefaultEntry 2 }


		-- 1.3.6.1.4.1.388.14.3.2.1.11.8.1.3
		wsCcRfRadioDefaultApType OBJECT-TYPE
			SYNTAX ApType
			MAX-ACCESS read-only
			STATUS current
			DESCRIPTION
				" "
			::= { wsCcRfRadioDefaultEntry 3 }


		-- 1.3.6.1.4.1.388.14.3.2.1.11.8.1.4
		wsCcRfRadioDefaultBssWlanMap OBJECT-TYPE
			SYNTAX OCTET STRING
			MAX-ACCESS read-write
			STATUS current
			DESCRIPTION
				" "
			::= { wsCcRfRadioDefaultEntry 4 }


		-- 1.3.6.1.4.1.388.14.3.2.1.11.8.1.5
		wsCcRfRadioDefaultAntDiversity OBJECT-TYPE
			SYNTAX INTEGER
				{
				fullDiversity(1),
				primaryOnly(2),
				secondaryOnly(3)
				}
			MAX-ACCESS read-write
			STATUS current
			DESCRIPTION
				" "
			::= { wsCcRfRadioDefaultEntry 5 }


		-- 1.3.6.1.4.1.388.14.3.2.1.11.8.1.6
		wsCcRfRadioDefaultShortPreamble OBJECT-TYPE
			SYNTAX TruthValue
			MAX-ACCESS read-write
			STATUS current
			DESCRIPTION
				" "
			::= { wsCcRfRadioDefaultEntry 6 }


		-- 1.3.6.1.4.1.388.14.3.2.1.11.8.1.7
		wsCcRfRadioDefaultRtsThresh OBJECT-TYPE
			SYNTAX Integer32
			MAX-ACCESS read-write
			STATUS current
			DESCRIPTION
				" "
			::= { wsCcRfRadioDefaultEntry 7 }


		-- 1.3.6.1.4.1.388.14.3.2.1.11.8.1.8
		wsCcRfRadioDefaultBeaconInt OBJECT-TYPE
			SYNTAX Integer32 (50..200)
			MAX-ACCESS read-write
			STATUS current
			DESCRIPTION
				" "
			::= { wsCcRfRadioDefaultEntry 8 }


		-- 1.3.6.1.4.1.388.14.3.2.1.11.8.1.9
		wsCcRfRadioDefaultDtimPrd OBJECT-TYPE
			SYNTAX Integer32 (1..50)
			MAX-ACCESS read-write
			STATUS current
			DESCRIPTION
				" "
			::= { wsCcRfRadioDefaultEntry 9 }


		-- 1.3.6.1.4.1.388.14.3.2.1.11.8.1.10
		wsCcRfRadioDefaultBasicRates OBJECT-TYPE
			SYNTAX TransmitRate
			MAX-ACCESS read-write
			STATUS current
			DESCRIPTION
				" "
			::= { wsCcRfRadioDefaultEntry 10 }


		-- 1.3.6.1.4.1.388.14.3.2.1.11.8.1.11
		wsCcRfRadioDefaultSupportedRates OBJECT-TYPE
			SYNTAX TransmitRate
			MAX-ACCESS read-write
			STATUS current
			DESCRIPTION
				" "
			::= { wsCcRfRadioDefaultEntry 11 }


		-- 1.3.6.1.4.1.388.14.3.2.1.11.8.1.12
		wsCcRfRadioDefaultRapDetector OBJECT-TYPE
			SYNTAX TruthValue
			MAX-ACCESS read-write
			STATUS current
			DESCRIPTION
				" "
			::= { wsCcRfRadioDefaultEntry 12 }


		-- 1.3.6.1.4.1.388.14.3.2.1.11.8.1.13
		wsCcRfRadioDefaultClusterIndex OBJECT-TYPE
			SYNTAX Unsigned32
			MAX-ACCESS read-write
			STATUS current
			DESCRIPTION
				" "
			::= { wsCcRfRadioDefaultEntry 13 }


		-- 1.3.6.1.4.1.388.14.3.2.1.11.8.1.14
		wsCcRfRadioDefaultMaxMu OBJECT-TYPE
			SYNTAX Unsigned32 (1..256)
			MAX-ACCESS read-write
			STATUS current
			DESCRIPTION
				" "
			::= { wsCcRfRadioDefaultEntry 14 }


		-- 1.3.6.1.4.1.388.14.3.2.1.11.8.1.15
		wsCcRfRadioDefaultSelfHealingAction OBJECT-TYPE
			SYNTAX INTEGER
				{
				none(1),
				both(2),
				raisePower(3),
				openRates(4)
				}
			MAX-ACCESS read-write
			STATUS current
			DESCRIPTION
				" "
			::= { wsCcRfRadioDefaultEntry 15 }


		-- 1.3.6.1.4.1.388.14.3.2.1.11.8.1.16
		wsCcRfRadioDefaultSelfHealingPwrOffset OBJECT-TYPE
			SYNTAX Unsigned32 (0..30)
			MAX-ACCESS read-write
			STATUS current
			DESCRIPTION
				" "
			::= { wsCcRfRadioDefaultEntry 16 }


		-- 1.3.6.1.4.1.388.14.3.2.1.11.8.1.17
		wsCcRfRadioDefaultRapSingleChannelScan OBJECT-TYPE
			SYNTAX TruthValue
			MAX-ACCESS read-write
			STATUS current
			DESCRIPTION
				"Enable or disable single-channel scan for Rogue AP."
			::= { wsCcRfRadioDefaultEntry 17 }


		-- 1.3.6.1.4.1.388.14.3.2.1.11.9
		wsCcRfRadioDefaultChannelPowerTable OBJECT-TYPE
			SYNTAX SEQUENCE OF WsCcRfRadioDefaultChannelPowerEntry
			MAX-ACCESS not-accessible
			STATUS current
			DESCRIPTION
				"Use wsCcRfRadioDefaultChannelPower table to view and
				set the channel/power/placement properties of
				the default radio configurations.

				Please refer to the descriptions in wsCcRfRadioChannelPowerTable


				"
			::= { wsCcRfRadio 9 }


		-- 1.3.6.1.4.1.388.14.3.2.1.11.9.1
		wsCcRfRadioDefaultChannelPowerEntry OBJECT-TYPE
			SYNTAX WsCcRfRadioDefaultChannelPowerEntry
			MAX-ACCESS not-accessible
			STATUS current
			DESCRIPTION
				" "
			INDEX { wsCcRfRadioDefaultIndex }
			::= { wsCcRfRadioDefaultChannelPowerTable 1 }


		WsCcRfRadioDefaultChannelPowerEntry ::=
			SEQUENCE {
				wsCcRfRadioDefaultCpPlacement
					INTEGER,
				wsCcRfRadioDefaultCpChannelMode
					INTEGER,
				wsCcRfRadioDefaultCpPosChannel
					MultiPointer64,
				wsCcRfRadioDefaultCpDesChannel
					Unsigned32,
				wsCcRfRadioDefaultCpPosPowerDb
					Integer32,
				wsCcRfRadioDefaultCpDesPowerDb
					Integer32,
				wsCcRfRadioDefaultCpDesPowerMw
					Integer32,
				wsCcRfRadioDefaultCpSet
					DoActionShowProgress,
				wsCcRfRadioDefaultCpReset
					DoActionShowProgress
			 }

		-- 1.3.6.1.4.1.388.14.3.2.1.11.9.1.1
		wsCcRfRadioDefaultCpPlacement OBJECT-TYPE
			SYNTAX INTEGER
				{
				indoor(1),
				outdoor(2)
				}
			MAX-ACCESS read-write
			STATUS current
			DESCRIPTION
				" "
			::= { wsCcRfRadioDefaultChannelPowerEntry 1 }


		-- 1.3.6.1.4.1.388.14.3.2.1.11.9.1.2
		wsCcRfRadioDefaultCpChannelMode OBJECT-TYPE
			SYNTAX INTEGER
				{
				random(2),
				acs(3)
				}
			MAX-ACCESS read-write
			STATUS current
			DESCRIPTION
				" "
			::= { wsCcRfRadioDefaultChannelPowerEntry 2 }


		-- 1.3.6.1.4.1.388.14.3.2.1.11.9.1.3
		wsCcRfRadioDefaultCpPosChannel OBJECT-TYPE
			SYNTAX MultiPointer64
			MAX-ACCESS read-only
			STATUS current
			DESCRIPTION
				" "
			::= { wsCcRfRadioDefaultChannelPowerEntry 3 }


		-- 1.3.6.1.4.1.388.14.3.2.1.11.9.1.4
		wsCcRfRadioDefaultCpDesChannel OBJECT-TYPE
			SYNTAX Unsigned32
			MAX-ACCESS read-write
			STATUS current
			DESCRIPTION
				" "
			::= { wsCcRfRadioDefaultChannelPowerEntry 4 }


		-- 1.3.6.1.4.1.388.14.3.2.1.11.9.1.5
		wsCcRfRadioDefaultCpPosPowerDb OBJECT-TYPE
			SYNTAX Integer32
			MAX-ACCESS read-only
			STATUS current
			DESCRIPTION
				" "
			::= { wsCcRfRadioDefaultChannelPowerEntry 5 }


		-- 1.3.6.1.4.1.388.14.3.2.1.11.9.1.6
		wsCcRfRadioDefaultCpDesPowerDb OBJECT-TYPE
			SYNTAX Integer32
			MAX-ACCESS read-write
			STATUS current
			DESCRIPTION
				" "
			::= { wsCcRfRadioDefaultChannelPowerEntry 6 }


		-- 1.3.6.1.4.1.388.14.3.2.1.11.9.1.7
		wsCcRfRadioDefaultCpDesPowerMw OBJECT-TYPE
			SYNTAX Integer32
			MAX-ACCESS read-only
			STATUS current
			DESCRIPTION
				" "
			::= { wsCcRfRadioDefaultChannelPowerEntry 7 }


		-- 1.3.6.1.4.1.388.14.3.2.1.11.9.1.8
		wsCcRfRadioDefaultCpSet OBJECT-TYPE
			SYNTAX DoActionShowProgress
			MAX-ACCESS read-write
			STATUS current
			DESCRIPTION
				" ."
			::= { wsCcRfRadioDefaultChannelPowerEntry 8 }


		-- 1.3.6.1.4.1.388.14.3.2.1.11.9.1.9
		wsCcRfRadioDefaultCpReset OBJECT-TYPE
			SYNTAX DoActionShowProgress
			MAX-ACCESS read-write
			STATUS current
			DESCRIPTION
				" "
			::= { wsCcRfRadioDefaultChannelPowerEntry 9 }


		-- 1.3.6.1.4.1.388.14.3.2.1.11.10
		wsCcRfRadioDefaultWmmTable OBJECT-TYPE
			SYNTAX SEQUENCE OF WsCcRfRadioDefaultWmmEntry
			MAX-ACCESS not-accessible
			STATUS current
			DESCRIPTION
				"Configuration parameters for 802.11e / Wireless
				MultiMedia, which control the Quality of
				Service between the wireless devices on
				the network"
			::= { wsCcRfRadio 10 }


		-- 1.3.6.1.4.1.388.14.3.2.1.11.10.1
		wsCcRfRadioDefaultWmmEntry OBJECT-TYPE
			SYNTAX WsCcRfRadioDefaultWmmEntry
			MAX-ACCESS not-accessible
			STATUS current
			DESCRIPTION
				" "
			INDEX { wsCcRfRadioDefaultIndex, wsCcRfRadioDefaultWmmAccessCategory }
			::= { wsCcRfRadioDefaultWmmTable 1 }


		WsCcRfRadioDefaultWmmEntry ::=
			SEQUENCE {
				wsCcRfRadioDefaultWmmAccessCategory
					INTEGER,
				wsCcRfRadioDefaultWmmAdmissionCtrl
					TruthValue,
				wsCcRfRadioDefaultWmmAifsn
					Unsigned32,
				wsCcRfRadioDefaultWmmTxOp
					Unsigned32,
				wsCcRfRadioDefaultWmmCwMin
					Unsigned32,
				wsCcRfRadioDefaultWmmCwMax
					Integer32
			 }

		-- 1.3.6.1.4.1.388.14.3.2.1.11.10.1.1
		wsCcRfRadioDefaultWmmAccessCategory OBJECT-TYPE
			SYNTAX INTEGER
				{
				acBestEffort(1),
				acBackground(2),
				acVideo(3),
				acVoice(4)
				}
			MAX-ACCESS accessible-for-notify
			STATUS current
			DESCRIPTION
				"A label for a particular QoS category of traffic in
				an 802.11e network. WMM defines 4 Access Categories
				(Voice, Video, Best Effort, Background)."
			::= { wsCcRfRadioDefaultWmmEntry 1 }


		-- 1.3.6.1.4.1.388.14.3.2.1.11.10.1.2
		wsCcRfRadioDefaultWmmAdmissionCtrl OBJECT-TYPE
			SYNTAX TruthValue
			MAX-ACCESS read-write
			STATUS current
			DESCRIPTION
				" "
			::= { wsCcRfRadioDefaultWmmEntry 2 }


		-- 1.3.6.1.4.1.388.14.3.2.1.11.10.1.3
		wsCcRfRadioDefaultWmmAifsn OBJECT-TYPE
			SYNTAX Unsigned32 (1..15)
			MAX-ACCESS read-write
			STATUS current
			DESCRIPTION
				"The Arbitration Inter-Frame Spacing is the wait time
				in milliSeconds between data frames. A smaller
				number leads to greater priority for medium access."
			::= { wsCcRfRadioDefaultWmmEntry 3 }


		-- 1.3.6.1.4.1.388.14.3.2.1.11.10.1.4
		wsCcRfRadioDefaultWmmTxOp OBJECT-TYPE
			SYNTAX Unsigned32 (0..65535)
			UNITS "millisecond"
			MAX-ACCESS read-write
			STATUS current
			DESCRIPTION
				"An interval of time where an 802.11e station
				(MU/AP) has the right to initiate transmissions
				on the wireless medium."
			::= { wsCcRfRadioDefaultWmmEntry 4 }


		-- 1.3.6.1.4.1.388.14.3.2.1.11.10.1.5
		wsCcRfRadioDefaultWmmCwMin OBJECT-TYPE
			SYNTAX Unsigned32 (0..15)
			MAX-ACCESS read-write
			STATUS current
			DESCRIPTION
				"If the medium is busy, or a transmitted frame
				collides, the AP or MU choose a random number
				between 0 and this minimum contention window size,
				to decide how long to wait before attempting
				(re)-transmission. For ease of use this value is
				configured as a number between 0 and 10; the
				actual window is calculated using 2**x -1 where
				x is the value configured."
			::= { wsCcRfRadioDefaultWmmEntry 5 }


		-- 1.3.6.1.4.1.388.14.3.2.1.11.10.1.6
		wsCcRfRadioDefaultWmmCwMax OBJECT-TYPE
			SYNTAX Integer32 (0..15)
			MAX-ACCESS read-write
			STATUS current
			DESCRIPTION
				"On each collision the AP or MU doubles its
				initial contention window wait time, until that
				number is as large as this maximum contention
				window size. For ease of use this value is
				configured as a number between 0 and 10; the
				actual window is calculated using 2**x -1 where
				x is the value configured."
			::= { wsCcRfRadioDefaultWmmEntry 6 }


		-- 1.3.6.1.4.1.388.14.3.2.1.11.11
		wsCcRfRadioStatusTable OBJECT-TYPE
			SYNTAX SEQUENCE OF WsCcRfRadioStatusEntry
			MAX-ACCESS not-accessible
			STATUS current
			DESCRIPTION
				"Status of adopted radios."
			::= { wsCcRfRadio 11 }


		-- 1.3.6.1.4.1.388.14.3.2.1.11.11.1
		wsCcRfRadioStatusEntry OBJECT-TYPE
			SYNTAX WsCcRfRadioStatusEntry
			MAX-ACCESS not-accessible
			STATUS current
			DESCRIPTION
				" "
			INDEX { wsCcRfRadioIndex }
			::= { wsCcRfRadioStatusTable 1 }


		WsCcRfRadioStatusEntry ::=
			SEQUENCE {
				wsCcRfRadioStatusRadioMac
					PhysAddress,
				wsCcRfRadioStatusState
					INTEGER,
				wsCcRfRadioStatusPtrToAp
					SinglePointer,
				wsCcRfRadioStatusMaxWlans
					Integer32,
				wsCcRfRadioStatusMaxBss
					Integer32,
				wsCcRfRadioStatusCurrChannel
					Unsigned32,
				wsCcRfRadioStatusCurrPowerDb
					Integer32,
				wsCcRfRadioStatusCurrPowerMw
					Integer32,
				wsCcRfRadioStatusAssociatedMus
					Integer32,
				wsCcRfRadioStatusLastAdoption
					TimeTicks,
				wsCcRfRadioStatusShortSlotTime
					Integer32,
				wsCcRfRadioStatusVlanTag
					Unsigned32,
				wsCcRfRadioStatusCfgMethod
					INTEGER
			 }

		-- 1.3.6.1.4.1.388.14.3.2.1.11.11.1.1
		wsCcRfRadioStatusRadioMac OBJECT-TYPE
			SYNTAX PhysAddress
			MAX-ACCESS read-only
			STATUS current
			DESCRIPTION
				"Radio MAC address"
			::= { wsCcRfRadioStatusEntry 1 }


		-- 1.3.6.1.4.1.388.14.3.2.1.11.11.1.2
		wsCcRfRadioStatusState OBJECT-TYPE
			SYNTAX INTEGER
				{
				unadopted(1),
				normal(2),
				detector(3),
				selfHealing(4)
				}
			MAX-ACCESS read-only
			STATUS current
			DESCRIPTION
				"This value describes the state of the radio.

				A healthy radio would power-on, and quickly advance from
				  radioUpAndWaitingForConfig and then on to
				  radioReceivingConfig and then on to
				  radioUpAndAdopted.

				A radio that is denied adoption due to ACLs would show:
				  radioDeniedAdoptionDueToAcl.

				A radio that does not 'handshake' with the switch properly
				would be found in state:
				  radioBroken."
			::= { wsCcRfRadioStatusEntry 2 }


		-- 1.3.6.1.4.1.388.14.3.2.1.11.11.1.3
		wsCcRfRadioStatusPtrToAp OBJECT-TYPE
			SYNTAX SinglePointer
			MAX-ACCESS read-only
			STATUS current
			DESCRIPTION
				"This value is the index in the ApTable for the
				entry representing the Access Port that contains
				this radio.

				Since each radio has one and only one Access Port
				as 'parent', this value is a simple integer, not a
				bit-mask."
			::= { wsCcRfRadioStatusEntry 3 }


		-- 1.3.6.1.4.1.388.14.3.2.1.11.11.1.4
		wsCcRfRadioStatusMaxWlans OBJECT-TYPE
			SYNTAX Integer32
			MAX-ACCESS read-only
			STATUS current
			DESCRIPTION
				"the maximum number of 802.11 ESSIDs (wireless lans)
				supported by this radio"
			::= { wsCcRfRadioStatusEntry 4 }


		-- 1.3.6.1.4.1.388.14.3.2.1.11.11.1.5
		wsCcRfRadioStatusMaxBss OBJECT-TYPE
			SYNTAX Integer32
			MAX-ACCESS read-only
			STATUS current
			DESCRIPTION
				"The maximum number of 802.11 BSSIDs supported by
				this radio"
			::= { wsCcRfRadioStatusEntry 5 }


		-- 1.3.6.1.4.1.388.14.3.2.1.11.11.1.6
		wsCcRfRadioStatusCurrChannel OBJECT-TYPE
			SYNTAX Unsigned32
			MAX-ACCESS read-only
			STATUS current
			DESCRIPTION
				"current channel (may be different from configured channel due to DFS etc)."
			::= { wsCcRfRadioStatusEntry 6 }


		-- 1.3.6.1.4.1.388.14.3.2.1.11.11.1.7
		wsCcRfRadioStatusCurrPowerDb OBJECT-TYPE
			SYNTAX Integer32 (0..255)
			UNITS "dB"
			MAX-ACCESS read-only
			STATUS current
			DESCRIPTION
				"Output power level for the radio in Db. "
			::= { wsCcRfRadioStatusEntry 7 }


		-- 1.3.6.1.4.1.388.14.3.2.1.11.11.1.8
		wsCcRfRadioStatusCurrPowerMw OBJECT-TYPE
			SYNTAX Integer32
			MAX-ACCESS read-only
			STATUS current
			DESCRIPTION
				"Output power level for the radio in Mw."
			::= { wsCcRfRadioStatusEntry 8 }


		-- 1.3.6.1.4.1.388.14.3.2.1.11.11.1.9
		wsCcRfRadioStatusAssociatedMus OBJECT-TYPE
			SYNTAX Integer32
			MAX-ACCESS read-only
			STATUS current
			DESCRIPTION
				"Number of associated MUs."
			::= { wsCcRfRadioStatusEntry 9 }


		-- 1.3.6.1.4.1.388.14.3.2.1.11.11.1.10
		wsCcRfRadioStatusLastAdoption OBJECT-TYPE
			SYNTAX TimeTicks
			MAX-ACCESS read-only
			STATUS current
			DESCRIPTION
				"Timeticks since radio adoption time"
			::= { wsCcRfRadioStatusEntry 10 }


		-- 1.3.6.1.4.1.388.14.3.2.1.11.11.1.11
		wsCcRfRadioStatusShortSlotTime OBJECT-TYPE
			SYNTAX Integer32
			MAX-ACCESS read-only
			STATUS current
			DESCRIPTION
				"Indicates the 802.11g short-slot time on the radio"
			::= { wsCcRfRadioStatusEntry 11 }


		-- 1.3.6.1.4.1.388.14.3.2.1.11.11.1.12
		wsCcRfRadioStatusVlanTag OBJECT-TYPE
			SYNTAX Unsigned32
			MAX-ACCESS read-only
			STATUS current
			DESCRIPTION
				"The VLAN tag using which the switch is
				communicating with the radio"
			::= { wsCcRfRadioStatusEntry 12 }


		-- 1.3.6.1.4.1.388.14.3.2.1.11.11.1.13
		wsCcRfRadioStatusCfgMethod OBJECT-TYPE
			SYNTAX INTEGER
				{
				userConfigured(1),
				switchConfigured(2)
				}
			MAX-ACCESS read-only
			STATUS deprecated
			DESCRIPTION
				"The radio can be configured by user before being adopted
				or by the switch while adoption."
			::= { wsCcRfRadioStatusEntry 13 }


-- 802.1x Port Authentication is used to provide
-- security and authentication of all wired clients on
-- a network. The WS 2000 supports 802.1x port
-- authentication for the AP 300 Access Ports connected
-- to it. It uses a username and password for all ports
-- that can be configured from the wireless switch.
		-- 1.3.6.1.4.1.388.14.3.2.1.11.12
		wsCcRf802dt1xRadioAuth OBJECT IDENTIFIER ::= { wsCcRfRadio 12 }


		-- 1.3.6.1.4.1.388.14.3.2.1.11.12.1
		wsCcRf802dt1xRadioAuthLogin OBJECT-TYPE
			SYNTAX DisplayString (SIZE (1..64))
			MAX-ACCESS read-write
			STATUS current
			DESCRIPTION
				"802.1x Port Authentication username."
			::= { wsCcRf802dt1xRadioAuth 1 }


		-- 1.3.6.1.4.1.388.14.3.2.1.11.12.2
		wsCcRf802dt1xRadioAuthPass OBJECT-TYPE
			SYNTAX Password
			MAX-ACCESS read-write
			STATUS current
			DESCRIPTION
				"802.1x Port Authentication password."
			::= { wsCcRf802dt1xRadioAuth 2 }


		-- 1.3.6.1.4.1.388.14.3.2.1.11.12.3
		wsCcRf802dt1xRadioAuthSetRadio OBJECT-TYPE
			SYNTAX DoActionNow
			MAX-ACCESS read-write
			STATUS current
			DESCRIPTION
				"Set the username and password stored in
				wsCcRf802dt1xRadioAuthLogin and wsCcRf802dt1xRadioAuthPass
				on all radios adopted by the switch."
			::= { wsCcRf802dt1xRadioAuth 3 }


		-- 1.3.6.1.4.1.388.14.3.2.1.11.13
		wsCcRfRadioHealingModeCnt OBJECT-TYPE
			SYNTAX Integer32
			MAX-ACCESS read-only
			STATUS current
			DESCRIPTION
				"Description."
			::= { wsCcRfRadio 13 }


		-- 1.3.6.1.4.1.388.14.3.2.1.11.14
		wsCcRfRadioNormalModeCnt OBJECT-TYPE
			SYNTAX Integer32
			MAX-ACCESS read-write
			STATUS current
			DESCRIPTION
				"Description."
			::= { wsCcRfRadio 14 }


		-- 1.3.6.1.4.1.388.14.3.2.1.11.15
		wsCcRfRadioConfiguredCnt OBJECT-TYPE
			SYNTAX Unsigned32
			MAX-ACCESS read-only
			STATUS current
			DESCRIPTION
				"Number of configured radios. This is a count of the number of rows in wsCcRfRadioTable."
			::= { wsCcRfRadio 15 }


		-- 1.3.6.1.4.1.388.14.3.2.1.12
		wsCcRfMus OBJECT IDENTIFIER ::= { wsCcRfMIB 12 }


		-- 1.3.6.1.4.1.388.14.3.2.1.12.1
		wsCcRfMuCnt OBJECT-TYPE
			SYNTAX Unsigned32
			MAX-ACCESS read-only
			STATUS current
			DESCRIPTION
				"Number of rows in the wsCcRfMuTable "
			::= { wsCcRfMus 1 }


		-- 1.3.6.1.4.1.388.14.3.2.1.12.2
		wsCcRfMuLastMac OBJECT-TYPE
			SYNTAX PhysAddress
			MAX-ACCESS read-only
			STATUS current
			DESCRIPTION
				"This scalar records the MAC address of the most
				recent mu to be associated/disassociated."
			::= { wsCcRfMus 2 }


		-- 1.3.6.1.4.1.388.14.3.2.1.12.3
		wsCcRfMuTable OBJECT-TYPE
			SYNTAX SEQUENCE OF WsCcRfMuEntry
			MAX-ACCESS not-accessible
			STATUS current
			DESCRIPTION
				"This table describes general information about
				each MU serviced by the switch."
			::= { wsCcRfMus 3 }


		-- 1.3.6.1.4.1.388.14.3.2.1.12.3.1
		wsCcRfMuEntry OBJECT-TYPE
			SYNTAX WsCcRfMuEntry
			MAX-ACCESS not-accessible
			STATUS current
			DESCRIPTION
				" "
			INDEX { wsCcRfMuMac }
			::= { wsCcRfMuTable 1 }


		WsCcRfMuEntry ::=
			SEQUENCE {
				wsCcRfMuMac
					PhysAddress,
				wsCcRfMuWlanIndex
					Integer32,
				wsCcRfMuRadioIndex
					Integer32,
				wsCcRfMuVlanIndex
					Unsigned32,
				wsCcRfMuKeyIndex
					Unsigned32,
				wsCcRfMuIpAddr
					IpAddress,
				wsCcRfMuBSS
					PhysAddress,
				wsCcRfMuAuthMethod
					AuthType,
				wsCcRfMuEncMethod
					EncType,
				wsCcRfMuRadioType
					RadioType,
				wsCcRfMuPowerMode
					INTEGER,
				wsCcRfMuSupportedRates
					TransmitRate,
				wsCcRfMuVoice
					INTEGER,
				wsCcRfMuIsDataReady
					TruthValue,
				wsCcRfMuRogueApEna
					TruthValue,
				wsCcRfMuIsWmm
					TruthValue,
				wsCcRfMuRoamCount
					Unsigned32,
				wsCcRfMuLastHeard
					TimeTicks,
				wsCcRfMuDisassociateNow
					DoActionNow,
				wsCcRfMuTunnelIndex
					INTEGER,
				wsCcRfMuQosInfo
					INTEGER
			 }

		-- 1.3.6.1.4.1.388.14.3.2.1.12.3.1.1
		wsCcRfMuMac OBJECT-TYPE
			SYNTAX PhysAddress
			MAX-ACCESS read-only
			STATUS current
			DESCRIPTION
				"MAC address of the MU."
			::= { wsCcRfMuEntry 1 }


		-- 1.3.6.1.4.1.388.14.3.2.1.12.3.1.2
		wsCcRfMuWlanIndex OBJECT-TYPE
			SYNTAX Integer32 (1..64)
			MAX-ACCESS read-only
			STATUS current
			DESCRIPTION
				"(Reserved for future implementation)."
			::= { wsCcRfMuEntry 2 }


		-- 1.3.6.1.4.1.388.14.3.2.1.12.3.1.3
		wsCcRfMuRadioIndex OBJECT-TYPE
			SYNTAX Integer32
			MAX-ACCESS read-only
			STATUS current
			DESCRIPTION
				"The index of the entry in the wsCcRfRadioTable to
				which this MU is associated."
			::= { wsCcRfMuEntry 3 }


		-- 1.3.6.1.4.1.388.14.3.2.1.12.3.1.4
		wsCcRfMuVlanIndex OBJECT-TYPE
			SYNTAX Unsigned32 (0..4096)
			MAX-ACCESS read-only
			STATUS current
			DESCRIPTION
				"The VLAN that this MU is assigned to."
			::= { wsCcRfMuEntry 4 }


		-- 1.3.6.1.4.1.388.14.3.2.1.12.3.1.5
		wsCcRfMuKeyIndex OBJECT-TYPE
			SYNTAX Unsigned32 (0..3)
			MAX-ACCESS read-only
			STATUS current
			DESCRIPTION
				"The key index using which the MU is sending us frames. Useful
				when pre-shared keys are used with WEP, as we will know if this
				MU is "
			::= { wsCcRfMuEntry 5 }


		-- 1.3.6.1.4.1.388.14.3.2.1.12.3.1.6
		wsCcRfMuIpAddr OBJECT-TYPE
			SYNTAX IpAddress
			MAX-ACCESS read-only
			STATUS current
			DESCRIPTION
				"IP address of the MU."
			::= { wsCcRfMuEntry 6 }


		-- 1.3.6.1.4.1.388.14.3.2.1.12.3.1.7
		wsCcRfMuBSS OBJECT-TYPE
			SYNTAX PhysAddress
			MAX-ACCESS read-only
			STATUS current
			DESCRIPTION
				"The BSSID that this MU is associated with."
			::= { wsCcRfMuEntry 7 }


		-- 1.3.6.1.4.1.388.14.3.2.1.12.3.1.8
		wsCcRfMuAuthMethod OBJECT-TYPE
			SYNTAX AuthType
			MAX-ACCESS read-only
			STATUS current
			DESCRIPTION
				"Authentication method implemented by the MU."
			::= { wsCcRfMuEntry 8 }


		-- 1.3.6.1.4.1.388.14.3.2.1.12.3.1.9
		wsCcRfMuEncMethod OBJECT-TYPE
			SYNTAX EncType
			MAX-ACCESS read-only
			STATUS current
			DESCRIPTION
				"Encryption method implemented by the MU."
			::= { wsCcRfMuEntry 9 }


		-- 1.3.6.1.4.1.388.14.3.2.1.12.3.1.10
		wsCcRfMuRadioType OBJECT-TYPE
			SYNTAX RadioType
			MAX-ACCESS read-only
			STATUS current
			DESCRIPTION
				"Radio type of the MU."
			::= { wsCcRfMuEntry 10 }


		-- 1.3.6.1.4.1.388.14.3.2.1.12.3.1.11
		wsCcRfMuPowerMode OBJECT-TYPE
			SYNTAX INTEGER
				{
				continuousAccessMode(1),
				powerSavePolling(2)
				}
			MAX-ACCESS read-only
			STATUS current
			DESCRIPTION
				"Power-mode implemented by the MU.

				A MU's status will constantly switch between PSP and
				CAM mode when it is in PSP mode.
				 "
			::= { wsCcRfMuEntry 11 }


		-- 1.3.6.1.4.1.388.14.3.2.1.12.3.1.12
		wsCcRfMuSupportedRates OBJECT-TYPE
			SYNTAX TransmitRate
			MAX-ACCESS read-only
			STATUS current
			DESCRIPTION
				"A bit-mask of rates supported by this MU."
			::= { wsCcRfMuEntry 12 }


		-- 1.3.6.1.4.1.388.14.3.2.1.12.3.1.13
		wsCcRfMuVoice OBJECT-TYPE
			SYNTAX INTEGER
				{
				data(1),
				voice(2)
				}
			MAX-ACCESS read-only
			STATUS current
			DESCRIPTION
				"Whether this MU has registered itself as voice-capable."
			::= { wsCcRfMuEntry 13 }


		-- 1.3.6.1.4.1.388.14.3.2.1.12.3.1.14
		wsCcRfMuIsDataReady OBJECT-TYPE
			SYNTAX TruthValue
			MAX-ACCESS read-only
			STATUS current
			DESCRIPTION
				"This value is true if the wireless switch is ready to
				forward/switch packets to/from this MU,
				(internally called the 'data ready' state).
				Otherwise this value is false."
			::= { wsCcRfMuEntry 14 }


		-- 1.3.6.1.4.1.388.14.3.2.1.12.3.1.15
		wsCcRfMuRogueApEna OBJECT-TYPE
			SYNTAX TruthValue
			MAX-ACCESS read-only
			STATUS current
			DESCRIPTION
				"If true, this MU supports Rogue AP detection assist
				algorithm."
			::= { wsCcRfMuEntry 15 }


		-- 1.3.6.1.4.1.388.14.3.2.1.12.3.1.16
		wsCcRfMuIsWmm OBJECT-TYPE
			SYNTAX TruthValue
			MAX-ACCESS read-only
			STATUS current
			DESCRIPTION
				"If the MU is using WMM"
			::= { wsCcRfMuEntry 16 }


		-- 1.3.6.1.4.1.388.14.3.2.1.12.3.1.17
		wsCcRfMuRoamCount OBJECT-TYPE
			SYNTAX Unsigned32
			MAX-ACCESS read-only
			STATUS current
			DESCRIPTION
				"Number of times the mu has roamed without de-authentication."
			::= { wsCcRfMuEntry 17 }


		-- 1.3.6.1.4.1.388.14.3.2.1.12.3.1.18
		wsCcRfMuLastHeard OBJECT-TYPE
			SYNTAX TimeTicks
			MAX-ACCESS read-only
			STATUS current
			DESCRIPTION
				"Timeticks since last heard from MU. "
			::= { wsCcRfMuEntry 18 }


		-- 1.3.6.1.4.1.388.14.3.2.1.12.3.1.19
		wsCcRfMuDisassociateNow OBJECT-TYPE
			SYNTAX DoActionNow
			MAX-ACCESS read-write
			STATUS current
			DESCRIPTION
				"Setting this value to one initiates the action to
				disassociate the MU."
			::= { wsCcRfMuEntry 19 }


		-- 1.3.6.1.4.1.388.14.3.2.1.12.3.1.20
		wsCcRfMuTunnelIndex OBJECT-TYPE
			SYNTAX INTEGER (0..32)
			MAX-ACCESS read-only
			STATUS current
			DESCRIPTION
				"The tunnel identifier for this MU."
			::= { wsCcRfMuEntry 20 }


-- Shows the UAPSD parameters for a given MU.  This field has the following bit values :
--
-- Bit 0    - UAPSD enabled for Voice AC
-- Bit 1    - UAPSD enabled for Video AC
-- Bit 2    - UAPSD enabled for Best-Effort AC
-- Bit 3    - UAPSD enabled for Background AC
-- Bits 4-5 - UAPSD service period ( 00 - unlimited, 01 - 2 packets, 10 - 4 packets, 11 - 6 packets ).
--
		-- 1.3.6.1.4.1.388.14.3.2.1.12.3.1.21
		wsCcRfMuQosInfo OBJECT-TYPE
			SYNTAX INTEGER (0..63)
			MAX-ACCESS read-only
			STATUS current
			DESCRIPTION
				"UAPSD parameters for a given MU. Has the following bit values :

				Bit  0   - UAPSD enabled for Voice AC
				Bit  1   - UAPSD enabled for Video AC
				Bit  2   - UAPSD enabled for Best-Effort AC
				Bit  3   - UAPSD enabled for Background AC
				Bits 4-5 - UAPSD service period ( 00 - unlimited, 01 - 2 packets, 10 - 4 packets, 11 - 6 packets ).


				"
			::= { wsCcRfMuEntry 21 }


		-- 1.3.6.1.4.1.388.14.3.2.1.12.4
		wsCcRfMuHistoryTable OBJECT-TYPE
			SYNTAX SEQUENCE OF WsCcRfMuHistoryEntry
			MAX-ACCESS not-accessible
			STATUS deprecated
			DESCRIPTION
				"Description."
			::= { wsCcRfMus 4 }


		-- 1.3.6.1.4.1.388.14.3.2.1.12.4.1
		wsCcRfMuHistoryEntry OBJECT-TYPE
			SYNTAX WsCcRfMuHistoryEntry
			MAX-ACCESS not-accessible
			STATUS deprecated
			DESCRIPTION
				"Description."
			INDEX { wsCcRfMuHistoryIndex, wsCcRfMuHistoryMac }
			::= { wsCcRfMuHistoryTable 1 }


		WsCcRfMuHistoryEntry ::=
			SEQUENCE {
				wsCcRfMuHistoryIndex
					INTEGER,
				wsCcRfMuHistoryMac
					PhysAddress,
				wsCcRfMuHistoryRadioIndex
					INTEGER,
				wsCcRfMuHistoryWlanIndex
					INTEGER,
				wsCcRfMuHistoryTimestamp
					Unsigned32,
				wsCcRfMuHistoryEvent
					INTEGER
			 }

		-- 1.3.6.1.4.1.388.14.3.2.1.12.4.1.1
		wsCcRfMuHistoryIndex OBJECT-TYPE
			SYNTAX INTEGER (1..255)
			MAX-ACCESS read-only
			STATUS deprecated
			DESCRIPTION
				"Simple Index"
			::= { wsCcRfMuHistoryEntry 1 }


		-- 1.3.6.1.4.1.388.14.3.2.1.12.4.1.2
		wsCcRfMuHistoryMac OBJECT-TYPE
			SYNTAX PhysAddress
			MAX-ACCESS read-only
			STATUS deprecated
			DESCRIPTION
				"MAC address of MU"
			::= { wsCcRfMuHistoryEntry 2 }


		-- 1.3.6.1.4.1.388.14.3.2.1.12.4.1.3
		wsCcRfMuHistoryRadioIndex OBJECT-TYPE
			SYNTAX INTEGER (1..2000)
			MAX-ACCESS read-only
			STATUS deprecated
			DESCRIPTION
				"Index of Radio"
			::= { wsCcRfMuHistoryEntry 3 }


		-- 1.3.6.1.4.1.388.14.3.2.1.12.4.1.4
		wsCcRfMuHistoryWlanIndex OBJECT-TYPE
			SYNTAX INTEGER (1..32)
			MAX-ACCESS read-only
			STATUS deprecated
			DESCRIPTION
				"Index of Wlan"
			::= { wsCcRfMuHistoryEntry 4 }


		-- 1.3.6.1.4.1.388.14.3.2.1.12.4.1.5
		wsCcRfMuHistoryTimestamp OBJECT-TYPE
			SYNTAX Unsigned32
			MAX-ACCESS read-write
			STATUS deprecated
			DESCRIPTION
				"The event happened wsCcRfMuHistoryTimestamp seconds ago"
			::= { wsCcRfMuHistoryEntry 5 }


		-- 1.3.6.1.4.1.388.14.3.2.1.12.4.1.6
		wsCcRfMuHistoryEvent OBJECT-TYPE
			SYNTAX INTEGER
				{
				adoption(1),
				disassociation(2),
				timeout(3)
				}
			MAX-ACCESS read-write
			STATUS deprecated
			DESCRIPTION
				"Event: Adoption, disassociation or timeout."
			::= { wsCcRfMuHistoryEntry 6 }


		-- 1.3.6.1.4.1.388.14.3.2.1.12.5
		wsCfRfMuProbeHistoryTable OBJECT-TYPE
			SYNTAX SEQUENCE OF WsCfRfMuProbeHistoryEntry
			MAX-ACCESS not-accessible
			STATUS deprecated
			DESCRIPTION
				"Description."
			::= { wsCcRfMus 5 }


		-- 1.3.6.1.4.1.388.14.3.2.1.12.5.1
		wsCfRfMuProbeHistoryEntry OBJECT-TYPE
			SYNTAX WsCfRfMuProbeHistoryEntry
			MAX-ACCESS not-accessible
			STATUS deprecated
			DESCRIPTION
				"Description."
			INDEX { wsCfRfMuProbeHistoryMac, wsCfRfMuProbeHistoryIndex }
			::= { wsCfRfMuProbeHistoryTable 1 }


		WsCfRfMuProbeHistoryEntry ::=
			SEQUENCE {
				wsCfRfMuProbeHistoryMac
					PhysAddress,
				wsCfRfMuProbeHistoryIndex
					INTEGER,
				wsCfRfMuProbeHistoryTimeticks
					Unsigned32,
				wsCfRfMuProbeHistorySignalStrength
					Integer32,
				wsCfRfMuProbeHeardRadio
					INTEGER
			 }

		-- 1.3.6.1.4.1.388.14.3.2.1.12.5.1.1
		wsCfRfMuProbeHistoryMac OBJECT-TYPE
			SYNTAX PhysAddress
			MAX-ACCESS read-only
			STATUS deprecated
			DESCRIPTION
				"Description."
			::= { wsCfRfMuProbeHistoryEntry 1 }


		-- 1.3.6.1.4.1.388.14.3.2.1.12.5.1.2
		wsCfRfMuProbeHistoryIndex OBJECT-TYPE
			SYNTAX INTEGER (1..255)
			MAX-ACCESS read-only
			STATUS deprecated
			DESCRIPTION
				"Simple Index"
			::= { wsCfRfMuProbeHistoryEntry 2 }


		-- 1.3.6.1.4.1.388.14.3.2.1.12.5.1.4
		wsCfRfMuProbeHistoryTimeticks OBJECT-TYPE
			SYNTAX Unsigned32
			MAX-ACCESS read-only
			STATUS deprecated
			DESCRIPTION
				"Date and Time"
			::= { wsCfRfMuProbeHistoryEntry 4 }


		-- 1.3.6.1.4.1.388.14.3.2.1.12.5.1.5
		wsCfRfMuProbeHistorySignalStrength OBJECT-TYPE
			SYNTAX Integer32
			MAX-ACCESS read-only
			STATUS deprecated
			DESCRIPTION
				"It is not yet decided if this will be reported in db or rssi"
			::= { wsCfRfMuProbeHistoryEntry 5 }


		-- 1.3.6.1.4.1.388.14.3.2.1.12.5.1.6
		wsCfRfMuProbeHeardRadio OBJECT-TYPE
			SYNTAX INTEGER (1..1000)
			MAX-ACCESS read-only
			STATUS deprecated
			DESCRIPTION
				"Index of the heard radio."
			::= { wsCfRfMuProbeHistoryEntry 6 }


		-- 1.3.6.1.4.1.388.14.3.2.1.12.6
		wsCcRfMuProbeRequestsAgeHeardOut OBJECT-TYPE
			SYNTAX INTEGER (15..900)
			UNITS "seconds"
			MAX-ACCESS read-write
			STATUS current
			DESCRIPTION
				"Range is from 15 secs - 15 minutes"
			::= { wsCcRfMus 6 }


		-- 1.3.6.1.4.1.388.14.3.2.1.12.7
		wsCcRfMuHistoryEnable OBJECT-TYPE
			SYNTAX INTEGER
				{
				enable(1),
				disable(2)
				}
			MAX-ACCESS read-write
			STATUS current
			DESCRIPTION
				"Enable / disable MU history data collection"
			::= { wsCcRfMus 7 }


		-- 1.3.6.1.4.1.388.14.3.2.1.12.8
		wsCcRfMuHistoryClear OBJECT-TYPE
			SYNTAX TruthValue
			MAX-ACCESS read-write
			STATUS current
			DESCRIPTION
				"Clears the entries in the MU History table."
			::= { wsCcRfMus 8 }


		-- 1.3.6.1.4.1.388.14.3.2.1.12.9
		wsCcRfMuProbeHistoryEnable OBJECT-TYPE
			SYNTAX INTEGER
				{
				enable(1),
				disable(2)
				}
			MAX-ACCESS read-write
			STATUS current
			DESCRIPTION
				"Enable / disable MU probe history data collection"
			::= { wsCcRfMus 9 }


		-- 1.3.6.1.4.1.388.14.3.2.1.12.10
		wsCcRfMuProbeHistoryClear OBJECT-TYPE
			SYNTAX TruthValue
			MAX-ACCESS read-write
			STATUS current
			DESCRIPTION
				"Clears the entries in the MU Probe History table."
			::= { wsCcRfMus 10 }


		-- 1.3.6.1.4.1.388.14.3.2.1.12.11
		wsCcRfMuProbeConfigTable OBJECT-TYPE
			SYNTAX SEQUENCE OF WsCcRfMuProbeConfigEntry
			MAX-ACCESS not-accessible
			STATUS current
			DESCRIPTION
				"Table to configure MUs that have to be tracked for probe history status"
			::= { wsCcRfMus 11 }


		-- 1.3.6.1.4.1.388.14.3.2.1.12.11.1
		wsCcRfMuProbeConfigEntry OBJECT-TYPE
			SYNTAX WsCcRfMuProbeConfigEntry
			MAX-ACCESS not-accessible
			STATUS current
			DESCRIPTION
				"Description."
			INDEX { wsCcRfMuProbeConfigIndex }
			::= { wsCcRfMuProbeConfigTable 1 }


		WsCcRfMuProbeConfigEntry ::=
			SEQUENCE {
				wsCcRfMuProbeConfigIndex
					INTEGER,
				wsCcRfMuProbeConfigMac
					PhysAddress,
				wsCcRfMuProbeConfigStatus
					INTEGER
			 }

		-- 1.3.6.1.4.1.388.14.3.2.1.12.11.1.1
		wsCcRfMuProbeConfigIndex OBJECT-TYPE
			SYNTAX INTEGER (1..100)
			MAX-ACCESS accessible-for-notify
			STATUS current
			DESCRIPTION
				"Simple index"
			::= { wsCcRfMuProbeConfigEntry 1 }


		-- 1.3.6.1.4.1.388.14.3.2.1.12.11.1.2
		wsCcRfMuProbeConfigMac OBJECT-TYPE
			SYNTAX PhysAddress
			MAX-ACCESS read-write
			STATUS current
			DESCRIPTION
				"MAc address of MU to be tracked"
			::= { wsCcRfMuProbeConfigEntry 2 }


		-- 1.3.6.1.4.1.388.14.3.2.1.12.11.1.3
		wsCcRfMuProbeConfigStatus OBJECT-TYPE
			SYNTAX INTEGER
				{
				inUse(1),
				notInUse(2)
				}
			MAX-ACCESS read-write
			STATUS current
			DESCRIPTION
				"Set tracking on or off for particular MU"
			::= { wsCcRfMuProbeConfigEntry 3 }


		-- 1.3.6.1.4.1.388.14.3.2.1.12.12
		wsCcRfMuProbeStatusTable OBJECT-TYPE
			SYNTAX SEQUENCE OF WsCcRfMuProbeStatusEntry
			MAX-ACCESS not-accessible
			STATUS current
			DESCRIPTION
				"Status of MU probe history"
			::= { wsCcRfMus 12 }


		-- 1.3.6.1.4.1.388.14.3.2.1.12.12.1
		wsCcRfMuProbeStatusEntry OBJECT-TYPE
			SYNTAX WsCcRfMuProbeStatusEntry
			MAX-ACCESS not-accessible
			STATUS current
			DESCRIPTION
				"Description."
			INDEX { wsCcRfMuProbeConfigIndex, wsCcRfMuProbeStatusIndex }
			::= { wsCcRfMuProbeStatusTable 1 }


		WsCcRfMuProbeStatusEntry ::=
			SEQUENCE {
				wsCcRfMuProbeStatusIndex
					INTEGER,
				wsCcRfMuProbeStatusMac
					PhysAddress,
				wsCcRfMuProbeStatusTimeticks
					Unsigned32,
				wsCcRfMuProbeStatusSignalStrength
					Integer32,
				wsCcRfMuProbeStatusHeardRadio
					INTEGER
			 }

		-- 1.3.6.1.4.1.388.14.3.2.1.12.12.1.1
		wsCcRfMuProbeStatusIndex OBJECT-TYPE
			SYNTAX INTEGER (1..255)
			MAX-ACCESS read-only
			STATUS current
			DESCRIPTION
				"Simple Index"
			::= { wsCcRfMuProbeStatusEntry 1 }


		-- 1.3.6.1.4.1.388.14.3.2.1.12.12.1.2
		wsCcRfMuProbeStatusMac OBJECT-TYPE
			SYNTAX PhysAddress
			MAX-ACCESS read-only
			STATUS current
			DESCRIPTION
				"Mac Address"
			::= { wsCcRfMuProbeStatusEntry 2 }


		-- 1.3.6.1.4.1.388.14.3.2.1.12.12.1.4
		wsCcRfMuProbeStatusTimeticks OBJECT-TYPE
			SYNTAX Unsigned32
			MAX-ACCESS read-only
			STATUS current
			DESCRIPTION
				"Date and Time"
			::= { wsCcRfMuProbeStatusEntry 4 }


		-- 1.3.6.1.4.1.388.14.3.2.1.12.12.1.5
		wsCcRfMuProbeStatusSignalStrength OBJECT-TYPE
			SYNTAX Integer32
			MAX-ACCESS read-only
			STATUS current
			DESCRIPTION
				"It is not yet decided if this will be reported in db or rssi"
			::= { wsCcRfMuProbeStatusEntry 5 }


		-- 1.3.6.1.4.1.388.14.3.2.1.12.12.1.6
		wsCcRfMuProbeStatusHeardRadio OBJECT-TYPE
			SYNTAX INTEGER (1..1000)
			MAX-ACCESS read-only
			STATUS current
			DESCRIPTION
				"Index of the heard radio."
			::= { wsCcRfMuProbeStatusEntry 6 }


		-- 1.3.6.1.4.1.388.14.3.2.1.12.13
		wsCcRfMuHistoryStatusMac OBJECT-TYPE
			SYNTAX PhysAddress
			MAX-ACCESS read-write
			STATUS current
			DESCRIPTION
				"The Mac addres which the user want to view the history status"
			::= { wsCcRfMus 13 }


		-- 1.3.6.1.4.1.388.14.3.2.1.12.14
		wsCcRfMuHistoryStatusTable OBJECT-TYPE
			SYNTAX SEQUENCE OF WsCcRfMuHistoryStatusEntry
			MAX-ACCESS not-accessible
			STATUS current
			DESCRIPTION
				"wsCcRfMuHistoryStatusTable, the procedure to view the table will be:
				1.set the Mac address you are interested in wsCcRfMuHistoryStatusMac
				2.do a walk of the table, and it will show you the history of that MU"
			::= { wsCcRfMus 14 }


		-- 1.3.6.1.4.1.388.14.3.2.1.12.14.1
		wsCcRfMuHistoryStatusEntry OBJECT-TYPE
			SYNTAX WsCcRfMuHistoryStatusEntry
			MAX-ACCESS not-accessible
			STATUS current
			DESCRIPTION
				"wsCcRfMuHistoryStatusEntry"
			INDEX { wsCcRfMuHistoryStatusIndex }
			::= { wsCcRfMuHistoryStatusTable 1 }


		WsCcRfMuHistoryStatusEntry ::=
			SEQUENCE {
				wsCcRfMuHistoryStatusIndex
					INTEGER,
				wsCcRfMuHistoryStatusRadioIndex
					INTEGER,
				wsCcRfMuHistoryStatusWlanIndex
					INTEGER,
				wsCcRfMuHistoryStatusTimestamp
					Unsigned32,
				wsCcRfMuHistoryStatusEvent
					INTEGER
			 }

		-- 1.3.6.1.4.1.388.14.3.2.1.12.14.1.1
		wsCcRfMuHistoryStatusIndex OBJECT-TYPE
			SYNTAX INTEGER (1..10)
			MAX-ACCESS accessible-for-notify
			STATUS current
			DESCRIPTION
				"Simple index of wsCcRfMuHistoryStatusTable"
			::= { wsCcRfMuHistoryStatusEntry 1 }


		-- 1.3.6.1.4.1.388.14.3.2.1.12.14.1.2
		wsCcRfMuHistoryStatusRadioIndex OBJECT-TYPE
			SYNTAX INTEGER (1..8192)
			MAX-ACCESS read-only
			STATUS current
			DESCRIPTION
				"Index of Radio"
			::= { wsCcRfMuHistoryStatusEntry 2 }


		-- 1.3.6.1.4.1.388.14.3.2.1.12.14.1.3
		wsCcRfMuHistoryStatusWlanIndex OBJECT-TYPE
			SYNTAX INTEGER (1..256)
			MAX-ACCESS read-only
			STATUS current
			DESCRIPTION
				"Index of Wlan"
			::= { wsCcRfMuHistoryStatusEntry 3 }


		-- 1.3.6.1.4.1.388.14.3.2.1.12.14.1.4
		wsCcRfMuHistoryStatusTimestamp OBJECT-TYPE
			SYNTAX Unsigned32
			MAX-ACCESS read-only
			STATUS current
			DESCRIPTION
				"The event happened wsCcRfMuHistoryTimestamp seconds ago"
			::= { wsCcRfMuHistoryStatusEntry 4 }


		-- 1.3.6.1.4.1.388.14.3.2.1.12.14.1.5
		wsCcRfMuHistoryStatusEvent OBJECT-TYPE
			SYNTAX INTEGER
				{
				adoption(1),
				disassociation(2),
				timeout(3)
				}
			MAX-ACCESS read-only
			STATUS current
			DESCRIPTION
				"Event: Adoption, disassociation or timeout"
			::= { wsCcRfMuHistoryStatusEntry 5 }


		-- 1.3.6.1.4.1.388.14.3.2.1.14
		wsCcRfWlan OBJECT IDENTIFIER ::= { wsCcRfMIB 14 }


		-- 1.3.6.1.4.1.388.14.3.2.1.14.1
		wsCcRfWlanTable OBJECT-TYPE
			SYNTAX SEQUENCE OF WsCcRfWlanEntry
			MAX-ACCESS not-accessible
			STATUS current
			DESCRIPTION
				"Table of wireless LANs on the switch."
			::= { wsCcRfWlan 1 }


		-- 1.3.6.1.4.1.388.14.3.2.1.14.1.1
		wsCcRfWlanEntry OBJECT-TYPE
			SYNTAX WsCcRfWlanEntry
			MAX-ACCESS not-accessible
			STATUS current
			DESCRIPTION
				" "
			INDEX { wsCcRfWlanIndex }
			::= { wsCcRfWlanTable 1 }


		WsCcRfWlanEntry ::=
			SEQUENCE {
				wsCcRfWlanIndex
					Integer32,
				wsCcRfWlanEnable
					StaticRowEnable,
				wsCcRfWlanDescr
					DisplayString,
				wsCcRfWlanEssid
					DisplayString,
				wsCcRfWlanVlan
					Unsigned32,
				wsCcRfWlanDisallowMuToMu
					TruthValue,
				wsCcRfWlanSecBeacon
					TruthValue,
				wsCcRfWlanVoicePrioritization
					TruthValue,
				wsCcRfWlanAnswerBroadcastEss
					TruthValue,
				wsCcRfWlanMulticastAddr1
					PhysAddress,
				wsCcRfWlanMulticastAddr2
					PhysAddress,
				wsCcRfWlanWeight
					Integer32,
				wsCcRfWlanWmmEnable
					TruthValue,
				wsCcRfWlanSvpEnable
					TruthValue,
				wsCcRfWlanAuthentication
					AuthType,
				wsCcRfWlanEncryptionMap
					EncMap,
				wsCcRfWlanBcastEnc
					EncType,
				wsCcRfWlanNumRadiosAdopted
					Unsigned32,
				wsCcRfWlanUseDscp
					TruthValue,
				wsCcRfWlanMuIdleTime
					Integer32,
				wsCcRfWlanMobilityEnable
					TruthValue,
				wsCcRfWlanGRETunnelIdx
					INTEGER,
				wsCcRfWlanGRETunnelGatewayIp
					IpAddress,
				wsCcRfWlanGRETunnelGatewayMask
					IpAddress,
				wsCcRfWlanMuToMu
					INTEGER,
				wsCcRfWlanQosPrioritization
					INTEGER,
				wsCcRfWlanDynamicVlanAssignment
					TruthValue,
				wsCcRfWlanAccountingType
					INTEGER,
				wsCcRfWlanSyslogServerIp
					IpAddress,
				wsCcRfWlanSyslogServerPort
					Unsigned32
			 }

		-- 1.3.6.1.4.1.388.14.3.2.1.14.1.1.1
		wsCcRfWlanIndex OBJECT-TYPE
			SYNTAX Integer32 (1..1001)
			MAX-ACCESS accessible-for-notify
			STATUS current
			DESCRIPTION
				"Simple index."
			::= { wsCcRfWlanEntry 1 }


		-- 1.3.6.1.4.1.388.14.3.2.1.14.1.1.2
		wsCcRfWlanEnable OBJECT-TYPE
			SYNTAX StaticRowEnable
			MAX-ACCESS read-write
			STATUS current
			DESCRIPTION
				"Enable/Disable wireless Lan.  If this wlan is
				referenced by wsCcRfRadioBssWlanMap, a set to
				disabled mode will fail."
			::= { wsCcRfWlanEntry 2 }


		-- 1.3.6.1.4.1.388.14.3.2.1.14.1.1.3
		wsCcRfWlanDescr OBJECT-TYPE
			SYNTAX DisplayString (SIZE (0..32))
			MAX-ACCESS read-write
			STATUS current
			DESCRIPTION
				"Description the Wlan."
			::= { wsCcRfWlanEntry 3 }


		-- 1.3.6.1.4.1.388.14.3.2.1.14.1.1.4
		wsCcRfWlanEssid OBJECT-TYPE
			SYNTAX DisplayString
			MAX-ACCESS read-write
			STATUS current
			DESCRIPTION
				"ESSID of the WLAN."
			::= { wsCcRfWlanEntry 4 }


		-- 1.3.6.1.4.1.388.14.3.2.1.14.1.1.5
		wsCcRfWlanVlan OBJECT-TYPE
			SYNTAX Unsigned32
			MAX-ACCESS read-write
			STATUS current
			DESCRIPTION
				"The Vlan this Wlan is associated with.

				If not associated with any Vlan, this value
				will be 0."
			::= { wsCcRfWlanEntry 5 }


		-- 1.3.6.1.4.1.388.14.3.2.1.14.1.1.6
		wsCcRfWlanDisallowMuToMu OBJECT-TYPE
			SYNTAX TruthValue
			MAX-ACCESS read-write
			STATUS deprecated
			DESCRIPTION
				"Set to true to prohibit MU-to-MU communication."
			::= { wsCcRfWlanEntry 6 }


		-- 1.3.6.1.4.1.388.14.3.2.1.14.1.1.7
		wsCcRfWlanSecBeacon OBJECT-TYPE
			SYNTAX TruthValue
			MAX-ACCESS read-write
			STATUS current
			DESCRIPTION
				"Enable the Secure Beacon checkbox to disallow the
				Access Port from broadcasting an ESSID in its
				beacons. This is a safeguard to prevent intruders
				from tapping into the WLAN. Consider this security
				measure for a private, corporate network."
			::= { wsCcRfWlanEntry 7 }


		-- 1.3.6.1.4.1.388.14.3.2.1.14.1.1.8
		wsCcRfWlanVoicePrioritization OBJECT-TYPE
			SYNTAX TruthValue
			MAX-ACCESS read-write
			STATUS current
			DESCRIPTION
				"Enable voice prioritization."
			::= { wsCcRfWlanEntry 8 }


		-- 1.3.6.1.4.1.388.14.3.2.1.14.1.1.9
		wsCcRfWlanAnswerBroadcastEss OBJECT-TYPE
			SYNTAX TruthValue
			MAX-ACCESS read-write
			STATUS current
			DESCRIPTION
				"Answer broadcast ESS."
			::= { wsCcRfWlanEntry 9 }


		-- 1.3.6.1.4.1.388.14.3.2.1.14.1.1.10
		wsCcRfWlanMulticastAddr1 OBJECT-TYPE
			SYNTAX PhysAddress
			MAX-ACCESS read-write
			STATUS current
			DESCRIPTION
				"Multicast address 1."
			::= { wsCcRfWlanEntry 10 }


		-- 1.3.6.1.4.1.388.14.3.2.1.14.1.1.11
		wsCcRfWlanMulticastAddr2 OBJECT-TYPE
			SYNTAX PhysAddress
			MAX-ACCESS read-write
			STATUS current
			DESCRIPTION
				"Multicast address 2."
			::= { wsCcRfWlanEntry 11 }


		-- 1.3.6.1.4.1.388.14.3.2.1.14.1.1.12
		wsCcRfWlanWeight OBJECT-TYPE
			SYNTAX Integer32
			MAX-ACCESS read-write
			STATUS deprecated
			DESCRIPTION
				"The weight to be used when QoS for all WLANs
				is set to weighted-round-robin.

				Note that the sum of all weights across all
				WLANs need not total 100.
				"
			::= { wsCcRfWlanEntry 12 }


		-- 1.3.6.1.4.1.388.14.3.2.1.14.1.1.13
		wsCcRfWlanWmmEnable OBJECT-TYPE
			SYNTAX TruthValue
			MAX-ACCESS read-write
			STATUS current
			DESCRIPTION
				"Enable/Disable WMM on this wireless LAN"
			::= { wsCcRfWlanEntry 13 }


		-- 1.3.6.1.4.1.388.14.3.2.1.14.1.1.14
		wsCcRfWlanSvpEnable OBJECT-TYPE
			SYNTAX TruthValue
			MAX-ACCESS read-write
			STATUS current
			DESCRIPTION
				"Enable/Disable support for Spectralink Voice Prioritization
				on this wireless LAN"
			::= { wsCcRfWlanEntry 14 }


		-- 1.3.6.1.4.1.388.14.3.2.1.14.1.1.15
		wsCcRfWlanAuthentication OBJECT-TYPE
			SYNTAX AuthType
			MAX-ACCESS read-write
			STATUS current
			DESCRIPTION
				"If auth802dot1xEap, additional EAP settings for this
				WLAN will be used from the matching entry in the wireless
				authentication.

				"
			::= { wsCcRfWlanEntry 15 }


		-- 1.3.6.1.4.1.388.14.3.2.1.14.1.1.16
		wsCcRfWlanEncryptionMap OBJECT-TYPE
			SYNTAX EncMap
			MAX-ACCESS read-write
			STATUS current
			DESCRIPTION
				"** this needs to be a bitmap of enc types **
				If cryptoWep64 or cryptoWep128, additional WEP
				settings for this WLAN will be used from the matching
				entry in the ccWlanCryptoWepTable.

				Likewise, if cryptoWpaTkip, use the settings in the
				matching entry in the ccWlanCryptoWpaTable.

				Likewise, if cryptoKeyguardMcm, use the settings in
				the matching entry in the ccWlanCryptoKeyguardTable."
			::= { wsCcRfWlanEntry 16 }


		-- 1.3.6.1.4.1.388.14.3.2.1.14.1.1.17
		wsCcRfWlanBcastEnc OBJECT-TYPE
			SYNTAX EncType
			MAX-ACCESS read-only
			STATUS current
			DESCRIPTION
				"The broadcast encryption type in use on a WLAN.
				In most cases it is same as the unicast encryption
				type. When multiple encryption types are supported
				(TKIP+CCMP) it is usually the lowest encryption
				type."
			::= { wsCcRfWlanEntry 17 }


		-- 1.3.6.1.4.1.388.14.3.2.1.14.1.1.18
		wsCcRfWlanNumRadiosAdopted OBJECT-TYPE
			SYNTAX Unsigned32
			MAX-ACCESS read-only
			STATUS current
			DESCRIPTION
				"Number of radios adopted."
			::= { wsCcRfWlanEntry 18 }


		-- 1.3.6.1.4.1.388.14.3.2.1.14.1.1.19
		wsCcRfWlanUseDscp OBJECT-TYPE
			SYNTAX TruthValue
			MAX-ACCESS read-write
			STATUS current
			DESCRIPTION
				"Use Dscp when tagged."
			::= { wsCcRfWlanEntry 19 }


		-- 1.3.6.1.4.1.388.14.3.2.1.14.1.1.20
		wsCcRfWlanMuIdleTime OBJECT-TYPE
			SYNTAX Integer32 (60..86400)
			UNITS "second"
			MAX-ACCESS read-write
			STATUS current
			DESCRIPTION
				"The number of seconds for which if the switch does
				not receive/send any data frames from/to an MU, it
				disassociates the MU. If an MU roams away from an
				access point without disassociating, this timeout
				helps the switch determine that the MU is gone, and
				clear resources allocated for that MU."
			::= { wsCcRfWlanEntry 20 }


		-- 1.3.6.1.4.1.388.14.3.2.1.14.1.1.21
		wsCcRfWlanMobilityEnable OBJECT-TYPE
			SYNTAX TruthValue
			MAX-ACCESS read-write
			STATUS current
			DESCRIPTION
				"Description."
			::= { wsCcRfWlanEntry 21 }


		-- 1.3.6.1.4.1.388.14.3.2.1.14.1.1.22
		wsCcRfWlanGRETunnelIdx OBJECT-TYPE
			SYNTAX INTEGER (0..32)
			MAX-ACCESS read-write
			STATUS current
			DESCRIPTION
				"Description."
			::= { wsCcRfWlanEntry 22 }


		-- 1.3.6.1.4.1.388.14.3.2.1.14.1.1.23
		wsCcRfWlanGRETunnelGatewayIp OBJECT-TYPE
			SYNTAX IpAddress
			MAX-ACCESS read-write
			STATUS current
			DESCRIPTION
				"Description."
			::= { wsCcRfWlanEntry 23 }


		-- 1.3.6.1.4.1.388.14.3.2.1.14.1.1.24
		wsCcRfWlanGRETunnelGatewayMask OBJECT-TYPE
			SYNTAX IpAddress
			MAX-ACCESS read-write
			STATUS current
			DESCRIPTION
				"Description."
			::= { wsCcRfWlanEntry 24 }


		-- 1.3.6.1.4.1.388.14.3.2.1.14.1.1.25
		wsCcRfWlanMuToMu OBJECT-TYPE
			SYNTAX INTEGER
				{
				drop(1),
				allow(2),
				switchToWired(3)
				}
			MAX-ACCESS read-write
			STATUS current
			DESCRIPTION
				"States the form of MU-to-MU communication, whether to drop,
				allow or switch to wired."
			::= { wsCcRfWlanEntry 25 }


		-- 1.3.6.1.4.1.388.14.3.2.1.14.1.1.26
		wsCcRfWlanQosPrioritization OBJECT-TYPE
			SYNTAX INTEGER
				{
				autoWmm(1),
				voice(2),
				video(3),
				normal(4),
				low(5)
				}
			MAX-ACCESS read-write
			STATUS current
			DESCRIPTION
				"Sets the prioritization of the WLAN for QoS purposes."
			::= { wsCcRfWlanEntry 26 }


		-- 1.3.6.1.4.1.388.14.3.2.1.14.1.1.27
		wsCcRfWlanDynamicVlanAssignment OBJECT-TYPE
			SYNTAX TruthValue
			MAX-ACCESS read-write
			STATUS current
			DESCRIPTION
				"Enables or disables dynamic VLAN assignment for the WLAN."
			::= { wsCcRfWlanEntry 27 }


		-- 1.3.6.1.4.1.388.14.3.2.1.14.1.1.28
		wsCcRfWlanAccountingType OBJECT-TYPE
			SYNTAX INTEGER
				{
				off(1),
				radius(2),
				syslog(3)
				}
			MAX-ACCESS read-write
			STATUS current
			DESCRIPTION
				"Indicates if the accounting type is Radius, Syslog or turned off."
			::= { wsCcRfWlanEntry 28 }


		-- 1.3.6.1.4.1.388.14.3.2.1.14.1.1.29
		wsCcRfWlanSyslogServerIp OBJECT-TYPE
			SYNTAX IpAddress
			MAX-ACCESS read-write
			STATUS current
			DESCRIPTION
				"IP Address of the Syslog server"
			::= { wsCcRfWlanEntry 29 }


		-- 1.3.6.1.4.1.388.14.3.2.1.14.1.1.30
		wsCcRfWlanSyslogServerPort OBJECT-TYPE
			SYNTAX Unsigned32 (1..65535)
			MAX-ACCESS read-write
			STATUS current
			DESCRIPTION
				"Port of the Syslog Server"
			::= { wsCcRfWlanEntry 30 }


		-- 1.3.6.1.4.1.388.14.3.2.1.14.2
		wsCcRfWlanAuth OBJECT IDENTIFIER ::= { wsCcRfWlan 2 }


		-- 1.3.6.1.4.1.388.14.3.2.1.14.2.1
		wsCcRfWlanAuthEapTable OBJECT-TYPE
			SYNTAX SEQUENCE OF WsCcRfWlanAuthEapEntry
			MAX-ACCESS not-accessible
			STATUS current
			DESCRIPTION
				"Table of EAP authentication settings for each WLAN."
			::= { wsCcRfWlanAuth 1 }


		-- 1.3.6.1.4.1.388.14.3.2.1.14.2.1.1
		wsCcRfWlanAuthEapEntry OBJECT-TYPE
			SYNTAX WsCcRfWlanAuthEapEntry
			MAX-ACCESS not-accessible
			STATUS current
			DESCRIPTION
				" "
			INDEX { wsCcRfWlanIndex }
			::= { wsCcRfWlanAuthEapTable 1 }


		WsCcRfWlanAuthEapEntry ::=
			SEQUENCE {
				wsCcRfWlanAuthEapRadiusServerIp1
					IpAddress,
				wsCcRfWlanAuthEapRadiusServerPort1
					Integer32,
				wsCcRfWlanAuthEapRadiusServerSecret1
					Password,
				wsCcRfWlanAuthEapRadiusServerIp2
					IpAddress,
				wsCcRfWlanAuthEapRadiusServerPort2
					Integer32,
				wsCcRfWlanAuthEapRadiusServerSecret2
					Password,
				wsCcRfWlanAuthEapSuppRetries
					Integer32,
				wsCcRfWlanAuthEapSuppTimeout
					Integer32,
				wsCcRfWlanAuthEapServerRetries
					Integer32,
				wsCcRfWlanAuthEapServerTimeout
					Integer32,
				wsCcRfWlanAuthEapReauth
					TruthValue,
				wsCcRfWlanAuthEapReauthTimeout
					Integer32,
				wsCcRfWlanAuthEapAuthProtocol
					INTEGER,
				wsCcRfWlanAuthEapDscpTos
					INTEGER,
				wsCcRfWlanAuthEapAccountingMode
					INTEGER,
				wsCcRfWlanAuthEapInterimAcctInterval
					Unsigned32,
				wsCcRfWlanAuthEapAcctTimeout
					Unsigned32,
				wsCcRfWlanAuthEapAcctRetries
					Unsigned32,
				wsCcRfWlanAuthPrimaryServer
					IpAddress,
				wsCcRfWlanAuthEapSecondaryServer
					IpAddress,
				wsCcRfWlanAuthEapPrimarySrvrPort
					Unsigned32,
				wsCcRfWlanAuthEapSecondarySrvrPort
					Unsigned32,
				wsCcRfWlanAuthEapPrimarySecret
					DisplayString,
				wsCcRfWlanAuthEapSecondarySecret
					DisplayString,
				wsCcRfWlanAuthEapRadiusMacAuthFormat
					INTEGER
			 }

		-- 1.3.6.1.4.1.388.14.3.2.1.14.2.1.1.1
		wsCcRfWlanAuthEapRadiusServerIp1 OBJECT-TYPE
			SYNTAX IpAddress
			MAX-ACCESS read-write
			STATUS current
			DESCRIPTION
				"IP address of the 1st RADIUS server."
			::= { wsCcRfWlanAuthEapEntry 1 }


		-- 1.3.6.1.4.1.388.14.3.2.1.14.2.1.1.2
		wsCcRfWlanAuthEapRadiusServerPort1 OBJECT-TYPE
			SYNTAX Integer32 (1..65535)
			MAX-ACCESS read-write
			STATUS current
			DESCRIPTION
				"Port number of the 1st RADIUS server."
			::= { wsCcRfWlanAuthEapEntry 2 }


		-- 1.3.6.1.4.1.388.14.3.2.1.14.2.1.1.3
		wsCcRfWlanAuthEapRadiusServerSecret1 OBJECT-TYPE
			SYNTAX Password (SIZE (0..127))
			MAX-ACCESS read-write
			STATUS current
			DESCRIPTION
				"Shared secret of the 1st RADIUS server."
			::= { wsCcRfWlanAuthEapEntry 3 }


		-- 1.3.6.1.4.1.388.14.3.2.1.14.2.1.1.4
		wsCcRfWlanAuthEapRadiusServerIp2 OBJECT-TYPE
			SYNTAX IpAddress
			MAX-ACCESS read-write
			STATUS current
			DESCRIPTION
				"IP address of the 2nd RADIUS server."
			::= { wsCcRfWlanAuthEapEntry 4 }


		-- 1.3.6.1.4.1.388.14.3.2.1.14.2.1.1.5
		wsCcRfWlanAuthEapRadiusServerPort2 OBJECT-TYPE
			SYNTAX Integer32 (1..65535)
			MAX-ACCESS read-write
			STATUS current
			DESCRIPTION
				"Port number of the 2nd RADIUS server."
			::= { wsCcRfWlanAuthEapEntry 5 }


		-- 1.3.6.1.4.1.388.14.3.2.1.14.2.1.1.6
		wsCcRfWlanAuthEapRadiusServerSecret2 OBJECT-TYPE
			SYNTAX Password (SIZE (0..127))
			MAX-ACCESS read-write
			STATUS current
			DESCRIPTION
				"Shared secret of the 2nd RADIUS server."
			::= { wsCcRfWlanAuthEapEntry 6 }


		-- 1.3.6.1.4.1.388.14.3.2.1.14.2.1.1.7
		wsCcRfWlanAuthEapSuppRetries OBJECT-TYPE
			SYNTAX Integer32 (1..100)
			MAX-ACCESS read-write
			STATUS current
			DESCRIPTION
				"Supplicant max retries."
			::= { wsCcRfWlanAuthEapEntry 7 }


		-- 1.3.6.1.4.1.388.14.3.2.1.14.2.1.1.8
		wsCcRfWlanAuthEapSuppTimeout OBJECT-TYPE
			SYNTAX Integer32 (1..300)
			UNITS "second"
			MAX-ACCESS read-write
			STATUS current
			DESCRIPTION
				"Supplicant timeout."
			::= { wsCcRfWlanAuthEapEntry 8 }


		-- 1.3.6.1.4.1.388.14.3.2.1.14.2.1.1.9
		wsCcRfWlanAuthEapServerRetries OBJECT-TYPE
			SYNTAX Integer32 (1..10)
			MAX-ACCESS read-write
			STATUS current
			DESCRIPTION
				"Server max retries."
			::= { wsCcRfWlanAuthEapEntry 9 }


		-- 1.3.6.1.4.1.388.14.3.2.1.14.2.1.1.10
		wsCcRfWlanAuthEapServerTimeout OBJECT-TYPE
			SYNTAX Integer32 (1..60)
			UNITS "second"
			MAX-ACCESS read-write
			STATUS current
			DESCRIPTION
				"Server timeout."
			::= { wsCcRfWlanAuthEapEntry 10 }


		-- 1.3.6.1.4.1.388.14.3.2.1.14.2.1.1.11
		wsCcRfWlanAuthEapReauth OBJECT-TYPE
			SYNTAX TruthValue
			MAX-ACCESS read-write
			STATUS current
			DESCRIPTION
				"Enable reauthentication."
			::= { wsCcRfWlanAuthEapEntry 11 }


		-- 1.3.6.1.4.1.388.14.3.2.1.14.2.1.1.12
		wsCcRfWlanAuthEapReauthTimeout OBJECT-TYPE
			SYNTAX Integer32 (30..65535)
			UNITS "second"
			MAX-ACCESS read-write
			STATUS current
			DESCRIPTION
				"Reauthentication timeout."
			::= { wsCcRfWlanAuthEapEntry 12 }


		-- 1.3.6.1.4.1.388.14.3.2.1.14.2.1.1.13
		wsCcRfWlanAuthEapAuthProtocol OBJECT-TYPE
			SYNTAX INTEGER
				{
				pap(1),
				chap(2)
				}
			MAX-ACCESS read-write
			STATUS current
			DESCRIPTION
				"The authentication protocol to be used, PAP or CHAP."
			::= { wsCcRfWlanAuthEapEntry 13 }


		-- 1.3.6.1.4.1.388.14.3.2.1.14.2.1.1.14
		wsCcRfWlanAuthEapDscpTos OBJECT-TYPE
			SYNTAX INTEGER (0..63)
			MAX-ACCESS read-write
			STATUS current
			DESCRIPTION
				"DSCP or TOS value to be used (between 0 and 63)."
			::= { wsCcRfWlanAuthEapEntry 14 }


		-- 1.3.6.1.4.1.388.14.3.2.1.14.2.1.1.15
		wsCcRfWlanAuthEapAccountingMode OBJECT-TYPE
			SYNTAX INTEGER
				{
				startStop(1),
				stopOnly(2),
				startInterimStop(3)
				}
			MAX-ACCESS read-write
			STATUS current
			DESCRIPTION
				"Indicates if mode of accounting is one of: Start-Stop, Start-only or Start-interim-Stop"
			::= { wsCcRfWlanAuthEapEntry 15 }


		-- 1.3.6.1.4.1.388.14.3.2.1.14.2.1.1.16
		wsCcRfWlanAuthEapInterimAcctInterval OBJECT-TYPE
			SYNTAX Unsigned32 (60..86400)
			MAX-ACCESS read-write
			STATUS current
			DESCRIPTION
				"Interval for interim accounting"
			::= { wsCcRfWlanAuthEapEntry 16 }


		-- 1.3.6.1.4.1.388.14.3.2.1.14.2.1.1.17
		wsCcRfWlanAuthEapAcctTimeout OBJECT-TYPE
			SYNTAX Unsigned32 (1..300)
			MAX-ACCESS read-write
			STATUS current
			DESCRIPTION
				"Timeout value for accounting option"
			::= { wsCcRfWlanAuthEapEntry 17 }


		-- 1.3.6.1.4.1.388.14.3.2.1.14.2.1.1.18
		wsCcRfWlanAuthEapAcctRetries OBJECT-TYPE
			SYNTAX Unsigned32 (1..100)
			MAX-ACCESS read-write
			STATUS current
			DESCRIPTION
				"Number of accounting retries"
			::= { wsCcRfWlanAuthEapEntry 18 }


		-- 1.3.6.1.4.1.388.14.3.2.1.14.2.1.1.19
		wsCcRfWlanAuthPrimaryServer OBJECT-TYPE
			SYNTAX IpAddress
			MAX-ACCESS read-write
			STATUS current
			DESCRIPTION
				"IP Address of the Primary Accounting Server"
			::= { wsCcRfWlanAuthEapEntry 19 }


		-- 1.3.6.1.4.1.388.14.3.2.1.14.2.1.1.20
		wsCcRfWlanAuthEapSecondaryServer OBJECT-TYPE
			SYNTAX IpAddress
			MAX-ACCESS read-write
			STATUS current
			DESCRIPTION
				"IP Address of the Secondary Accounting Server"
			::= { wsCcRfWlanAuthEapEntry 20 }


		-- 1.3.6.1.4.1.388.14.3.2.1.14.2.1.1.21
		wsCcRfWlanAuthEapPrimarySrvrPort OBJECT-TYPE
			SYNTAX Unsigned32 (1..65535)
			MAX-ACCESS read-write
			STATUS current
			DESCRIPTION
				"Port Number of the Primary Server"
			::= { wsCcRfWlanAuthEapEntry 21 }


		-- 1.3.6.1.4.1.388.14.3.2.1.14.2.1.1.22
		wsCcRfWlanAuthEapSecondarySrvrPort OBJECT-TYPE
			SYNTAX Unsigned32 (1..65535)
			MAX-ACCESS read-write
			STATUS current
			DESCRIPTION
				"Port Number of the Secondary Server"
			::= { wsCcRfWlanAuthEapEntry 22 }


		-- 1.3.6.1.4.1.388.14.3.2.1.14.2.1.1.23
		wsCcRfWlanAuthEapPrimarySecret OBJECT-TYPE
			SYNTAX DisplayString (SIZE (1..127))
			MAX-ACCESS read-write
			STATUS current
			DESCRIPTION
				"Shared secret of the Primary Accounting server."
			::= { wsCcRfWlanAuthEapEntry 23 }


		-- 1.3.6.1.4.1.388.14.3.2.1.14.2.1.1.24
		wsCcRfWlanAuthEapSecondarySecret OBJECT-TYPE
			SYNTAX DisplayString (SIZE (1..127))
			MAX-ACCESS read-write
			STATUS current
			DESCRIPTION
				"Shared secret of the Secondary Accounting server."
			::= { wsCcRfWlanAuthEapEntry 24 }


		-- 1.3.6.1.4.1.388.14.3.2.1.14.2.1.1.25
		wsCcRfWlanAuthEapRadiusMacAuthFormat OBJECT-TYPE
			SYNTAX INTEGER
				{
				noDelim(1),
				pairColon(2),
				pairDash(3),
				quadDot(4),
				middleDash(5)
				}
			MAX-ACCESS read-write
			STATUS current
			DESCRIPTION
				"The format of the MAC address to be sent to a RADIUS server when using MAC authentication:
				                 no-delim: No Delimiter - AABBCCDDEEFF
				                 pair-colon: Colon Delmilter per Pair - AA:BB:CC:DD:EE:FF
				                 pair-dash: Dash Delimiter per Pair - AA-BB-CC-DD-EE-FF
				                 quad-dot: Dot Delimiter per Four Hex - AABB.CCDD.EEFF
				                 middle-dash: Dash Delmiter in the middle - AABBCC-DDEEFF"
			::= { wsCcRfWlanAuthEapEntry 25 }


		-- 1.3.6.1.4.1.388.14.3.2.1.14.2.2
		wsCcRfWlanAuthKerberosTable OBJECT-TYPE
			SYNTAX SEQUENCE OF WsCcRfWlanAuthKerberosEntry
			MAX-ACCESS not-accessible
			STATUS current
			DESCRIPTION
				"Table of Kerberos authentication settings for each WLAN."
			::= { wsCcRfWlanAuth 2 }


		-- 1.3.6.1.4.1.388.14.3.2.1.14.2.2.1
		wsCcRfWlanAuthKerberosEntry OBJECT-TYPE
			SYNTAX WsCcRfWlanAuthKerberosEntry
			MAX-ACCESS not-accessible
			STATUS current
			DESCRIPTION
				" "
			INDEX { wsCcRfWlanIndex }
			::= { wsCcRfWlanAuthKerberosTable 1 }


		WsCcRfWlanAuthKerberosEntry ::=
			SEQUENCE {
				wsCcRfwlanAuthKerbRealm
					DisplayString,
				wsCcRfWlanAuthKerbPassword
					Password,
				wsCcRfWlanAuthKerbKdcServerIp1
					IpAddress,
				wsCcRfWlanAuthKerbKdcServerPort1
					Integer32,
				wsCcRfWlanAuthKerbKdcServerIp2
					IpAddress,
				wsCcRfWlanAuthKerbKdcServerPort2
					Integer32,
				wsCcRfWlanAuthKerberosServerTimeout
					Integer32
			 }

		-- 1.3.6.1.4.1.388.14.3.2.1.14.2.2.1.1
		wsCcRfwlanAuthKerbRealm OBJECT-TYPE
			SYNTAX DisplayString (SIZE (0..63))
			MAX-ACCESS read-write
			STATUS current
			DESCRIPTION
				"Realm name.

				A realm name functions similarly to a DNS domain
				name. In theory, the realm name is arbitrary.
				However, in practice a Kerberos realm is named by
				uppercasing the DNS domain name that is associated
				with hosts in the realm."
			::= { wsCcRfWlanAuthKerberosEntry 1 }


		-- 1.3.6.1.4.1.388.14.3.2.1.14.2.2.1.2
		wsCcRfWlanAuthKerbPassword OBJECT-TYPE
			SYNTAX Password (SIZE (0..20))
			MAX-ACCESS read-write
			STATUS current
			DESCRIPTION
				"Password for the Kerberos configuration."
			::= { wsCcRfWlanAuthKerberosEntry 2 }


		-- 1.3.6.1.4.1.388.14.3.2.1.14.2.2.1.3
		wsCcRfWlanAuthKerbKdcServerIp1 OBJECT-TYPE
			SYNTAX IpAddress
			MAX-ACCESS read-write
			STATUS current
			DESCRIPTION
				"IP address of the 1st Kerberos server."
			::= { wsCcRfWlanAuthKerberosEntry 3 }


		-- 1.3.6.1.4.1.388.14.3.2.1.14.2.2.1.4
		wsCcRfWlanAuthKerbKdcServerPort1 OBJECT-TYPE
			SYNTAX Integer32 (1..65535)
			MAX-ACCESS read-write
			STATUS current
			DESCRIPTION
				"Port number of the 1st Kerberos server."
			::= { wsCcRfWlanAuthKerberosEntry 4 }


		-- 1.3.6.1.4.1.388.14.3.2.1.14.2.2.1.5
		wsCcRfWlanAuthKerbKdcServerIp2 OBJECT-TYPE
			SYNTAX IpAddress
			MAX-ACCESS read-write
			STATUS current
			DESCRIPTION
				"IP address of the 2nd Kerberos server."
			::= { wsCcRfWlanAuthKerberosEntry 5 }


		-- 1.3.6.1.4.1.388.14.3.2.1.14.2.2.1.6
		wsCcRfWlanAuthKerbKdcServerPort2 OBJECT-TYPE
			SYNTAX Integer32 (1..65535)
			MAX-ACCESS read-write
			STATUS current
			DESCRIPTION
				"Port number of the 2nd Kerberos server."
			::= { wsCcRfWlanAuthKerberosEntry 6 }


		-- 1.3.6.1.4.1.388.14.3.2.1.14.2.2.1.7
		wsCcRfWlanAuthKerberosServerTimeout OBJECT-TYPE
			SYNTAX Integer32 (1..65535)
			MAX-ACCESS read-write
			STATUS current
			DESCRIPTION
				"Description."
			::= { wsCcRfWlanAuthKerberosEntry 7 }


		-- 1.3.6.1.4.1.388.14.3.2.1.14.3
		wsCcRfWlanEnc OBJECT IDENTIFIER ::= { wsCcRfWlan 3 }


		-- 1.3.6.1.4.1.388.14.3.2.1.14.3.1
		wsCcRfWlanEncSkEnable OBJECT-TYPE
			SYNTAX TruthValue
			MAX-ACCESS read-write
			STATUS current
			DESCRIPTION
				"Enable/disable Wlan encryption shared-key"
			::= { wsCcRfWlanEnc 1 }


		-- 1.3.6.1.4.1.388.14.3.2.1.14.3.2
		wsCcRfWlanEncWep64Table OBJECT-TYPE
			SYNTAX SEQUENCE OF WsCcRfWlanEncWep64Entry
			MAX-ACCESS not-accessible
			STATUS current
			DESCRIPTION
				"Table of WEP encryption settings for each WLAN."
			::= { wsCcRfWlanEnc 2 }


		-- 1.3.6.1.4.1.388.14.3.2.1.14.3.2.1
		wsCcRfWlanEncWep64Entry OBJECT-TYPE
			SYNTAX WsCcRfWlanEncWep64Entry
			MAX-ACCESS not-accessible
			STATUS current
			DESCRIPTION
				" "
			INDEX { wsCcRfWlanIndex }
			::= { wsCcRfWlanEncWep64Table 1 }


		WsCcRfWlanEncWep64Entry ::=
			SEQUENCE {
				wsCcRfWlanEncWep64KeyIndex
					Unsigned32,
				wsCcRfWlanEncWep64Key1
					OCTET STRING,
				wsCcRfWlanEncWep64Key2
					OCTET STRING,
				wsCcRfWlanEncWep64Key3
					OCTET STRING,
				wsCcRfWlanEncWep64Key4
					OCTET STRING
			 }

		-- 1.3.6.1.4.1.388.14.3.2.1.14.3.2.1.1
		wsCcRfWlanEncWep64KeyIndex OBJECT-TYPE
			SYNTAX Unsigned32 (1..4)
			MAX-ACCESS read-write
			STATUS current
			DESCRIPTION
				"Specifies which WEP key to use."
			::= { wsCcRfWlanEncWep64Entry 1 }


		-- 1.3.6.1.4.1.388.14.3.2.1.14.3.2.1.2
		wsCcRfWlanEncWep64Key1 OBJECT-TYPE
			SYNTAX OCTET STRING
			MAX-ACCESS read-write
			STATUS current
			DESCRIPTION
				"WEP key #1

				exactly  5 octets for WEP-64 (40-bit key)."
			::= { wsCcRfWlanEncWep64Entry 2 }


		-- 1.3.6.1.4.1.388.14.3.2.1.14.3.2.1.3
		wsCcRfWlanEncWep64Key2 OBJECT-TYPE
			SYNTAX OCTET STRING
			MAX-ACCESS read-write
			STATUS current
			DESCRIPTION
				"WEP key #2

				exactly  5 octets for WEP-64 (40-bit key)."
			::= { wsCcRfWlanEncWep64Entry 3 }


		-- 1.3.6.1.4.1.388.14.3.2.1.14.3.2.1.4
		wsCcRfWlanEncWep64Key3 OBJECT-TYPE
			SYNTAX OCTET STRING
			MAX-ACCESS read-write
			STATUS current
			DESCRIPTION
				"WEP key #3

				exactly  5 octets for WEP-64 (40-bit key)."
			::= { wsCcRfWlanEncWep64Entry 4 }


		-- 1.3.6.1.4.1.388.14.3.2.1.14.3.2.1.5
		wsCcRfWlanEncWep64Key4 OBJECT-TYPE
			SYNTAX OCTET STRING
			MAX-ACCESS read-write
			STATUS current
			DESCRIPTION
				"WEP key #4

				exactly  5 octets for WEP-64 (40-bit key)."
			::= { wsCcRfWlanEncWep64Entry 5 }


		-- 1.3.6.1.4.1.388.14.3.2.1.14.3.3
		wsCcRfWlanEncWep128KgTable OBJECT-TYPE
			SYNTAX SEQUENCE OF WsCcRfWlanEncWep128KgEntry
			MAX-ACCESS not-accessible
			STATUS current
			DESCRIPTION
				"Table of WEP encryption settings for each WLAN."
			::= { wsCcRfWlanEnc 3 }


		-- 1.3.6.1.4.1.388.14.3.2.1.14.3.3.1
		wsCcRfWlanEncWep128KgEntry OBJECT-TYPE
			SYNTAX WsCcRfWlanEncWep128KgEntry
			MAX-ACCESS not-accessible
			STATUS current
			DESCRIPTION
				" "
			INDEX { wsCcRfWlanIndex }
			::= { wsCcRfWlanEncWep128KgTable 1 }


		WsCcRfWlanEncWep128KgEntry ::=
			SEQUENCE {
				wsCcRfWlanEncWep128KgKeyIndex
					Unsigned32,
				wsCcRfWlanEncWep128KgKey1
					OCTET STRING,
				wsCcRfWlanEncWep128KgKey2
					OCTET STRING,
				wsCcRfWlanEncWep128KgKey3
					OCTET STRING,
				wsCcRfWlanEncWep128KgKey4
					OCTET STRING
			 }

		-- 1.3.6.1.4.1.388.14.3.2.1.14.3.3.1.1
		wsCcRfWlanEncWep128KgKeyIndex OBJECT-TYPE
			SYNTAX Unsigned32 (1..4)
			MAX-ACCESS read-write
			STATUS current
			DESCRIPTION
				"Specifies which WEP key to use."
			::= { wsCcRfWlanEncWep128KgEntry 1 }


		-- 1.3.6.1.4.1.388.14.3.2.1.14.3.3.1.2
		wsCcRfWlanEncWep128KgKey1 OBJECT-TYPE
			SYNTAX OCTET STRING
			MAX-ACCESS read-write
			STATUS current
			DESCRIPTION
				"WEP key #1

				exactly 13 octets for WEP-128 (104-bit key);
				"
			::= { wsCcRfWlanEncWep128KgEntry 2 }


		-- 1.3.6.1.4.1.388.14.3.2.1.14.3.3.1.3
		wsCcRfWlanEncWep128KgKey2 OBJECT-TYPE
			SYNTAX OCTET STRING
			MAX-ACCESS read-write
			STATUS current
			DESCRIPTION
				"WEP key #2

				exactly 13 octets for WEP-128 (104-bit key);
				"
			::= { wsCcRfWlanEncWep128KgEntry 3 }


		-- 1.3.6.1.4.1.388.14.3.2.1.14.3.3.1.4
		wsCcRfWlanEncWep128KgKey3 OBJECT-TYPE
			SYNTAX OCTET STRING
			MAX-ACCESS read-write
			STATUS current
			DESCRIPTION
				"WEP key #3

				exactly 13 octets for WEP-128 (104-bit key);
				"
			::= { wsCcRfWlanEncWep128KgEntry 4 }


		-- 1.3.6.1.4.1.388.14.3.2.1.14.3.3.1.5
		wsCcRfWlanEncWep128KgKey4 OBJECT-TYPE
			SYNTAX OCTET STRING
			MAX-ACCESS read-write
			STATUS current
			DESCRIPTION
				"WEP key #4

				exactly 13 octets for WEP-128 (104-bit key);
				"
			::= { wsCcRfWlanEncWep128KgEntry 5 }


		-- 1.3.6.1.4.1.388.14.3.2.1.14.3.4
		wsCcRfWlanEncTkipCcmpTable OBJECT-TYPE
			SYNTAX SEQUENCE OF WsCcRfWlanEncTkipCcmpEntry
			MAX-ACCESS not-accessible
			STATUS current
			DESCRIPTION
				"Table of Tkip/Ccmp encryption settings for each WLAN."
			::= { wsCcRfWlanEnc 4 }


		-- 1.3.6.1.4.1.388.14.3.2.1.14.3.4.1
		wsCcRfWlanEncTkipCcmpEntry OBJECT-TYPE
			SYNTAX WsCcRfWlanEncTkipCcmpEntry
			MAX-ACCESS not-accessible
			STATUS current
			DESCRIPTION
				" "
			INDEX { wsCcRfWlanIndex }
			::= { wsCcRfWlanEncTkipCcmpTable 1 }


		WsCcRfWlanEncTkipCcmpEntry ::=
			SEQUENCE {
				wsCcRfWlanEncTkipCcmpKeyType
					INTEGER,
				wsCcRfWlanEncTkipCcmpPassphrase
					Password,
				wsCcRfWlanEncTkipCcmpKey
					OCTET STRING,
				wsCcRfWlanEncTkipCcmpKeyRotation
					TruthValue,
				wsCcRfWlanEncTkipCcmpKeyInterval
					Integer32,
				wsCcRfWlanEncTkipCcmpPmkCaching
					TruthValue,
				wsCcRfWlanEncTkipCcmpOppPmkCaching
					TruthValue,
				wsCcRfWlanEncTkipCcmpPreauthentication
					TruthValue
			 }

		-- 1.3.6.1.4.1.388.14.3.2.1.14.3.4.1.1
		wsCcRfWlanEncTkipCcmpKeyType OBJECT-TYPE
			SYNTAX INTEGER
				{
				key(1),
				passphrase(2)
				}
			MAX-ACCESS read-write
			STATUS current
			DESCRIPTION
				"Specify whether to use key or passphrase."
			::= { wsCcRfWlanEncTkipCcmpEntry 1 }


		-- 1.3.6.1.4.1.388.14.3.2.1.14.3.4.1.2
		wsCcRfWlanEncTkipCcmpPassphrase OBJECT-TYPE
			SYNTAX Password
			MAX-ACCESS read-write
			STATUS current
			DESCRIPTION
				"Passphrase."
			::= { wsCcRfWlanEncTkipCcmpEntry 2 }


		-- 1.3.6.1.4.1.388.14.3.2.1.14.3.4.1.3
		wsCcRfWlanEncTkipCcmpKey OBJECT-TYPE
			SYNTAX OCTET STRING
			MAX-ACCESS read-write
			STATUS current
			DESCRIPTION
				"Key."
			::= { wsCcRfWlanEncTkipCcmpEntry 3 }


		-- 1.3.6.1.4.1.388.14.3.2.1.14.3.4.1.4
		wsCcRfWlanEncTkipCcmpKeyRotation OBJECT-TYPE
			SYNTAX TruthValue
			MAX-ACCESS read-write
			STATUS current
			DESCRIPTION
				" A truth-value that indicates whether the group
				key for a TKIP/CCMP mobile-unit should be
				periodically rotated."
			::= { wsCcRfWlanEncTkipCcmpEntry 4 }


		-- 1.3.6.1.4.1.388.14.3.2.1.14.3.4.1.5
		wsCcRfWlanEncTkipCcmpKeyInterval OBJECT-TYPE
			SYNTAX Integer32 (1800..86400)
			UNITS "second"
			MAX-ACCESS read-write
			STATUS current
			DESCRIPTION
				"The number of seconds after which the broadcast
				key of all mobile-units on a particular wireless
				lan is replaced by a new broadcast key."
			::= { wsCcRfWlanEncTkipCcmpEntry 5 }


		-- 1.3.6.1.4.1.388.14.3.2.1.14.3.4.1.6
		wsCcRfWlanEncTkipCcmpPmkCaching OBJECT-TYPE
			SYNTAX TruthValue
			MAX-ACCESS read-write
			STATUS current
			DESCRIPTION
				"Whether IEEE 802.11i PMK caching is enabled. Use
				of PMK caching allows a mobile-unit to authenticate
				just once to an AP, even if it roams away from it,
				and roams back to it. Enabling this feature results
				in much faster roam times on wireless LANs that
				use 802.1x authentication."
			::= { wsCcRfWlanEncTkipCcmpEntry 6 }


		-- 1.3.6.1.4.1.388.14.3.2.1.14.3.4.1.7
		wsCcRfWlanEncTkipCcmpOppPmkCaching OBJECT-TYPE
			SYNTAX TruthValue
			MAX-ACCESS read-write
			STATUS current
			DESCRIPTION
				"Whether extensions to IEEE 802.11i PMK caching,
				known as opportunistic PMK caching, are enabled.
				It extends PMK caching (authenticate once to an AP)
				to the whole switch (authenticate once to a switch).
				Enabling this feature results in much faster roam
				times on wireless LANs that use 802.1x
				authentication"
			::= { wsCcRfWlanEncTkipCcmpEntry 7 }


		-- 1.3.6.1.4.1.388.14.3.2.1.14.3.4.1.8
		wsCcRfWlanEncTkipCcmpPreauthentication OBJECT-TYPE
			SYNTAX TruthValue
			MAX-ACCESS read-write
			STATUS current
			DESCRIPTION
				"Whether pre-authentication is enabled."
			::= { wsCcRfWlanEncTkipCcmpEntry 8 }


-- A utility mib group used to generate wep keys from
-- a passphrase.
		-- 1.3.6.1.4.1.388.14.3.2.1.14.3.5
		wsCcRfWlanEncPhraseToWep OBJECT IDENTIFIER ::= { wsCcRfWlanEnc 5 }


		-- 1.3.6.1.4.1.388.14.3.2.1.14.3.5.1
		wsCcRfWlanEncP2WPassphrase OBJECT-TYPE
			SYNTAX DisplayString (SIZE (4..32))
			MAX-ACCESS read-write
			STATUS current
			DESCRIPTION
				"An input to an algorithm used to convert ascii into
				wep keys."
			::= { wsCcRfWlanEncPhraseToWep 1 }


		-- 1.3.6.1.4.1.388.14.3.2.1.14.3.5.2
		wsCcRfWlanEncP2WKey1 OBJECT-TYPE
			SYNTAX OCTET STRING
			MAX-ACCESS read-only
			STATUS current
			DESCRIPTION
				"Generated Wep128 key #1."
			::= { wsCcRfWlanEncPhraseToWep 2 }


		-- 1.3.6.1.4.1.388.14.3.2.1.14.3.5.3
		wsCcRfWlanEncP2WKey2 OBJECT-TYPE
			SYNTAX OCTET STRING
			MAX-ACCESS read-only
			STATUS current
			DESCRIPTION
				"Generated Wep128 key #2."
			::= { wsCcRfWlanEncPhraseToWep 3 }


		-- 1.3.6.1.4.1.388.14.3.2.1.14.3.5.4
		wsCcRfWlanEncP2WKey3 OBJECT-TYPE
			SYNTAX OCTET STRING
			MAX-ACCESS read-only
			STATUS current
			DESCRIPTION
				"Generated Wep128 key #3."
			::= { wsCcRfWlanEncPhraseToWep 4 }


		-- 1.3.6.1.4.1.388.14.3.2.1.14.3.5.5
		wsCcRfWlanEncP2WKey4 OBJECT-TYPE
			SYNTAX OCTET STRING
			MAX-ACCESS read-only
			STATUS current
			DESCRIPTION
				"Generated Wep128 key #4."
			::= { wsCcRfWlanEncPhraseToWep 5 }


		-- 1.3.6.1.4.1.388.14.3.2.1.14.3.5.6
		wsCcRfWlanEncP2WClearKeys OBJECT-TYPE
			SYNTAX DoActionNow
			MAX-ACCESS read-write
			STATUS current
			DESCRIPTION
				"Setting this scalar to 1 will clear all wep key
				fields."
			::= { wsCcRfWlanEncPhraseToWep 6 }


		-- 1.3.6.1.4.1.388.14.3.2.1.14.4
		wsCcRfWlanWmmTable OBJECT-TYPE
			SYNTAX SEQUENCE OF WsCcRfWlanWmmEntry
			MAX-ACCESS not-accessible
			STATUS current
			DESCRIPTION
				"Configuration parameters for 802.11e / Wireless
				MultiMedia, which control the Quality of
				Service between the wireless devices on
				the network"
			::= { wsCcRfWlan 4 }


		-- 1.3.6.1.4.1.388.14.3.2.1.14.4.1
		wsCcRfWlanWmmEntry OBJECT-TYPE
			SYNTAX WsCcRfWlanWmmEntry
			MAX-ACCESS not-accessible
			STATUS current
			DESCRIPTION
				" "
			INDEX { wsCcRfWlanIndex, wsCcRfWlanWmmAccessCategory }
			::= { wsCcRfWlanWmmTable 1 }


		WsCcRfWlanWmmEntry ::=
			SEQUENCE {
				wsCcRfWlanWmmAccessCategory
					INTEGER,
				wsCcRfWlanWmmAdmissionCtrl
					TruthValue,
				wsCcRfWlanWmmAifsn
					Unsigned32,
				wsCcRfWlanWmmTxOp
					Unsigned32,
				wsCcRfWlanWmmCwMin
					Unsigned32,
				wsCcRfWlanWmmCwMax
					Integer32,
				wsCcRfWlanWmmAdmissionDeviceMax
					Integer32
			 }

		-- 1.3.6.1.4.1.388.14.3.2.1.14.4.1.1
		wsCcRfWlanWmmAccessCategory OBJECT-TYPE
			SYNTAX INTEGER
				{
				acBestEffort(1),
				acBackground(2),
				acVideo(3),
				acVoice(4)
				}
			MAX-ACCESS accessible-for-notify
			STATUS current
			DESCRIPTION
				"A label for a particular QoS category of traffic
				in an 802.11e network. WMM defines 4 Access
				Categories (Voice, Video, Best Effort, Background)."
			::= { wsCcRfWlanWmmEntry 1 }


		-- 1.3.6.1.4.1.388.14.3.2.1.14.4.1.2
		wsCcRfWlanWmmAdmissionCtrl OBJECT-TYPE
			SYNTAX TruthValue
			MAX-ACCESS read-write
			STATUS deprecated
			DESCRIPTION
				"Enables/disables admission control."
			::= { wsCcRfWlanWmmEntry 2 }


		-- 1.3.6.1.4.1.388.14.3.2.1.14.4.1.3
		wsCcRfWlanWmmAifsn OBJECT-TYPE
			SYNTAX Unsigned32 (2..15)
			MAX-ACCESS read-write
			STATUS current
			DESCRIPTION
				"The Arbitration Inter-Frame Spacing is the wait
				time in milliSeconds between data frames. A
				smaller number leads to greater priority for
				medium access."
			::= { wsCcRfWlanWmmEntry 3 }


		-- 1.3.6.1.4.1.388.14.3.2.1.14.4.1.4
		wsCcRfWlanWmmTxOp OBJECT-TYPE
			SYNTAX Unsigned32 (0..65535)
			UNITS "millisecond"
			MAX-ACCESS read-write
			STATUS current
			DESCRIPTION
				" An interval of time where an 802.11e station
				(MU/AP) has the right to initiate transmissions
				on the wireless medium."
			::= { wsCcRfWlanWmmEntry 4 }


		-- 1.3.6.1.4.1.388.14.3.2.1.14.4.1.5
		wsCcRfWlanWmmCwMin OBJECT-TYPE
			SYNTAX Unsigned32 (0..15)
			MAX-ACCESS read-write
			STATUS current
			DESCRIPTION
				"If the medium is busy, or a transmitted frame
				collides, the AP or MU choose a random number
				between 0 and this minimum contention window size,
				to decide how long to wait before attempting
				(re)-transmission. For ease of use this value is
				configured as a number between 0 and 10; the
				actual window is calculated using 2**x -1 where
				x is the value configured."
			::= { wsCcRfWlanWmmEntry 5 }


		-- 1.3.6.1.4.1.388.14.3.2.1.14.4.1.6
		wsCcRfWlanWmmCwMax OBJECT-TYPE
			SYNTAX Integer32 (0..15)
			MAX-ACCESS read-write
			STATUS current
			DESCRIPTION
				"On each collision the AP or MU doubles its
				initial contention window wait time, until that
				number is as large as this maximum contention
				window size. For ease of use this value is
				configured as a number between 0 and 10; the
				actual window is calculated using 2**x -1 where
				x is the value configured."
			::= { wsCcRfWlanWmmEntry 6 }


		-- 1.3.6.1.4.1.388.14.3.2.1.14.4.1.7
		wsCcRfWlanWmmAdmissionDeviceMax OBJECT-TYPE
			SYNTAX Integer32 (1..255)
			MAX-ACCESS read-write
			STATUS deprecated
			DESCRIPTION
				"Max number of devices to admit."
			::= { wsCcRfWlanWmmEntry 7 }


		-- 1.3.6.1.4.1.388.14.3.2.1.14.5
		wsCcRfWlanCount OBJECT-TYPE
			SYNTAX INTEGER (1..256)
			MAX-ACCESS read-only
			STATUS current
			DESCRIPTION
				"the current number of wlan in the system"
			::= { wsCcRfWlan 5 }


		-- 1.3.6.1.4.1.388.14.3.2.1.15
		wsCcRfAssocAcl OBJECT IDENTIFIER ::= { wsCcRfMIB 15 }


		-- 1.3.6.1.4.1.388.14.3.2.1.15.1
		wsCcRfMuAssocAclTable OBJECT-TYPE
			SYNTAX SEQUENCE OF WsCcRfMuAssocAclEntry
			MAX-ACCESS not-accessible
			STATUS current
			DESCRIPTION
				"A table that allows users to filter MUs that are
				allowed/denied association to different WLANs
				based on their MAC address"
			::= { wsCcRfAssocAcl 1 }


		-- 1.3.6.1.4.1.388.14.3.2.1.15.1.1
		wsCcRfMuAssocAclEntry OBJECT-TYPE
			SYNTAX WsCcRfMuAssocAclEntry
			MAX-ACCESS not-accessible
			STATUS current
			DESCRIPTION
				" "
			INDEX { wsCcRfMuAssocAclIndex }
			::= { wsCcRfMuAssocAclTable 1 }


		WsCcRfMuAssocAclEntry ::=
			SEQUENCE {
				wsCcRfMuAssocAclIndex
					Integer32,
				wsCcRfMuAssocAclMode
					INTEGER,
				wsCcRfMuAssocAclStartingMac
					PhysAddress,
				wsCcRfMuAssocAclEndingMac
					PhysAddress,
				wsCcRfMuAssocAclWlans
					MultiPointer64,
				wsCcRfMuAssocAclRowStatus
					RowStatus
			 }

		-- 1.3.6.1.4.1.388.14.3.2.1.15.1.1.1
		wsCcRfMuAssocAclIndex OBJECT-TYPE
			SYNTAX Integer32 (1..1000)
			MAX-ACCESS accessible-for-notify
			STATUS current
			DESCRIPTION
				"Simple index."
			::= { wsCcRfMuAssocAclEntry 1 }


		-- 1.3.6.1.4.1.388.14.3.2.1.15.1.1.2
		wsCcRfMuAssocAclMode OBJECT-TYPE
			SYNTAX INTEGER
				{
				allow(1),
				deny(2)
				}
			MAX-ACCESS read-create
			STATUS current
			DESCRIPTION
				"Allow or deny the Mac range specified by
				wsCcRfWlanMuAclStartingMac and
				wsCcRfWlanMuAclEndingMac."
			DEFVAL { deny }
			::= { wsCcRfMuAssocAclEntry 2 }


		-- 1.3.6.1.4.1.388.14.3.2.1.15.1.1.3
		wsCcRfMuAssocAclStartingMac OBJECT-TYPE
			SYNTAX PhysAddress
			MAX-ACCESS read-create
			STATUS current
			DESCRIPTION
				"Starting MAC address in a range or addresses."
			DEFVAL { 'FFFFFFFFFFFF'h }
			::= { wsCcRfMuAssocAclEntry 3 }


		-- 1.3.6.1.4.1.388.14.3.2.1.15.1.1.4
		wsCcRfMuAssocAclEndingMac OBJECT-TYPE
			SYNTAX PhysAddress
			MAX-ACCESS read-create
			STATUS current
			DESCRIPTION
				"Ending MAC address in a range of addresses."
			DEFVAL { 'FFFFFFFFFFFF'h }
			::= { wsCcRfMuAssocAclEntry 4 }


		-- 1.3.6.1.4.1.388.14.3.2.1.15.1.1.5
		wsCcRfMuAssocAclWlans OBJECT-TYPE
			SYNTAX MultiPointer64
			MAX-ACCESS read-create
			STATUS current
			DESCRIPTION
				"The list of WLANs that this ACL rule applies to"
			DEFVAL { { referToEntry001 } }
			::= { wsCcRfMuAssocAclEntry 5 }


		-- 1.3.6.1.4.1.388.14.3.2.1.15.1.1.6
		wsCcRfMuAssocAclRowStatus OBJECT-TYPE
			SYNTAX RowStatus
			MAX-ACCESS read-create
			STATUS current
			DESCRIPTION
				"Row status."
			::= { wsCcRfMuAssocAclEntry 6 }


		-- 1.3.6.1.4.1.388.14.3.2.1.16
		wsCcRfRap OBJECT IDENTIFIER ::= { wsCcRfMIB 16 }


		-- 1.3.6.1.4.1.388.14.3.2.1.16.1
		wsCcRfRapMode OBJECT-TYPE
			SYNTAX INTEGER
				{
				enable(1),
				disable(2)
				}
			MAX-ACCESS read-write
			STATUS current
			DESCRIPTION
				"Enable/disable rogue AP detection"
			::= { wsCcRfRap 1 }


		-- 1.3.6.1.4.1.388.14.3.2.1.16.2
		wsCcRfRapMaxRogue OBJECT-TYPE
			SYNTAX Integer32 (1..1000)
			MAX-ACCESS read-write
			STATUS deprecated
			DESCRIPTION
				"The maximum number of rows in wsCcRfRapStatusTable"
			::= { wsCcRfRap 2 }


		-- 1.3.6.1.4.1.388.14.3.2.1.16.3
		wsCcRfRapTimeout OBJECT-TYPE
			SYNTAX Integer32
			UNITS "second"
			MAX-ACCESS read-write
			STATUS deprecated
			DESCRIPTION
				"The amount of time a rogue AP will remain after it is no longer
				seen"
			::= { wsCcRfRap 3 }


		-- 1.3.6.1.4.1.388.14.3.2.1.16.4
		wsCcRfRapCfgTable OBJECT-TYPE
			SYNTAX SEQUENCE OF WsCcRfRapCfgEntry
			MAX-ACCESS not-accessible
			STATUS current
			DESCRIPTION
				"Configure rogue-ap (ap-detection) parameter"
			::= { wsCcRfRap 4 }


		-- 1.3.6.1.4.1.388.14.3.2.1.16.4.1
		wsCcRfRapCfgEntry OBJECT-TYPE
			SYNTAX WsCcRfRapCfgEntry
			MAX-ACCESS not-accessible
			STATUS current
			DESCRIPTION
				" "
			INDEX { wsCcRfRapCfgIndex }
			::= { wsCcRfRapCfgTable 1 }


		WsCcRfRapCfgEntry ::=
			SEQUENCE {
				wsCcRfRapCfgIndex
					Integer32,
				wsCcRfRapCfgAnyMac
					TruthValue,
				wsCcRfRapCfgMac
					PhysAddress,
				wsCcRfRapCfgAnySsid
					TruthValue,
				wsCcRfRapCfgSsid
					DisplayString,
				wsCcRfRapCfgRowStatus
					RowStatus
			 }

		-- 1.3.6.1.4.1.388.14.3.2.1.16.4.1.1
		wsCcRfRapCfgIndex OBJECT-TYPE
			SYNTAX Integer32 (1..200)
			MAX-ACCESS accessible-for-notify
			STATUS current
			DESCRIPTION
				"Simple index"
			::= { wsCcRfRapCfgEntry 1 }


		-- 1.3.6.1.4.1.388.14.3.2.1.16.4.1.2
		wsCcRfRapCfgAnyMac OBJECT-TYPE
			SYNTAX TruthValue
			MAX-ACCESS read-create
			STATUS current
			DESCRIPTION
				"any Mac address"
			DEFVAL { 1 }
			::= { wsCcRfRapCfgEntry 2 }


		-- 1.3.6.1.4.1.388.14.3.2.1.16.4.1.3
		wsCcRfRapCfgMac OBJECT-TYPE
			SYNTAX PhysAddress
			MAX-ACCESS read-create
			STATUS current
			DESCRIPTION
				"Mac address"
			DEFVAL { 'FFFFFFFFFFFF'h }
			::= { wsCcRfRapCfgEntry 3 }


		-- 1.3.6.1.4.1.388.14.3.2.1.16.4.1.4
		wsCcRfRapCfgAnySsid OBJECT-TYPE
			SYNTAX TruthValue
			MAX-ACCESS read-create
			STATUS current
			DESCRIPTION
				"Any ssid "
			DEFVAL { 1 }
			::= { wsCcRfRapCfgEntry 4 }


		-- 1.3.6.1.4.1.388.14.3.2.1.16.4.1.5
		wsCcRfRapCfgSsid OBJECT-TYPE
			SYNTAX DisplayString
			MAX-ACCESS read-create
			STATUS current
			DESCRIPTION
				"ssid"
			DEFVAL { "" }
			::= { wsCcRfRapCfgEntry 5 }


		-- 1.3.6.1.4.1.388.14.3.2.1.16.4.1.6
		wsCcRfRapCfgRowStatus OBJECT-TYPE
			SYNTAX RowStatus
			MAX-ACCESS read-create
			STATUS current
			DESCRIPTION
				"Row status"
			::= { wsCcRfRapCfgEntry 6 }


		-- 1.3.6.1.4.1.388.14.3.2.1.16.5
		wsCcRfRapStatusTable OBJECT-TYPE
			SYNTAX SEQUENCE OF WsCcRfRapStatusEntry
			MAX-ACCESS not-accessible
			STATUS current
			DESCRIPTION
				"Status of AP assisted approved and un-approved access ports"
			::= { wsCcRfRap 5 }


		-- 1.3.6.1.4.1.388.14.3.2.1.16.5.1
		wsCcRfRapStatusEntry OBJECT-TYPE
			SYNTAX WsCcRfRapStatusEntry
			MAX-ACCESS not-accessible
			STATUS current
			DESCRIPTION
				" "
			INDEX { wsCcRfRapStatusType, wsCcRfRapStatusMac, wsCcRfRapStatusHeardAp }
			::= { wsCcRfRapStatusTable 1 }


		WsCcRfRapStatusEntry ::=
			SEQUENCE {
				wsCcRfRapStatusType
					INTEGER,
				wsCcRfRapStatusMac
					PhysAddress,
				wsCcRfRapStatusHeardAp
					Unsigned32,
				wsCcRfRapStatusChannel
					Integer32,
				wsCcRfRapStatusSsid
					DisplayString,
				wsCcRfRapStatusLastTimeSeen
					TimeTicks,
				wsCcRfRapStatusLastSignal
					Integer32,
				wsCcRfRapStatusMinSignal
					Integer32,
				wsCcRfRapStatusMaxSignal
					Integer32,
				wsCcRfRapStatusSumSignal
					Integer32,
				wsCcRfRapStatusSignalCount
					Counter32
			 }

		-- 1.3.6.1.4.1.388.14.3.2.1.16.5.1.1
		wsCcRfRapStatusType OBJECT-TYPE
			SYNTAX INTEGER
				{
				rogue(1),
				approved(2)
				}
			MAX-ACCESS read-only
			STATUS current
			DESCRIPTION
				"Radio type."
			::= { wsCcRfRapStatusEntry 1 }


		-- 1.3.6.1.4.1.388.14.3.2.1.16.5.1.2
		wsCcRfRapStatusMac OBJECT-TYPE
			SYNTAX PhysAddress
			MAX-ACCESS read-only
			STATUS current
			DESCRIPTION
				"Mac address of the access port"
			::= { wsCcRfRapStatusEntry 2 }


		-- 1.3.6.1.4.1.388.14.3.2.1.16.5.1.3
		wsCcRfRapStatusHeardAp OBJECT-TYPE
			SYNTAX Unsigned32 (1..500)
			MAX-ACCESS read-only
			STATUS current
			DESCRIPTION
				"Index of the heard access port "
			::= { wsCcRfRapStatusEntry 3 }


		-- 1.3.6.1.4.1.388.14.3.2.1.16.5.1.4
		wsCcRfRapStatusChannel OBJECT-TYPE
			SYNTAX Integer32 (1..512)
			MAX-ACCESS read-only
			STATUS current
			DESCRIPTION
				"Channel of heard radio"
			::= { wsCcRfRapStatusEntry 4 }


		-- 1.3.6.1.4.1.388.14.3.2.1.16.5.1.5
		wsCcRfRapStatusSsid OBJECT-TYPE
			SYNTAX DisplayString
			MAX-ACCESS read-only
			STATUS current
			DESCRIPTION
				"Ssid of heard radio"
			::= { wsCcRfRapStatusEntry 5 }


		-- 1.3.6.1.4.1.388.14.3.2.1.16.5.1.6
		wsCcRfRapStatusLastTimeSeen OBJECT-TYPE
			SYNTAX TimeTicks
			UNITS "second(s)"
			MAX-ACCESS read-only
			STATUS current
			DESCRIPTION
				"The number of second(s) ago this ap was last seen."
			::= { wsCcRfRapStatusEntry 6 }


		-- 1.3.6.1.4.1.388.14.3.2.1.16.5.1.7
		wsCcRfRapStatusLastSignal OBJECT-TYPE
			SYNTAX Integer32
			UNITS "dBm"
			MAX-ACCESS read-only
			STATUS current
			DESCRIPTION
				"Last signal level from the radio."
			::= { wsCcRfRapStatusEntry 7 }


		-- 1.3.6.1.4.1.388.14.3.2.1.16.5.1.8
		wsCcRfRapStatusMinSignal OBJECT-TYPE
			SYNTAX Integer32
			UNITS "dBm"
			MAX-ACCESS read-only
			STATUS current
			DESCRIPTION
				"Weakest signal heard from this radio."
			::= { wsCcRfRapStatusEntry 8 }


		-- 1.3.6.1.4.1.388.14.3.2.1.16.5.1.9
		wsCcRfRapStatusMaxSignal OBJECT-TYPE
			SYNTAX Integer32
			UNITS "dBm"
			MAX-ACCESS read-only
			STATUS current
			DESCRIPTION
				"Strongest signal heard from this radio."
			::= { wsCcRfRapStatusEntry 9 }


		-- 1.3.6.1.4.1.388.14.3.2.1.16.5.1.10
		wsCcRfRapStatusSumSignal OBJECT-TYPE
			SYNTAX Integer32
			UNITS "dBm"
			MAX-ACCESS read-only
			STATUS current
			DESCRIPTION
				"Sum of all signal values for this radio."
			::= { wsCcRfRapStatusEntry 10 }


		-- 1.3.6.1.4.1.388.14.3.2.1.16.5.1.11
		wsCcRfRapStatusSignalCount OBJECT-TYPE
			SYNTAX Counter32
			MAX-ACCESS read-only
			STATUS current
			DESCRIPTION
				"Number of signal data points for this radio."
			::= { wsCcRfRapStatusEntry 11 }


		-- 1.3.6.1.4.1.388.14.3.2.1.16.6
		wsCcRfRapMuAssistMode OBJECT-TYPE
			SYNTAX INTEGER
				{
				enable(1),
				disable(2)
				}
			MAX-ACCESS read-write
			STATUS current
			DESCRIPTION
				"Enable mobile-unit assisted scanning"
			::= { wsCcRfRap 6 }


		-- 1.3.6.1.4.1.388.14.3.2.1.16.7
		wsCcRfRapMuAssistRefreshPeriod OBJECT-TYPE
			SYNTAX INTEGER (300..86400)
			MAX-ACCESS read-write
			STATUS current
			DESCRIPTION
				"The period in seconds with which all scan-capable
				mobile-units are requested to scan for neighboring APs
				"
			::= { wsCcRfRap 7 }


		-- 1.3.6.1.4.1.388.14.3.2.1.16.8
		wsCcRfRUnpprovedApTimeout OBJECT-TYPE
			SYNTAX INTEGER (1..65535)
			UNITS "seconds"
			MAX-ACCESS read-write
			STATUS current
			DESCRIPTION
				"The amount of time an unapproved AP will remain after it is no longer
				seen"
			::= { wsCcRfRap 8 }


		-- 1.3.6.1.4.1.388.14.3.2.1.16.9
		wsCcRfRApprovedApTimeout OBJECT-TYPE
			SYNTAX INTEGER (1..65535)
			UNITS "seconds"
			MAX-ACCESS read-write
			STATUS current
			DESCRIPTION
				"The amount of time an approved AP will remain after it is no longer
				seen"
			::= { wsCcRfRap 9 }


		-- 1.3.6.1.4.1.388.14.3.2.1.16.10
		wsCcRfRapMuAssistTable OBJECT-TYPE
			SYNTAX SEQUENCE OF WsCcRfRapMuAssistEntry
			MAX-ACCESS not-accessible
			STATUS current
			DESCRIPTION
				"Status of MU assisted un-approved access ports"
			::= { wsCcRfRap 10 }


		-- 1.3.6.1.4.1.388.14.3.2.1.16.10.1
		wsCcRfRapMuAssistEntry OBJECT-TYPE
			SYNTAX WsCcRfRapMuAssistEntry
			MAX-ACCESS not-accessible
			STATUS current
			DESCRIPTION
				"Description."
			INDEX { wsCcRfRapMuAssistIndex }
			::= { wsCcRfRapMuAssistTable 1 }


		WsCcRfRapMuAssistEntry ::=
			SEQUENCE {
				wsCcRfRapMuAssistIndex
					INTEGER,
				wsCcRfRapMuAssistMac
					PhysAddress,
				wsCcRfRapMuAssistFoundOnPrtl
					Unsigned32,
				wsCcRfRapMuAssistTimestamp
					Unsigned32,
				wsCcRfRapMuAssistSsid
					DisplayString,
				wsCcRfRapMuAssistBss
					PhysAddress,
				wsCcRfRapMuAssistRssi
					Unsigned32
			 }

		-- 1.3.6.1.4.1.388.14.3.2.1.16.10.1.1
		wsCcRfRapMuAssistIndex OBJECT-TYPE
			SYNTAX INTEGER (1..1000)
			MAX-ACCESS read-only
			STATUS current
			DESCRIPTION
				"Simple index of approved and unapproved APs"
			::= { wsCcRfRapMuAssistEntry 1 }


		-- 1.3.6.1.4.1.388.14.3.2.1.16.10.1.2
		wsCcRfRapMuAssistMac OBJECT-TYPE
			SYNTAX PhysAddress
			MAX-ACCESS read-only
			STATUS current
			DESCRIPTION
				"MAC address of the access port"
			::= { wsCcRfRapMuAssistEntry 2 }


		-- 1.3.6.1.4.1.388.14.3.2.1.16.10.1.3
		wsCcRfRapMuAssistFoundOnPrtl OBJECT-TYPE
			SYNTAX Unsigned32 (1..1000)
			MAX-ACCESS read-only
			STATUS current
			DESCRIPTION
				"Portal with which the MU is associated"
			::= { wsCcRfRapMuAssistEntry 3 }


		-- 1.3.6.1.4.1.388.14.3.2.1.16.10.1.4
		wsCcRfRapMuAssistTimestamp OBJECT-TYPE
			SYNTAX Unsigned32
			MAX-ACCESS read-only
			STATUS current
			DESCRIPTION
				"Timestamp at which the radio was last heard"
			::= { wsCcRfRapMuAssistEntry 4 }


		-- 1.3.6.1.4.1.388.14.3.2.1.16.10.1.5
		wsCcRfRapMuAssistSsid OBJECT-TYPE
			SYNTAX DisplayString
			MAX-ACCESS read-only
			STATUS current
			DESCRIPTION
				"Ssid of heard radio"
			::= { wsCcRfRapMuAssistEntry 5 }


		-- 1.3.6.1.4.1.388.14.3.2.1.16.10.1.6
		wsCcRfRapMuAssistBss OBJECT-TYPE
			SYNTAX PhysAddress
			MAX-ACCESS read-only
			STATUS current
			DESCRIPTION
				"Bss of the heard radio"
			::= { wsCcRfRapMuAssistEntry 6 }


		-- 1.3.6.1.4.1.388.14.3.2.1.16.10.1.7
		wsCcRfRapMuAssistRssi OBJECT-TYPE
			SYNTAX Unsigned32 (0..256)
			MAX-ACCESS read-only
			STATUS current
			DESCRIPTION
				"RSSI of the heard radio"
			::= { wsCcRfRapMuAssistEntry 7 }


		-- 1.3.6.1.4.1.388.14.3.2.1.17
		wsCcRfIds OBJECT IDENTIFIER ::= { wsCcRfMIB 17 }


		-- 1.3.6.1.4.1.388.14.3.2.1.17.1
		wsCcRfIdsMaxExcsvAssoc OBJECT-TYPE
			SYNTAX Integer32 (0..65535)
			MAX-ACCESS read-write
			STATUS deprecated
			DESCRIPTION
				"Monitor the number of association requests from mobile-
				units."
			::= { wsCcRfIds 1 }


		-- 1.3.6.1.4.1.388.14.3.2.1.17.2
		wsCcRfIdsMaxExcsvProbes OBJECT-TYPE
			SYNTAX Integer32 (0..65535)
			MAX-ACCESS read-write
			STATUS deprecated
			DESCRIPTION
				"Monitor the number of probe requests from mobile-units."
			::= { wsCcRfIds 2 }


		-- 1.3.6.1.4.1.388.14.3.2.1.17.3
		wsCcRfIdsMuFilterAgeOut OBJECT-TYPE
			SYNTAX Integer32
			UNITS "seconds"
			MAX-ACCESS read-write
			STATUS deprecated
			DESCRIPTION
				"Set the number of seconds to filter a mobile-unit that
				set off IDS"
			::= { wsCcRfIds 3 }


		-- 1.3.6.1.4.1.388.14.3.2.1.17.4
		wsCcRfIdsMax OBJECT IDENTIFIER ::= { wsCcRfIds 4 }


		-- 1.3.6.1.4.1.388.14.3.2.1.17.4.1
		wsCcRfIdsMaxExcsvAssos OBJECT-TYPE
			SYNTAX INTEGER (0..65535)
			MAX-ACCESS read-write
			STATUS deprecated
			DESCRIPTION
				"Set the limit on the number of association requests from mobile-units."
			::= { wsCcRfIdsMax 1 }


		-- 1.3.6.1.4.1.388.14.3.2.1.17.4.2
		wsCcRfIdsMaxExcsvProbs OBJECT-TYPE
			SYNTAX INTEGER (0..65535)
			MAX-ACCESS read-write
			STATUS deprecated
			DESCRIPTION
				"Set the limit on the number of probe requests from mobile-units."
			::= { wsCcRfIdsMax 2 }


		-- 1.3.6.1.4.1.388.14.3.2.1.17.4.3
		wsCcRfIdsMaxExcsvDisassos OBJECT-TYPE
			SYNTAX INTEGER (0..65535)
			MAX-ACCESS read-write
			STATUS deprecated
			DESCRIPTION
				"Set the limit on the number of disassociation requests from mobile-units."
			::= { wsCcRfIdsMax 3 }


		-- 1.3.6.1.4.1.388.14.3.2.1.17.4.4
		wsCcRfIdsMaxExcsvAuthFailures OBJECT-TYPE
			SYNTAX INTEGER (0..65535)
			MAX-ACCESS read-write
			STATUS deprecated
			DESCRIPTION
				"Set the limit on the number of authentication failures in mobile-units."
			::= { wsCcRfIdsMax 4 }


		-- 1.3.6.1.4.1.388.14.3.2.1.17.4.5
		wsCcRfIdsMaxExcsvCryptoReplays OBJECT-TYPE
			SYNTAX INTEGER (0..65535)
			MAX-ACCESS read-write
			STATUS deprecated
			DESCRIPTION
				"Set the limit on the number of crypto replays in mobile-units."
			::= { wsCcRfIdsMax 5 }


		-- 1.3.6.1.4.1.388.14.3.2.1.17.4.6
		wsCcRfIdsMaxExcsv80211Replays OBJECT-TYPE
			SYNTAX INTEGER (0..65535)
			MAX-ACCESS read-write
			STATUS deprecated
			DESCRIPTION
				"Set the limit on the number of 802.11 replays in mobile-units."
			::= { wsCcRfIdsMax 6 }


		-- 1.3.6.1.4.1.388.14.3.2.1.17.4.7
		wsCcRfIdsMaxExcsvDecryptFails OBJECT-TYPE
			SYNTAX Integer32
			MAX-ACCESS read-write
			STATUS deprecated
			DESCRIPTION
				"Set the limit on the number of decryption failures in mobile-units."
			::= { wsCcRfIdsMax 7 }


		-- 1.3.6.1.4.1.388.14.3.2.1.17.5
		wsCcRfIdsAnmly OBJECT IDENTIFIER ::= { wsCcRfIds 5 }


		-- 1.3.6.1.4.1.388.14.3.2.1.17.5.1
		wsCcRfIdsAnmlySrcMacEqDestMac OBJECT-TYPE
			SYNTAX INTEGER
				{
				enable(1),
				disable(2)
				}
			MAX-ACCESS read-write
			STATUS deprecated
			DESCRIPTION
				"When enabled, it carries out anomaly detection where source and destination MAC
				addresses are same in the frame."
			::= { wsCcRfIdsAnmly 1 }


		-- 1.3.6.1.4.1.388.14.3.2.1.17.5.2
		wsCcRfIdsAnmlyNullDestination OBJECT-TYPE
			SYNTAX INTEGER
				{
				enable(1),
				disable(2)
				}
			MAX-ACCESS read-write
			STATUS deprecated
			DESCRIPTION
				"When enabled, it carries out anomaly detection where the destination MAC is NULL."
			::= { wsCcRfIdsAnmly 2 }


		-- 1.3.6.1.4.1.388.14.3.2.1.17.5.3
		wsCcRfIdsAnmlySrcMulticastMac OBJECT-TYPE
			SYNTAX INTEGER
				{
				enable(1),
				disable(2)
				}
			MAX-ACCESS read-write
			STATUS deprecated
			DESCRIPTION
				"When enabled, it carries out anomaly detection where the source MAC address in the
				 frame is a multicast address."
			::= { wsCcRfIdsAnmly 3 }


		-- 1.3.6.1.4.1.388.14.3.2.1.17.5.4
		wsCcRfIdsAnmlyWeakWepIv OBJECT-TYPE
			SYNTAX INTEGER
				{
				enable(1),
				disable(2)
				}
			MAX-ACCESS read-write
			STATUS deprecated
			DESCRIPTION
				"When enabled, it detects the out anomaly where the WEP IV is weak."
			::= { wsCcRfIdsAnmly 4 }


		-- 1.3.6.1.4.1.388.14.3.2.1.17.6
		wsCcRfIdsStatusFilteredMacMax OBJECT-TYPE
			SYNTAX INTEGER (0..65535)
			MAX-ACCESS read-only
			STATUS deprecated
			DESCRIPTION
				"Set the maximum number of MACs to be filtered for IDS."
			::= { wsCcRfIds 6 }


		-- 1.3.6.1.4.1.388.14.3.2.1.17.7
		wsCcRfIdsMuFilterAgeOutTime OBJECT-TYPE
			SYNTAX INTEGER (0..65535)
			MAX-ACCESS read-write
			STATUS deprecated
			DESCRIPTION
				"Set the number of seconds to filter a mobile-unit that
				set off IDS"
			::= { wsCcRfIds 7 }


		-- 1.3.6.1.4.1.388.14.3.2.1.17.8
		wsCcRfIdsStatusTable OBJECT-TYPE
			SYNTAX SEQUENCE OF WsCcRfIdsStatusEntry
			MAX-ACCESS not-accessible
			STATUS current
			DESCRIPTION
				"A table to track WIDS status for each filtered MAC."
			::= { wsCcRfIds 8 }


		-- 1.3.6.1.4.1.388.14.3.2.1.17.8.1
		wsCcRfIdsStatusEntry OBJECT-TYPE
			SYNTAX WsCcRfIdsStatusEntry
			MAX-ACCESS not-accessible
			STATUS current
			DESCRIPTION
				"An entry in the wsCcRfIdsStatusTable"
			INDEX { wsCcRfIdsStatusViolatnIndex }
			::= { wsCcRfIdsStatusTable 1 }


		WsCcRfIdsStatusEntry ::=
			SEQUENCE {
				wsCcRfIdsStatusViolatnIndex
					INTEGER,
				wsCcRfIdsStatusFilteredMuMac
					PhysAddress,
				wsCcRfIdsStatusViolatnType
					IdsViolationType,
				wsCcRfIdsStatusRadioIndex
					INTEGER,
				wsCcRfIdsStatusRemainingBlacklistTime
					TimeTicks,
				wsCcRfIdsStatusRowStatus
					RowStatus
			 }

		-- 1.3.6.1.4.1.388.14.3.2.1.17.8.1.1
		wsCcRfIdsStatusViolatnIndex OBJECT-TYPE
			SYNTAX INTEGER (1..100)
			MAX-ACCESS read-only
			STATUS current
			DESCRIPTION
				"The index for this table which tells about at most 100 most recent violations."
			::= { wsCcRfIdsStatusEntry 1 }


		-- 1.3.6.1.4.1.388.14.3.2.1.17.8.1.2
		wsCcRfIdsStatusFilteredMuMac OBJECT-TYPE
			SYNTAX PhysAddress
			MAX-ACCESS read-only
			STATUS current
			DESCRIPTION
				"The MAC address of the mobile-unit which is being filtered for WIDS."
			::= { wsCcRfIdsStatusEntry 2 }


		-- 1.3.6.1.4.1.388.14.3.2.1.17.8.1.3
		wsCcRfIdsStatusViolatnType OBJECT-TYPE
			SYNTAX IdsViolationType
			MAX-ACCESS read-only
			STATUS current
			DESCRIPTION
				"The specific violation type done by the MU, whether a threshold was crossed or an
				anomaly was detected."
			::= { wsCcRfIdsStatusEntry 3 }


		-- 1.3.6.1.4.1.388.14.3.2.1.17.8.1.4
		wsCcRfIdsStatusRadioIndex OBJECT-TYPE
			SYNTAX INTEGER (1..1000)
			MAX-ACCESS read-only
			STATUS current
			DESCRIPTION
				"The radio index where this violation occured."
			::= { wsCcRfIdsStatusEntry 4 }


		-- 1.3.6.1.4.1.388.14.3.2.1.17.8.1.5
		wsCcRfIdsStatusRemainingBlacklistTime OBJECT-TYPE
			SYNTAX TimeTicks
			MAX-ACCESS read-only
			STATUS current
			DESCRIPTION
				"The remaining blacklist time for this mobile-unit which had a WIDS violation."
			::= { wsCcRfIdsStatusEntry 5 }


		-- 1.3.6.1.4.1.388.14.3.2.1.17.8.1.6
		wsCcRfIdsStatusRowStatus OBJECT-TYPE
			SYNTAX RowStatus
			MAX-ACCESS read-create
			STATUS current
			DESCRIPTION
				"The row status for this entry."
			::= { wsCcRfIdsStatusEntry 6 }


		-- 1.3.6.1.4.1.388.14.3.2.1.17.9
		wsCcRfIdsEventTable OBJECT-TYPE
			SYNTAX SEQUENCE OF WsCcRfIdsEventEntry
			MAX-ACCESS not-accessible
			STATUS current
			DESCRIPTION
				"An entry in the wsCcRfIdsEventTable"
			::= { wsCcRfIds 9 }


		-- 1.3.6.1.4.1.388.14.3.2.1.17.9.1
		wsCcRfIdsEventEntry OBJECT-TYPE
			SYNTAX WsCcRfIdsEventEntry
			MAX-ACCESS not-accessible
			STATUS current
			DESCRIPTION
				"An entry in the wsCcRfMuIdsTable."
			INDEX { wsCcRfIdsEventRadioIndex, wsCcRfIdsEventType }
			::= { wsCcRfIdsEventTable 1 }


		WsCcRfIdsEventEntry ::=
			SEQUENCE {
				wsCcRfIdsEventRadioIndex
					INTEGER,
				wsCcRfIdsEventType
					IdsViolationType,
				wsCcRfIdsEventLastOccurredTime
					TimeTicks,
				wsCcRfIdsEventTotalCount
					Integer32,
				wsCcRfIdsEventCountSinceMidnight
					Integer32
			 }

		-- 1.3.6.1.4.1.388.14.3.2.1.17.9.1.1
		wsCcRfIdsEventRadioIndex OBJECT-TYPE
			SYNTAX INTEGER (1..1000)
			MAX-ACCESS read-only
			STATUS current
			DESCRIPTION
				"The radio index where this event last occured."
			::= { wsCcRfIdsEventEntry 1 }


		-- 1.3.6.1.4.1.388.14.3.2.1.17.9.1.2
		wsCcRfIdsEventType OBJECT-TYPE
			SYNTAX IdsViolationType
			MAX-ACCESS read-only
			STATUS current
			DESCRIPTION
				"The event type, which is the index for this table. There are eleven event types
				enumerated so far and hence this table has eleven rows."
			::= { wsCcRfIdsEventEntry 2 }


		-- 1.3.6.1.4.1.388.14.3.2.1.17.9.1.3
		wsCcRfIdsEventLastOccurredTime OBJECT-TYPE
			SYNTAX TimeTicks
			MAX-ACCESS read-only
			STATUS current
			DESCRIPTION
				"Timeticks since the last occurence of this event."
			::= { wsCcRfIdsEventEntry 3 }


		-- 1.3.6.1.4.1.388.14.3.2.1.17.9.1.4
		wsCcRfIdsEventTotalCount OBJECT-TYPE
			SYNTAX Integer32
			MAX-ACCESS read-only
			STATUS current
			DESCRIPTION
				"The total count of how many times a given type of event has occurred in the switch."
			::= { wsCcRfIdsEventEntry 4 }


		-- 1.3.6.1.4.1.388.14.3.2.1.17.9.1.5
		wsCcRfIdsEventCountSinceMidnight OBJECT-TYPE
			SYNTAX Integer32
			MAX-ACCESS read-only
			STATUS current
			DESCRIPTION
				"A count of how many times a given type of event has occurred in the switch since midnight i.e.
				00:00:00 hours."
			::= { wsCcRfIdsEventEntry 5 }


		-- 1.3.6.1.4.1.388.14.3.2.1.17.10
		wsCcRfIdsClearMuIdsEventEntries OBJECT-TYPE
			SYNTAX TruthValue
			MAX-ACCESS read-write
			STATUS current
			DESCRIPTION
				"A scalar to reset all entries in the wsCcRfIdsMuEventTable to 0"
			::= { wsCcRfIds 10 }


		-- 1.3.6.1.4.1.388.14.3.2.1.17.11
		wsCcRfIdsEventPeriod OBJECT-TYPE
			SYNTAX INTEGER (0..10)
			UNITS "seconds"
			MAX-ACCESS read-write
			STATUS deprecated
			DESCRIPTION
				"The period of time, in seconds, over which the IDS events are observed to check
				if they exceeded the threshold. For example if this value is set as 5 seconds,
				the threshold for, say, excessive authentication failures can be, say, 100 event
				detections per 5 second interval."
			::= { wsCcRfIds 11 }


		-- 1.3.6.1.4.1.388.14.3.2.1.17.12
		wsCcRfIdsDetectionWindow OBJECT-TYPE
			SYNTAX Unsigned32 (5..300)
			UNITS "seconds"
			MAX-ACCESS read-write
			STATUS current
			DESCRIPTION
				"Number of seconds for detection."
			::= { wsCcRfIds 12 }


		-- 1.3.6.1.4.1.388.14.3.2.1.17.13
		wsCcRfIdsThresholdsTable OBJECT-TYPE
			SYNTAX SEQUENCE OF WsCcRfIdsThresholdsEntry
			MAX-ACCESS not-accessible
			STATUS current
			DESCRIPTION
				"Thresholds and filter-ageout for each violation type."
			::= { wsCcRfIds 13 }


		-- 1.3.6.1.4.1.388.14.3.2.1.17.13.1
		wsCcRfIdsThresholdsEntry OBJECT-TYPE
			SYNTAX WsCcRfIdsThresholdsEntry
			MAX-ACCESS not-accessible
			STATUS current
			DESCRIPTION
				"An entry in the wsCcRfIdsThresholdsTable."
			INDEX { wsCcRfIdsThresholdsViolTypeIndex }
			::= { wsCcRfIdsThresholdsTable 1 }


		WsCcRfIdsThresholdsEntry ::=
			SEQUENCE {
				wsCcRfIdsThresholdsViolTypeIndex
					IdsViolationType,
				wsCcRfIdsThresholdsMu
					Unsigned32,
				wsCcRfIdsThresholdsRadio
					Unsigned32,
				wsCcRfIdsThresholdsSwitch
					Unsigned32,
				wsCcRfIdsThresholdsFilterAgeout
					Unsigned32
			 }

		-- 1.3.6.1.4.1.388.14.3.2.1.17.13.1.1
		wsCcRfIdsThresholdsViolTypeIndex OBJECT-TYPE
			SYNTAX IdsViolationType
			MAX-ACCESS read-write
			STATUS current
			DESCRIPTION
				"Description."
			::= { wsCcRfIdsThresholdsEntry 1 }


		-- 1.3.6.1.4.1.388.14.3.2.1.17.13.1.2
		wsCcRfIdsThresholdsMu OBJECT-TYPE
			SYNTAX Unsigned32 (0..65535)
			MAX-ACCESS read-write
			STATUS current
			DESCRIPTION
				"MU threshold for violation type.  Setting the value
				to 0 will disable the check."
			::= { wsCcRfIdsThresholdsEntry 2 }


		-- 1.3.6.1.4.1.388.14.3.2.1.17.13.1.3
		wsCcRfIdsThresholdsRadio OBJECT-TYPE
			SYNTAX Unsigned32 (0..65535)
			MAX-ACCESS read-write
			STATUS current
			DESCRIPTION
				"Radio threshold for violation type.  Setting the value
				to 0 will disable the check."
			::= { wsCcRfIdsThresholdsEntry 3 }


		-- 1.3.6.1.4.1.388.14.3.2.1.17.13.1.4
		wsCcRfIdsThresholdsSwitch OBJECT-TYPE
			SYNTAX Unsigned32 (0..65535)
			MAX-ACCESS read-write
			STATUS current
			DESCRIPTION
				"Switch threshold for violation type.  Setting the value
				to 0 will disable the check."
			::= { wsCcRfIdsThresholdsEntry 4 }


		-- 1.3.6.1.4.1.388.14.3.2.1.17.13.1.5
		wsCcRfIdsThresholdsFilterAgeout OBJECT-TYPE
			SYNTAX Unsigned32 (0..86400)
			UNITS "seconds"
			MAX-ACCESS read-write
			STATUS current
			DESCRIPTION
				"Number of seconds to filter for violation type."
			::= { wsCcRfIdsThresholdsEntry 5 }


		-- 1.3.6.1.4.1.388.14.3.2.1.17.14
		wsCcRfIdsRadioIndex OBJECT-TYPE
			SYNTAX Integer32
			MAX-ACCESS read-only
			STATUS current
			DESCRIPTION
				"The radio index where this event last occured."
			::= { wsCcRfIds 14 }


		-- 1.3.6.1.4.1.388.14.3.2.1.17.15
		wsCcRfIdsViolationType OBJECT-TYPE
			SYNTAX IdsViolationType
			MAX-ACCESS read-only
			STATUS current
			DESCRIPTION
				"The specific type of the IDS violation has occured."
			::= { wsCcRfIds 15 }


		-- 1.3.6.1.4.1.388.14.3.2.1.17.16
		wsCcRfIdsViolCountLastDetWindow OBJECT-TYPE
			SYNTAX Integer32
			MAX-ACCESS read-only
			STATUS current
			DESCRIPTION
				"The number of IDS violations has occured in the last detection window."
			::= { wsCcRfIds 16 }


		-- 1.3.6.1.4.1.388.14.3.2.1.18
		wsCcRfSelfHealing OBJECT IDENTIFIER ::= { wsCcRfMIB 18 }


		-- 1.3.6.1.4.1.388.14.3.2.1.18.1
		wsCcRfSelfHealingNeighborRecoveryEnable OBJECT-TYPE
			SYNTAX TruthValue
			MAX-ACCESS read-write
			STATUS current
			DESCRIPTION
				"Enable/Disable monitoring of APs and attempt to increase coverage
				on failure."
			::= { wsCcRfSelfHealing 1 }


		-- 1.3.6.1.4.1.388.14.3.2.1.18.2
		wsCcRfSelfHealingDetectNeighborNow OBJECT-TYPE
			SYNTAX DoActionShowProgress
			MAX-ACCESS read-write
			STATUS current
			DESCRIPTION
				"Disassociate all MUs, clear current neigbors and run a
				neighbor detection"
			::= { wsCcRfSelfHealing 2 }


		-- 1.3.6.1.4.1.388.14.3.2.1.18.3
		wsCcRfSelfHealingInterferenceAvoidanceEnable OBJECT-TYPE
			SYNTAX TruthValue
			MAX-ACCESS read-write
			STATUS current
			DESCRIPTION
				"Enable/disable interference avoidance."
			::= { wsCcRfSelfHealing 3 }


		-- 1.3.6.1.4.1.388.14.3.2.1.18.4
		wsCcRfSelfHealingInterferenceAvoidanceRetriesx10 OBJECT-TYPE
			SYNTAX Integer32 (0..150)
			MAX-ACCESS read-write
			STATUS current
			DESCRIPTION
				"The average number retries (x10) to cause a radio to re-run
				auto channel selection."
			::= { wsCcRfSelfHealing 4 }


		-- 1.3.6.1.4.1.388.14.3.2.1.18.5
		wsCcRfSelfHealingInterferenceAvoidanceHoldTime OBJECT-TYPE
			SYNTAX Integer32 (0..65535)
			UNITS "second"
			MAX-ACCESS read-write
			STATUS current
			DESCRIPTION
				"The number of seconds to disable interference avoidance
				after a detection.  This prevents a radio from changing
				channels continuously."
			::= { wsCcRfSelfHealing 5 }


		-- 1.3.6.1.4.1.388.14.3.2.1.18.6
		wsCcRfSelfHealingNeighborRadioTable OBJECT-TYPE
			SYNTAX SEQUENCE OF WsCcRfSelfHealingNeighborRadioEntry
			MAX-ACCESS not-accessible
			STATUS current
			DESCRIPTION
				"This table stores radio neighbor information."
			::= { wsCcRfSelfHealing 6 }


		-- 1.3.6.1.4.1.388.14.3.2.1.18.6.1
		wsCcRfSelfHealingNeighborRadioEntry OBJECT-TYPE
			SYNTAX WsCcRfSelfHealingNeighborRadioEntry
			MAX-ACCESS not-accessible
			STATUS current
			DESCRIPTION
				" "
			INDEX { wsCcRfSelfHealingNeighborRadioFirstRadio, wsCcRfSelfHealingNeighborRadioSecondRadio }
			::= { wsCcRfSelfHealingNeighborRadioTable 1 }


		WsCcRfSelfHealingNeighborRadioEntry ::=
			SEQUENCE {
				wsCcRfSelfHealingNeighborRadioFirstRadio
					Integer32,
				wsCcRfSelfHealingNeighborRadioSecondRadio
					Integer32,
				wsCcRfSelfHealingNeighborRadioRowStatus
					RowStatus
			 }

		-- 1.3.6.1.4.1.388.14.3.2.1.18.6.1.1
		wsCcRfSelfHealingNeighborRadioFirstRadio OBJECT-TYPE
			SYNTAX Integer32 (1..500)
			MAX-ACCESS accessible-for-notify
			STATUS current
			DESCRIPTION
				"Radio index of the first radio"
			::= { wsCcRfSelfHealingNeighborRadioEntry 1 }


		-- 1.3.6.1.4.1.388.14.3.2.1.18.6.1.2
		wsCcRfSelfHealingNeighborRadioSecondRadio OBJECT-TYPE
			SYNTAX Integer32 (1..500)
			MAX-ACCESS accessible-for-notify
			STATUS current
			DESCRIPTION
				"Radio index of the second radio"
			::= { wsCcRfSelfHealingNeighborRadioEntry 2 }


		-- 1.3.6.1.4.1.388.14.3.2.1.18.6.1.3
		wsCcRfSelfHealingNeighborRadioRowStatus OBJECT-TYPE
			SYNTAX RowStatus
			MAX-ACCESS read-create
			STATUS current
			DESCRIPTION
				"Row status"
			::= { wsCcRfSelfHealingNeighborRadioEntry 3 }


		-- 1.3.6.1.4.1.388.14.3.2.1.18.7
		wsCcRfSelfHealingMonitoringTable OBJECT-TYPE
			SYNTAX SEQUENCE OF WsCcRfSelfHealingMonitoringEntry
			MAX-ACCESS not-accessible
			STATUS current
			DESCRIPTION
				" "
			::= { wsCcRfSelfHealing 7 }


		-- 1.3.6.1.4.1.388.14.3.2.1.18.7.1
		wsCcRfSelfHealingMonitoringEntry OBJECT-TYPE
			SYNTAX WsCcRfSelfHealingMonitoringEntry
			MAX-ACCESS not-accessible
			STATUS current
			DESCRIPTION
				" "
			INDEX { wsCcRfSelfHealingMonitoringTransRadio, wsCcRfSelfHealingMonitoringRecvRadio }
			::= { wsCcRfSelfHealingMonitoringTable 1 }


		WsCcRfSelfHealingMonitoringEntry ::=
			SEQUENCE {
				wsCcRfSelfHealingMonitoringTransRadio
					Integer32,
				wsCcRfSelfHealingMonitoringRecvRadio
					Integer32,
				wsCcRfSelfHealingMonitoringChannel
					Integer32,
				wsCcRfSelfHealingMonitoringLastTime
					TimeTicks,
				wsCcRfSelfHealingMonitoringLastSignal
					Integer32,
				wsCcRfSelfHealingMonitoringMinSig
					Integer32,
				wsCcRfSelfHealingMonitoringMaxSig
					Integer32,
				wsCcRfSelfHealingMonitoringSumSig
					Integer32,
				wsCcRfSelfHealingMonitoringNumSig
					Unsigned32
			 }

		-- 1.3.6.1.4.1.388.14.3.2.1.18.7.1.1
		wsCcRfSelfHealingMonitoringTransRadio OBJECT-TYPE
			SYNTAX Integer32 (1..1000)
			MAX-ACCESS accessible-for-notify
			STATUS current
			DESCRIPTION
				"Index of transmitting radio."
			::= { wsCcRfSelfHealingMonitoringEntry 1 }


		-- 1.3.6.1.4.1.388.14.3.2.1.18.7.1.2
		wsCcRfSelfHealingMonitoringRecvRadio OBJECT-TYPE
			SYNTAX Integer32 (1..1000)
			MAX-ACCESS accessible-for-notify
			STATUS current
			DESCRIPTION
				"Index of receiving Radio."
			::= { wsCcRfSelfHealingMonitoringEntry 2 }


		-- 1.3.6.1.4.1.388.14.3.2.1.18.7.1.3
		wsCcRfSelfHealingMonitoringChannel OBJECT-TYPE
			SYNTAX Integer32
			MAX-ACCESS read-only
			STATUS current
			DESCRIPTION
				"Monitoring channel"
			::= { wsCcRfSelfHealingMonitoringEntry 3 }


		-- 1.3.6.1.4.1.388.14.3.2.1.18.7.1.4
		wsCcRfSelfHealingMonitoringLastTime OBJECT-TYPE
			SYNTAX TimeTicks
			MAX-ACCESS read-only
			STATUS current
			DESCRIPTION
				"The time of the last beacon heard"
			::= { wsCcRfSelfHealingMonitoringEntry 4 }


		-- 1.3.6.1.4.1.388.14.3.2.1.18.7.1.5
		wsCcRfSelfHealingMonitoringLastSignal OBJECT-TYPE
			SYNTAX Integer32
			MAX-ACCESS read-only
			STATUS current
			DESCRIPTION
				"The dBm signal value of the last beacon heard"
			::= { wsCcRfSelfHealingMonitoringEntry 5 }


		-- 1.3.6.1.4.1.388.14.3.2.1.18.7.1.6
		wsCcRfSelfHealingMonitoringMinSig OBJECT-TYPE
			SYNTAX Integer32
			MAX-ACCESS read-only
			STATUS current
			DESCRIPTION
				"The lowest dBm signal value heard"
			::= { wsCcRfSelfHealingMonitoringEntry 6 }


		-- 1.3.6.1.4.1.388.14.3.2.1.18.7.1.7
		wsCcRfSelfHealingMonitoringMaxSig OBJECT-TYPE
			SYNTAX Integer32
			MAX-ACCESS read-only
			STATUS current
			DESCRIPTION
				"The highest dBm signal value heard"
			::= { wsCcRfSelfHealingMonitoringEntry 7 }


		-- 1.3.6.1.4.1.388.14.3.2.1.18.7.1.8
		wsCcRfSelfHealingMonitoringSumSig OBJECT-TYPE
			SYNTAX Integer32
			MAX-ACCESS read-only
			STATUS current
			DESCRIPTION
				"The sum of all signal values heard"
			::= { wsCcRfSelfHealingMonitoringEntry 8 }


		-- 1.3.6.1.4.1.388.14.3.2.1.18.7.1.9
		wsCcRfSelfHealingMonitoringNumSig OBJECT-TYPE
			SYNTAX Unsigned32
			MAX-ACCESS read-only
			STATUS current
			DESCRIPTION
				"The number of signal values heard"
			::= { wsCcRfSelfHealingMonitoringEntry 9 }


		-- 1.3.6.1.4.1.388.14.3.2.1.19
		wsCcRfHotspot OBJECT IDENTIFIER ::= { wsCcRfMIB 19 }


		-- 1.3.6.1.4.1.388.14.3.2.1.19.1
		wsCcRfHotspotTable OBJECT-TYPE
			SYNTAX SEQUENCE OF WsCcRfHotspotEntry
			MAX-ACCESS not-accessible
			STATUS current
			DESCRIPTION
				"Configure hotspot related parameters."
			::= { wsCcRfHotspot 1 }


		-- 1.3.6.1.4.1.388.14.3.2.1.19.1.1
		wsCcRfHotspotEntry OBJECT-TYPE
			SYNTAX WsCcRfHotspotEntry
			MAX-ACCESS not-accessible
			STATUS current
			DESCRIPTION
				" "
			INDEX { wsCcRfWlanIndex }
			::= { wsCcRfHotspotTable 1 }


		WsCcRfHotspotEntry ::=
			SEQUENCE {
				wsCcRfHotspotServerIp1
					IpAddress,
				wsCcRfHotspotServerPort1
					Integer32,
				wsCcRfHotspotServerSecret1
					Password,
				wsCcRfHotspotServerIp2
					IpAddress,
				wsCcRfHotspotServerPort2
					Integer32,
				wsCcRfHotspotServerSecret2
					Password,
				wsCcRfHotspotServerRetries
					Integer32,
				wsCcRfHotspotServerTimeout
					Integer32,
				wsCcRfHotspotPageLocation
					INTEGER,
				wsCcRfHotspotWebsiteType
					INTEGER
			 }

		-- 1.3.6.1.4.1.388.14.3.2.1.19.1.1.1
		wsCcRfHotspotServerIp1 OBJECT-TYPE
			SYNTAX IpAddress
			MAX-ACCESS read-write
			STATUS current
			DESCRIPTION
				"Primary Radius server ip for hotspot authentication."
			::= { wsCcRfHotspotEntry 1 }


		-- 1.3.6.1.4.1.388.14.3.2.1.19.1.1.2
		wsCcRfHotspotServerPort1 OBJECT-TYPE
			SYNTAX Integer32 (1024..65535)
			MAX-ACCESS read-write
			STATUS current
			DESCRIPTION
				"Primary Radius server port for hotspot authentication."
			::= { wsCcRfHotspotEntry 2 }


		-- 1.3.6.1.4.1.388.14.3.2.1.19.1.1.3
		wsCcRfHotspotServerSecret1 OBJECT-TYPE
			SYNTAX Password (SIZE (0..127))
			MAX-ACCESS read-write
			STATUS current
			DESCRIPTION
				"Primary Radius server shared secret for hotspot
				authentication."
			::= { wsCcRfHotspotEntry 3 }


		-- 1.3.6.1.4.1.388.14.3.2.1.19.1.1.4
		wsCcRfHotspotServerIp2 OBJECT-TYPE
			SYNTAX IpAddress
			MAX-ACCESS read-write
			STATUS current
			DESCRIPTION
				"Secondary Radius server ip for hotspot authentication."
			::= { wsCcRfHotspotEntry 4 }


		-- 1.3.6.1.4.1.388.14.3.2.1.19.1.1.5
		wsCcRfHotspotServerPort2 OBJECT-TYPE
			SYNTAX Integer32 (1024..65535)
			MAX-ACCESS read-write
			STATUS current
			DESCRIPTION
				"Secondary Radius server port for hotspot authentication."
			::= { wsCcRfHotspotEntry 5 }


		-- 1.3.6.1.4.1.388.14.3.2.1.19.1.1.6
		wsCcRfHotspotServerSecret2 OBJECT-TYPE
			SYNTAX Password (SIZE (0..127))
			MAX-ACCESS read-write
			STATUS current
			DESCRIPTION
				"Secondary Radius server shared secret for hotspot
				authentication."
			::= { wsCcRfHotspotEntry 6 }


		-- 1.3.6.1.4.1.388.14.3.2.1.19.1.1.7
		wsCcRfHotspotServerRetries OBJECT-TYPE
			SYNTAX Integer32 (1..10)
			MAX-ACCESS read-write
			STATUS current
			DESCRIPTION
				"Number of retries the wireless switch initiates before
				giving up"
			::= { wsCcRfHotspotEntry 7 }


		-- 1.3.6.1.4.1.388.14.3.2.1.19.1.1.8
		wsCcRfHotspotServerTimeout OBJECT-TYPE
			SYNTAX Integer32 (1..60)
			UNITS "second"
			MAX-ACCESS read-write
			STATUS current
			DESCRIPTION
				"Time the wireless switch waits for a response from the
				radius server before retrying"
			::= { wsCcRfHotspotEntry 8 }


		-- 1.3.6.1.4.1.388.14.3.2.1.19.1.1.9
		wsCcRfHotspotPageLocation OBJECT-TYPE
			SYNTAX INTEGER
				{
				internal(1),
				external(2)
				}
			MAX-ACCESS read-write
			STATUS deprecated
			DESCRIPTION
				"The location of the webpages to be used for
				authentication.  These pages can either be hosted on
				the wireless switch or on an external web server"
			::= { wsCcRfHotspotEntry 9 }


		-- 1.3.6.1.4.1.388.14.3.2.1.19.1.1.10
		wsCcRfHotspotWebsiteType OBJECT-TYPE
			SYNTAX INTEGER
				{
				internal(1),
				external(2),
				advanced(3)
				}
			MAX-ACCESS read-write
			STATUS current
			DESCRIPTION
				"The website type to be used for authentication.
				The website can either be hosted on the wireless switch or
				on an external web server"
			::= { wsCcRfHotspotEntry 10 }


		-- 1.3.6.1.4.1.388.14.3.2.1.19.2
		wsCcRfHotspotPageTable OBJECT-TYPE
			SYNTAX SEQUENCE OF WsCcRfHotspotPageEntry
			MAX-ACCESS not-accessible
			STATUS current
			DESCRIPTION
				"Configure hotspot page parameters"
			::= { wsCcRfHotspot 2 }


		-- 1.3.6.1.4.1.388.14.3.2.1.19.2.1
		wsCcRfHotspotPageEntry OBJECT-TYPE
			SYNTAX WsCcRfHotspotPageEntry
			MAX-ACCESS not-accessible
			STATUS current
			DESCRIPTION
				" "
			INDEX { wsCcRfWlanIndex, wsCcRfHotspotPageType }
			::= { wsCcRfHotspotPageTable 1 }


		WsCcRfHotspotPageEntry ::=
			SEQUENCE {
				wsCcRfHotspotPageType
					INTEGER,
				wsCcRfHotspotIntPageTitle
					OCTET STRING,
				wsCcRfHotspotIntPageHeader
					OCTET STRING,
				wsCcRfHotspotIntPageDescr
					OCTET STRING,
				wsCcRfHotspotIntPageFooter
					OCTET STRING,
				wsCcRfHotspotIntPageImgUrl1
					OCTET STRING,
				wsCcRfHotspotIntPageImgUrl2
					OCTET STRING,
				wsCcRfHotspotExtPageUrl
					OCTET STRING
			 }

		-- 1.3.6.1.4.1.388.14.3.2.1.19.2.1.1
		wsCcRfHotspotPageType OBJECT-TYPE
			SYNTAX INTEGER
				{
				login(1),
				welcome(2),
				fail(3)
				}
			MAX-ACCESS accessible-for-notify
			STATUS current
			DESCRIPTION
				"Hotspot page type"
			::= { wsCcRfHotspotPageEntry 1 }


		-- 1.3.6.1.4.1.388.14.3.2.1.19.2.1.2
		wsCcRfHotspotIntPageTitle OBJECT-TYPE
			SYNTAX OCTET STRING
			MAX-ACCESS read-write
			STATUS current
			DESCRIPTION
				"Ascii string that will be in the title of the webpage."
			::= { wsCcRfHotspotPageEntry 2 }


		-- 1.3.6.1.4.1.388.14.3.2.1.19.2.1.3
		wsCcRfHotspotIntPageHeader OBJECT-TYPE
			SYNTAX OCTET STRING
			MAX-ACCESS read-write
			STATUS current
			DESCRIPTION
				"Ascii string that is displayed as a header. (large font,
				top section) of the webpage. "
			::= { wsCcRfHotspotPageEntry 3 }


		-- 1.3.6.1.4.1.388.14.3.2.1.19.2.1.4
		wsCcRfHotspotIntPageDescr OBJECT-TYPE
			SYNTAX OCTET STRING
			MAX-ACCESS read-write
			STATUS current
			DESCRIPTION
				"Ascii string that is displayed as the main body (normal
				font, middle of page) of the webpage"
			::= { wsCcRfHotspotPageEntry 4 }


		-- 1.3.6.1.4.1.388.14.3.2.1.19.2.1.5
		wsCcRfHotspotIntPageFooter OBJECT-TYPE
			SYNTAX OCTET STRING
			MAX-ACCESS read-write
			STATUS current
			DESCRIPTION
				"Ascii string that is displayed at the footer (smaller font,
				bottom section) of the webpage"
			::= { wsCcRfHotspotPageEntry 5 }


		-- 1.3.6.1.4.1.388.14.3.2.1.19.2.1.6
		wsCcRfHotspotIntPageImgUrl1 OBJECT-TYPE
			SYNTAX OCTET STRING
			MAX-ACCESS read-write
			STATUS current
			DESCRIPTION
				"main image( large size) that will be served up by the
				local webpage.  Appears between the header and description
				on the webpage."
			::= { wsCcRfHotspotPageEntry 6 }


		-- 1.3.6.1.4.1.388.14.3.2.1.19.2.1.7
		wsCcRfHotspotIntPageImgUrl2 OBJECT-TYPE
			SYNTAX OCTET STRING
			MAX-ACCESS read-write
			STATUS current
			DESCRIPTION
				"Small image (thumbnail size) that will be served up by the
				local webpage.  Appears near the footer on the webpage."
			::= { wsCcRfHotspotPageEntry 7 }


		-- 1.3.6.1.4.1.388.14.3.2.1.19.2.1.8
		wsCcRfHotspotExtPageUrl OBJECT-TYPE
			SYNTAX OCTET STRING
			MAX-ACCESS read-write
			STATUS current
			DESCRIPTION
				"Url of external page"
			::= { wsCcRfHotspotPageEntry 8 }


		-- 1.3.6.1.4.1.388.14.3.2.1.19.3
		wsCcRfHotspotWhiteIpTable OBJECT-TYPE
			SYNTAX SEQUENCE OF WsCcRfHotspotWhiteIpEntry
			MAX-ACCESS not-accessible
			STATUS current
			DESCRIPTION
				"Configure hotspot white list parameters.  Users who have
				not yet authenticated will be allowed access to these IP
				addresses"
			::= { wsCcRfHotspot 3 }


		-- 1.3.6.1.4.1.388.14.3.2.1.19.3.1
		wsCcRfHotspotWhiteIpEntry OBJECT-TYPE
			SYNTAX WsCcRfHotspotWhiteIpEntry
			MAX-ACCESS not-accessible
			STATUS current
			DESCRIPTION
				" "
			INDEX { wsCcRfWlanIndex, wsCcRfHotspotWhiteIpRuleIndex }
			::= { wsCcRfHotspotWhiteIpTable 1 }


		WsCcRfHotspotWhiteIpEntry ::=
			SEQUENCE {
				wsCcRfHotspotWhiteIpRuleIndex
					Integer32,
				wsCcRfHotspotWhiteIpAddr
					IpAddress
			 }

		-- 1.3.6.1.4.1.388.14.3.2.1.19.3.1.1
		wsCcRfHotspotWhiteIpRuleIndex OBJECT-TYPE
			SYNTAX Integer32 (1..10)
			MAX-ACCESS accessible-for-notify
			STATUS current
			DESCRIPTION
				"rule index"
			::= { wsCcRfHotspotWhiteIpEntry 1 }


		-- 1.3.6.1.4.1.388.14.3.2.1.19.3.1.2
		wsCcRfHotspotWhiteIpAddr OBJECT-TYPE
			SYNTAX IpAddress
			MAX-ACCESS read-write
			STATUS current
			DESCRIPTION
				"White-list IP address"
			DEFVAL { ''h }
			::= { wsCcRfHotspotWhiteIpEntry 2 }


		-- 1.3.6.1.4.1.388.14.3.2.1.20
		wsCcRfQos OBJECT IDENTIFIER ::= { wsCcRfMIB 20 }


		-- 1.3.6.1.4.1.388.14.3.2.1.20.1
		wsCcRfQosAcTo802dot1pTable OBJECT-TYPE
			SYNTAX SEQUENCE OF WsCcRfQosAcTo802dot1pEntry
			MAX-ACCESS not-accessible
			STATUS current
			DESCRIPTION
				"The mapping of access categories to 802.1p priorities."
			::= { wsCcRfQos 1 }


		-- 1.3.6.1.4.1.388.14.3.2.1.20.1.1
		wsCcRfQosAcTo802dot1pEntry OBJECT-TYPE
			SYNTAX WsCcRfQosAcTo802dot1pEntry
			MAX-ACCESS not-accessible
			STATUS current
			DESCRIPTION
				"A single mapping of an access category to 802.1p priority."
			INDEX { wsCcRfQosAcTo802dot1pAccessCategory }
			::= { wsCcRfQosAcTo802dot1pTable 1 }


		WsCcRfQosAcTo802dot1pEntry ::=
			SEQUENCE {
				wsCcRfQosAcTo802dot1pAccessCategory
					AccCatType,
				wsCcRfQosAcTo802dot1pPriority
					Integer32
			 }

		-- 1.3.6.1.4.1.388.14.3.2.1.20.1.1.1
		wsCcRfQosAcTo802dot1pAccessCategory OBJECT-TYPE
			SYNTAX AccCatType
			MAX-ACCESS accessible-for-notify
			STATUS current
			DESCRIPTION
				"An access category."
			::= { wsCcRfQosAcTo802dot1pEntry 1 }


		-- 1.3.6.1.4.1.388.14.3.2.1.20.1.1.2
		wsCcRfQosAcTo802dot1pPriority OBJECT-TYPE
			SYNTAX Integer32 (0..7)
			MAX-ACCESS read-write
			STATUS current
			DESCRIPTION
				"An 802.1p priority tag."
			::= { wsCcRfQosAcTo802dot1pEntry 2 }


		-- 1.3.6.1.4.1.388.14.3.2.1.20.2
		wsCcRfQos802dot1pToAcTable OBJECT-TYPE
			SYNTAX SEQUENCE OF WsCcRfQos802dot1pToAcEntry
			MAX-ACCESS not-accessible
			STATUS current
			DESCRIPTION
				"The mapping of 802.1p priorities to access categories ."
			::= { wsCcRfQos 2 }


		-- 1.3.6.1.4.1.388.14.3.2.1.20.2.1
		wsCcRfQos802dot1pToAcEntry OBJECT-TYPE
			SYNTAX WsCcRfQos802dot1pToAcEntry
			MAX-ACCESS not-accessible
			STATUS current
			DESCRIPTION
				"A single mapping of an 802.1p priority to an access category."
			INDEX { wsCcRfQos802dot1pToAcIndex }
			::= { wsCcRfQos802dot1pToAcTable 1 }


		WsCcRfQos802dot1pToAcEntry ::=
			SEQUENCE {
				wsCcRfQos802dot1pToAcIndex
					Integer32,
				wsCcRfQos802dot1pToAcPriority
					Integer32,
				wsCcRfQos802dot1pToAcAccessCategory
					AccCatType
			 }

		-- 1.3.6.1.4.1.388.14.3.2.1.20.2.1.1
		wsCcRfQos802dot1pToAcIndex OBJECT-TYPE
			SYNTAX Integer32 (1..8)
			MAX-ACCESS accessible-for-notify
			STATUS current
			DESCRIPTION
				"A simple sequential index."
			::= { wsCcRfQos802dot1pToAcEntry 1 }


		-- 1.3.6.1.4.1.388.14.3.2.1.20.2.1.2
		wsCcRfQos802dot1pToAcPriority OBJECT-TYPE
			SYNTAX Integer32 (0..7)
			MAX-ACCESS read-only
			STATUS current
			DESCRIPTION
				"An 802.1p priority tag."
			::= { wsCcRfQos802dot1pToAcEntry 2 }


		-- 1.3.6.1.4.1.388.14.3.2.1.20.2.1.3
		wsCcRfQos802dot1pToAcAccessCategory OBJECT-TYPE
			SYNTAX AccCatType
			MAX-ACCESS read-write
			STATUS current
			DESCRIPTION
				"An access category."
			::= { wsCcRfQos802dot1pToAcEntry 3 }


		-- 1.3.6.1.4.1.388.14.3.2.1.20.3
		wsCcRfQosDscpToAcTable OBJECT-TYPE
			SYNTAX SEQUENCE OF WsCcRfQosDscpToAcEntry
			MAX-ACCESS not-accessible
			STATUS current
			DESCRIPTION
				"The mapping of DSCP values to access categories."
			::= { wsCcRfQos 3 }


		-- 1.3.6.1.4.1.388.14.3.2.1.20.3.1
		wsCcRfQosDscpToAcEntry OBJECT-TYPE
			SYNTAX WsCcRfQosDscpToAcEntry
			MAX-ACCESS not-accessible
			STATUS current
			DESCRIPTION
				"A single mapping of a DSCP value to an access category."
			INDEX { wsCcRfQosDscpToAcIndex }
			::= { wsCcRfQosDscpToAcTable 1 }


		WsCcRfQosDscpToAcEntry ::=
			SEQUENCE {
				wsCcRfQosDscpToAcIndex
					Integer32,
				wsCcRfQosDscpToAcDscp
					Integer32,
				wsCcRfQosDscpToAcAccessCategory
					AccCatType
			 }

		-- 1.3.6.1.4.1.388.14.3.2.1.20.3.1.1
		wsCcRfQosDscpToAcIndex OBJECT-TYPE
			SYNTAX Integer32 (1..64)
			MAX-ACCESS accessible-for-notify
			STATUS current
			DESCRIPTION
				"A simple sequential index."
			::= { wsCcRfQosDscpToAcEntry 1 }


		-- 1.3.6.1.4.1.388.14.3.2.1.20.3.1.2
		wsCcRfQosDscpToAcDscp OBJECT-TYPE
			SYNTAX Integer32 (0..63)
			MAX-ACCESS read-only
			STATUS current
			DESCRIPTION
				"A DSCP value."
			::= { wsCcRfQosDscpToAcEntry 2 }


		-- 1.3.6.1.4.1.388.14.3.2.1.20.3.1.3
		wsCcRfQosDscpToAcAccessCategory OBJECT-TYPE
			SYNTAX AccCatType
			MAX-ACCESS read-write
			STATUS current
			DESCRIPTION
				"An access category."
			::= { wsCcRfQosDscpToAcEntry 3 }


		-- 1.3.6.1.4.1.388.14.3.2.1.21
		wsCcRfWiredWebAuth OBJECT IDENTIFIER ::= { wsCcRfMIB 21 }


		-- 1.3.6.1.4.1.388.14.3.2.1.21.1
		wsCcRfWiredWebAuthEnable OBJECT-TYPE
			SYNTAX TruthValue
			MAX-ACCESS read-write
			STATUS current
			DESCRIPTION
				"Enabling of wired web authentication."
			::= { wsCcRfWiredWebAuth 1 }


		-- 1.3.6.1.4.1.388.14.3.2.1.21.2
		wsCcRfWiredWebAuthVlan OBJECT-TYPE
			SYNTAX INTEGER (1..4094)
			MAX-ACCESS read-write
			STATUS current
			DESCRIPTION
				"Assignment of VLAN to the wired web authentication."
			::= { wsCcRfWiredWebAuth 2 }


		-- 1.3.6.1.4.1.388.14.3.2.1.21.3
		wsCcRfWiredWebAuthWlan OBJECT-TYPE
			SYNTAX INTEGER (1..32)
			MAX-ACCESS read-write
			STATUS current
			DESCRIPTION
				"Assignment of WLAN to the wired web authentication."
			::= { wsCcRfWiredWebAuth 3 }


		-- 1.3.6.1.4.1.388.14.3.2.1.21.4
		wsCcRfWiredWebAuthHostEntryDelete OBJECT-TYPE
			SYNTAX Integer32
			MAX-ACCESS read-write
			STATUS current
			DESCRIPTION
				"Description.Use this object to remove an entry in
				wsCcRfWiredWebAuthHostTable."
			::= { wsCcRfWiredWebAuth 4 }


		-- 1.3.6.1.4.1.388.14.3.2.1.21.5
		wsCcRfWiredWebAuthHostTable OBJECT-TYPE
			SYNTAX SEQUENCE OF WsCcRfWiredWebAuthHostEntry
			MAX-ACCESS not-accessible
			STATUS current
			DESCRIPTION
				"Description."
			::= { wsCcRfWiredWebAuth 5 }


		-- 1.3.6.1.4.1.388.14.3.2.1.21.5.1
		wsCcRfWiredWebAuthHostEntry OBJECT-TYPE
			SYNTAX WsCcRfWiredWebAuthHostEntry
			MAX-ACCESS not-accessible
			STATUS current
			DESCRIPTION
				"Description."
			INDEX { wsCcRfWiredWebAuthHostIndex }
			::= { wsCcRfWiredWebAuthHostTable 1 }


		WsCcRfWiredWebAuthHostEntry ::=
			SEQUENCE {
				wsCcRfWiredWebAuthHostIndex
					INTEGER,
				wsCcRfWiredWebAuthHostMac
					PhysAddress,
				wsCcRfWiredWebAuthHostIp
					IpAddress,
				wsCcRfWiredWebAuthHostState
					INTEGER,
				wsCcRfWiredWebAuthHostVlan
					Integer32
			 }

		-- 1.3.6.1.4.1.388.14.3.2.1.21.5.1.1
		wsCcRfWiredWebAuthHostIndex OBJECT-TYPE
			SYNTAX INTEGER (1..100)
			MAX-ACCESS read-only
			STATUS current
			DESCRIPTION
				"Description. The index for the wsCcRfWiredWebAuthHostTable."
			::= { wsCcRfWiredWebAuthHostEntry 1 }


		-- 1.3.6.1.4.1.388.14.3.2.1.21.5.1.2
		wsCcRfWiredWebAuthHostMac OBJECT-TYPE
			SYNTAX PhysAddress
			MAX-ACCESS read-only
			STATUS current
			DESCRIPTION
				"Description.The Mac Address of this wsCcRfWiredWebAuthHostEntry"
			::= { wsCcRfWiredWebAuthHostEntry 2 }


		-- 1.3.6.1.4.1.388.14.3.2.1.21.5.1.3
		wsCcRfWiredWebAuthHostIp OBJECT-TYPE
			SYNTAX IpAddress
			MAX-ACCESS read-only
			STATUS current
			DESCRIPTION
				"Description. The IP address of this wsCcRfWiredWebAuthHosEntry"
			::= { wsCcRfWiredWebAuthHostEntry 3 }


		-- 1.3.6.1.4.1.388.14.3.2.1.21.5.1.4
		wsCcRfWiredWebAuthHostState OBJECT-TYPE
			SYNTAX INTEGER
				{
				unused(0),
				notAuthenticated(5),
				authenticated(7)
				}
			MAX-ACCESS read-only
			STATUS current
			DESCRIPTION
				"Description.The current state of this wsCcRfWiredWebAuthHostEntry"
			::= { wsCcRfWiredWebAuthHostEntry 4 }


		-- 1.3.6.1.4.1.388.14.3.2.1.21.5.1.5
		wsCcRfWiredWebAuthHostVlan OBJECT-TYPE
			SYNTAX Integer32
			MAX-ACCESS read-only
			STATUS current
			DESCRIPTION
				"Description.The Vlan assigned to this wsCcRfWiredWebAuthHostEntry"
			::= { wsCcRfWiredWebAuthHostEntry 5 }


		-- 1.3.6.1.4.1.388.14.3.2.1.22
		wsCcRfLldp OBJECT IDENTIFIER ::= { wsCcRfMIB 22 }


		-- 1.3.6.1.4.1.388.14.3.2.1.22.1
		wsCcRfLldpName OBJECT-TYPE
			SYNTAX DisplayString (SIZE (0..127))
			MAX-ACCESS read-write
			STATUS current
			DESCRIPTION
				"LLDP friendly name to be used in LLDP for adopted radio-ports."
			::= { wsCcRfLldp 1 }


		-- 1.3.6.1.4.1.388.14.3.2.1.22.2
		wsCcRfLldpApMacAddr OBJECT-TYPE
			SYNTAX PhysAddress
			MAX-ACCESS read-write
			STATUS current
			DESCRIPTION
				"The Mac address to be associated with LLDP friendly name."
			::= { wsCcRfLldp 2 }


		-- 1.3.6.1.4.1.388.14.3.2.1.22.3
		wsCcRfLldpNameSet OBJECT-TYPE
			SYNTAX INTEGER
				{
				idle(1),
				setLldpNames(2)
				}
			MAX-ACCESS read-write
			STATUS current
			DESCRIPTION
				"Configure the LLDP friendly name to be used in LLDP
				for adopted radio-ports.  If wsCcRfLldpApMacAddr
				is not specified, the LLDP friendly name update will
				be sent to all currently adpoted radio ports.  "
			::= { wsCcRfLldp 3 }


		-- 1.3.6.1.4.1.388.14.3.2.1.100
		wsCcRfConformance OBJECT IDENTIFIER ::= { wsCcRfMIB 100 }


		-- 1.3.6.1.4.1.388.14.3.2.1.100.1
		wsCcRfCompliances OBJECT IDENTIFIER ::= { wsCcRfConformance 1 }


		-- 1.3.6.1.4.1.388.14.3.2.1.100.1.1
		wsCcRfCompliance MODULE-COMPLIANCE
			STATUS current
			DESCRIPTION
				" "
			MODULE -- this module
				MANDATORY-GROUPS { wsCcRfGroup }
			::= { wsCcRfCompliances 1 }


		-- 1.3.6.1.4.1.388.14.3.2.1.100.2
		wsCcRfGroups OBJECT IDENTIFIER ::= { wsCcRfConformance 2 }


		-- 1.3.6.1.4.1.388.14.3.2.1.100.2.1
		wsCcRfGroup OBJECT-GROUP
			OBJECTS { wsCcRfApRadio1, wsCcRfApRadio2, wsCcRfRadioDefaultWmmAccessCategory, wsCcRfRadioDefaultWmmAdmissionCtrl, wsCcRfRadioDefaultWmmAifsn,
				wsCcRfRadioDefaultWmmTxOp, wsCcRfRadioDefaultWmmCwMin, wsCcRfRadioDefaultWmmCwMax, wsCcRfWlanNumRadiosAdopted, wsCcRfOversizedFrameEnable,
				wsCcRfMuIsWmm, wsCcRfWlanDescr, wsCcRfSelfHealingNeighborRecoveryEnable, wsCcRfSelfHealingInterferenceAvoidanceEnable, wsCcRfSelfHealingInterferenceAvoidanceRetriesx10,
				wsCcRfSelfHealingInterferenceAvoidanceHoldTime, wsCcRfSelfHealingMonitoringTransRadio, wsCcRfSelfHealingMonitoringRecvRadio, wsCcRfSelfHealingMonitoringChannel, wsCcRfSelfHealingMonitoringLastTime,
				wsCcRfSelfHealingMonitoringLastSignal, wsCcRfSelfHealingMonitoringMinSig, wsCcRfSelfHealingMonitoringMaxSig, wsCcRfSelfHealingMonitoringSumSig, wsCcRfSelfHealingMonitoringNumSig,
				wsCcRfRadioDefaultSelfHealingAction, wsCcRfHotspotPageType, wsCcRfHotspotIntPageTitle, wsCcRfHotspotIntPageHeader, wsCcRfHotspotIntPageDescr,
				wsCcRfHotspotIntPageFooter, wsCcRfHotspotIntPageImgUrl1, wsCcRfHotspotIntPageImgUrl2, wsCcRfHotspotExtPageUrl, wsCcRfRadioWmmAifsn,
				wsCcRf802dt1xRadioAuthLogin, wsCcRf802dt1xRadioAuthPass, wsCcRf802dt1xRadioAuthSetRadio, wsCcRfWlanWmmAifsn, wsCcRfSelfHealingNeighborRadioFirstRadio,
				wsCcRfSelfHealingNeighborRadioSecondRadio, wsCcRfSelfHealingNeighborRadioRowStatus, wsCcRfRadioStatusVlanTag, wsCcRfWlanEncP2WPassphrase, wsCcRfWlanEncP2WKey1,
				wsCcRfWlanEncP2WKey2, wsCcRfWlanEncP2WKey3, wsCcRfWlanEncP2WKey4, wsCcRfWlanMuIdleTime, wsCcRfRadioRunAcsNow,
				wsCcRfRadioResetParentAp, wsCcRfRadioReset, wsCcRfRadioDefaultIndex, wsCcRfRadioDefaultType, wsCcRfRadioDefaultApType,
				wsCcRfRadioDefaultBssWlanMap, wsCcRfRadioDefaultAntDiversity, wsCcRfRadioDefaultShortPreamble, wsCcRfRadioDefaultRtsThresh, wsCcRfRadioDefaultBeaconInt,
				wsCcRfRadioDefaultDtimPrd, wsCcRfRadioDefaultBasicRates, wsCcRfRadioDefaultSupportedRates, wsCcRfRadioDefaultRapDetector, wsCcRfRadioDefaultClusterIndex,
				wsCcRfRadioDefaultMaxMu, wsCcRfWlanEncP2WClearKeys, wsCcRfCountryCode, wsCcRfSnmpSetDelay, wsCcRfClusterIndex,
				wsCcRfProxyRespMuArpReq, wsCcRfLastError, wsCcRfApIndex, wsCcRfApNicMac, wsCcRfApModelNumber,
				wsCcRfApSerialNumber, wsCcRfApPcbRevision, wsCcRfApBootLoaderRev, wsCcRfApWispVersion, wsCcRfApRuntimeFwVersion,
				wsCcRfApNumRadios, wsCcRfApImageVersionIndex, wsCcRfApImageVersionApType, wsCcRfApImageVersionName, wsCcRfApUnadoptedIndex,
				wsCcRfApUnadoptedMac, wsCcRfApUnadoptedLastSeen, wsCcRfRadioAutoAdopt, wsCcRfRadioCnt, wsCcRfRadioIndex,
				wsCcRfRadioApMac, wsCcRfRadioDescr, wsCcRfRadioType, wsCcRfRadioApType, wsCcRfRadioBssWlanMap,
				wsCcRfRadioAntDiversity, wsCcRfRadioShortPreamble, wsCcRfRadioRtsThresh, wsCcRfRadioBeaconInt, wsCcRfRadioDtimPrd,
				wsCcRfRadioBasicRates, wsCcRfRadioSupportedRates, wsCcRfRadioRapDetector, wsCcRfRadioClusterIndex, wsCcRfRadioMaxMu,
				wsCcRfRadioRowStatus, wsCcRfRadioCpPlacement, wsCcRfRadioCpPosChannel, wsCcRfRadioCpDesChannel, wsCcRfRadioCpPosPowerDb,
				wsCcRfRadioCpDesPowerDb, wsCcRfRadioCpDesPowerMw, wsCcRfRadioCpSet, wsCcRfRadioCpReset, wsCcRfRadioStatusState,
				wsCcRfRadioStatusPtrToAp, wsCcRfRadioStatusMaxWlans, wsCcRfRadioStatusMaxBss, wsCcRfRadioStatusCurrChannel, wsCcRfRadioStatusCurrPowerDb,
				wsCcRfRadioStatusCurrPowerMw, wsCcRfRadioStatusAssociatedMus, wsCcRfRadioStatusLastAdoption, wsCcRfRadioStatusShortSlotTime, wsCcRfRadioWmmAccessCategory,
				wsCcRfRadioWmmAdmissionCtrl, wsCcRfRadioWmmTxOp, wsCcRfRadioWmmCwMin, wsCcRfRadioWmmCwMax, wsCcRfMuMac,
				wsCcRfMuWlanIndex, wsCcRfMuRadioIndex, wsCcRfMuVlanIndex, wsCcRfMuKeyIndex, wsCcRfMuIpAddr,
				wsCcRfMuBSS, wsCcRfMuAuthMethod, wsCcRfMuEncMethod, wsCcRfMuRadioType, wsCcRfMuPowerMode,
				wsCcRfMuSupportedRates, wsCcRfMuVoice, wsCcRfMuIsDataReady, wsCcRfMuRogueApEna, wsCcRfMuDisassociateNow,
				wsCcRfWlanIndex, wsCcRfWlanEnable, wsCcRfWlanEssid, wsCcRfWlanVlan, wsCcRfWlanSecBeacon,
				wsCcRfWlanVoicePrioritization, wsCcRfWlanAnswerBroadcastEss, wsCcRfWlanMulticastAddr1, wsCcRfWlanMulticastAddr2, wsCcRfWlanAuthentication,
				wsCcRfWlanEncryptionMap, wsCcRfWlanBcastEnc, wsCcRfWlanUseDscp, wsCcRfWlanAuthEapRadiusServerIp1, wsCcRfWlanAuthEapRadiusServerPort1,
				wsCcRfWlanAuthEapRadiusServerSecret1, wsCcRfWlanAuthEapRadiusServerIp2, wsCcRfWlanAuthEapRadiusServerPort2, wsCcRfWlanAuthEapRadiusServerSecret2, wsCcRfWlanAuthEapSuppRetries,
				wsCcRfWlanAuthEapSuppTimeout, wsCcRfWlanAuthEapServerRetries, wsCcRfWlanAuthEapServerTimeout, wsCcRfWlanAuthEapReauth, wsCcRfWlanAuthEapReauthTimeout,
				wsCcRfwlanAuthKerbRealm, wsCcRfWlanAuthKerbPassword, wsCcRfWlanAuthKerbKdcServerIp1, wsCcRfWlanAuthKerbKdcServerPort1, wsCcRfWlanAuthKerbKdcServerIp2,
				wsCcRfWlanAuthKerbKdcServerPort2, wsCcRfWlanEncSkEnable, wsCcRfWlanEncWep64KeyIndex, wsCcRfWlanEncWep64Key1, wsCcRfWlanEncWep64Key2,
				wsCcRfWlanEncWep64Key3, wsCcRfWlanEncWep64Key4, wsCcRfWlanEncWep128KgKeyIndex, wsCcRfWlanEncWep128KgKey1, wsCcRfWlanEncWep128KgKey2,
				wsCcRfWlanEncWep128KgKey3, wsCcRfWlanEncWep128KgKey4, wsCcRfWlanEncTkipCcmpKeyType, wsCcRfWlanEncTkipCcmpPassphrase, wsCcRfWlanEncTkipCcmpKey,
				wsCcRfWlanEncTkipCcmpKeyRotation, wsCcRfWlanEncTkipCcmpKeyInterval, wsCcRfWlanEncTkipCcmpPmkCaching, wsCcRfWlanEncTkipCcmpOppPmkCaching, wsCcRfWlanWmmAccessCategory,
				wsCcRfWlanWmmTxOp, wsCcRfWlanWmmCwMin, wsCcRfWlanWmmCwMax, wsCcRfMuAssocAclIndex, wsCcRfMuAssocAclMode,
				wsCcRfMuAssocAclStartingMac, wsCcRfMuAssocAclEndingMac, wsCcRfMuAssocAclWlans, wsCcRfRapMode, wsCcRfRapCfgIndex,
				wsCcRfRapCfgAnyMac, wsCcRfRapCfgMac, wsCcRfRapCfgAnySsid, wsCcRfRapCfgSsid, wsCcRfRapCfgRowStatus,
				wsCcRfRapStatusMac, wsCcRfRapStatusHeardAp, wsCcRfRapStatusChannel, wsCcRfRapStatusType, wsCcRfRapStatusSsid,
				wsCcRfRapStatusLastTimeSeen, wsCcRfRapStatusLastSignal, wsCcRfRapStatusMinSignal, wsCcRfRapStatusMaxSignal, wsCcRfRapStatusSumSignal,
				wsCcRfRapStatusSignalCount, wsCcRfMuAssocAclRowStatus, wsCcRfRadioDefaultCpPlacement, wsCcRfRadioDefaultCpPosChannel, wsCcRfRadioDefaultCpDesChannel,
				wsCcRfRadioDefaultCpPosPowerDb, wsCcRfRadioDefaultCpDesPowerDb, wsCcRfRadioDefaultCpDesPowerMw, wsCcRfRadioDefaultCpSet, wsCcRfRadioDefaultCpReset,
				wsCcRfHotspotServerRetries, wsCcRfHotspotServerTimeout, wsCcRfWlanPriorityEnable, wsCcRfApImageVersionModel, wsCcRfRadioCpChannelMode,
				wsCcRfRadioDefaultCpChannelMode, wsCcRfApCount, wsCcRfRadioStatusRadioMac, wsCcRfMuRoamCount, wsCcRfAdvancedConfigEnable,
				wsCcRfMuLastHeard, wsCcRfRadioSelfHealingPwrOffset, wsCcRfWlanSvpEnable, wsCcRfMuCnt, wsCcRfApImageVersionReleaseDate,
				wsCcRfApImageVersionImageSize, wsCcRfApUnadoptedApType, wsCcRfRadioLastMac, wsCcRfRadioLastReason, wsCcRfRadioSelfHealingAction,
				wsCcRfMuLastMac, wsCcRfSelfHealingDetectNeighborNow, wsCcRfHotspotServerIp1, wsCcRfHotspotServerPort1, wsCcRfHotspotServerSecret1,
				wsCcRfHotspotServerIp2, wsCcRfHotspotServerPort2, wsCcRfHotspotServerSecret2, wsCcRfHotspotWhiteIpRuleIndex, wsCcRfWlanAuthKerberosServerTimeout, wsCcRfWlanMobilityEnable, wsCcRfWlanGRETunnelGatewayIp, wsCcRfWlanGRETunnelGatewayMask,
				wsCcRfIdsStatusFilteredMuMac, wsCcRfHotspotWhiteIpAddr, wsCcRfRadioDefaultSelfHealingPwrOffset, wsCcRfWlanWmmEnable, wsCcRfWlanGRETunnelIdx,
				wsCcRfHotspotWebsiteType, wsCcRfWlanMuToMu, wsCcRfIdsClearMuIdsEventEntries, wsCcRfIdsEventLastOccurredTime, wsCcRfIdsEventType,
				wsCcRfWlanQosPrioritization, wsCcRfQosAcTo802dot1pPriority, wsCcRfQosAcTo802dot1pAccessCategory, wsCcRfQos802dot1pToAcAccessCategory, wsCcRfQos802dot1pToAcPriority,
				wsCcRfQosDscpToAcAccessCategory, wsCcRfQosDscpToAcDscp, wsCcRfQosDscpToAcIndex, wsCcRfQos802dot1pToAcIndex, wsCcRfWlanAuthEapAuthProtocol,
				wsCcRfWlanAuthEapDscpTos, wsCcRfApAddress, wsCcRfIdsStatusViolatnIndex, wsCcRfIdsStatusViolatnType, wsCcRfIdsStatusRadioIndex,
				wsCcRfApHistoryIndex, wsCcRfApHistoryRadioType, wsCcRfApHistoryTimestamp, wsCcRfApHistoryEvent, wsCcRfApHistoryReason,
				wsCcRfRadioHealingModeCnt, wsCcRfRadioNormalModeCnt, wsCcRfMuProbeRequestsAgeHeardOut, wsCcRfApHistoryMac, wsCcRfWlanDynamicVlanAssignment,
				wsCcRfRadioRapSingleChannelScan, wsCcRfRadioDefaultRapSingleChannelScan, wsCcRfIdsThresholdsMu, wsCcRfIdsThresholdsRadio, wsCcRfIdsThresholdsSwitch,
				wsCcRfIdsThresholdsFilterAgeout, wsCcRfIdsStatusRemainingBlacklistTime, wsCcRfIdsEventRadioIndex, wsCcRfIdsStatusRowStatus, wsCcRfIdsEventTotalCount,
				wsCcRfIdsEventCountSinceMidnight, wsCcRfWlanEncTkipCcmpPreauthentication, wsCcRfIdsThresholdsViolTypeIndex, wsCcRfWlanAuthEapAccountingMode, wsCcRfWlanAuthEapInterimAcctInterval,
				wsCcRfWlanAuthEapAcctTimeout, wsCcRfWlanAuthEapAcctRetries, wsCcRfWlanAuthPrimaryServer, wsCcRfWlanAuthEapSecondaryServer, wsCcRfWlanAuthEapPrimarySrvrPort,
				wsCcRfWlanAuthEapSecondarySrvrPort, wsCcRfWlanAuthEapPrimarySecret, wsCcRfWlanAuthEapSecondarySecret, wsCcRfWlanSyslogServerPort, wsCcRfWlanSyslogServerIp,
				wsCcRfWlanAccountingType, wsCcRfApHistoryEnable, wsCcRfApHistoryClear, wsCcRfMuHistoryEnable, wsCcRfMuHistoryClear,
				wsCcRfMuProbeHistoryEnable, wsCcRfMuProbeHistoryClear, wsCcRfWlanAuthEapRadiusMacAuthFormat, wsCcRfIdsViolCountLastDetWindow, wsCcRfIdsViolationType,
				wsCcRfIdsRadioIndex, wsCcRfRadioConfiguredCnt, wsCcRfRapMuAssistMode, wsCcRfRUnpprovedApTimeout, wsCcRfRApprovedApTimeout,
				wsCcRfRapMuAssistRefreshPeriod, wsCcRfLldpName, wsCcRfLldpNameSet, wsCcRfLldpApMacAddr, wsCcRfWiredWebAuthWlan,
				wsCcRfWiredWebAuthVlan, wsCcRfWiredWebAuthEnable, wsCcRfRadioBssDtim, wsCcRfRapMuAssistIndex, wsCcRfRapMuAssistMac,
				wsCcRfRapMuAssistFoundOnPrtl, wsCcRfRapMuAssistTimestamp, wsCcRfRapMuAssistSsid, wsCcRfRapMuAssistBss, wsCcRfRapMuAssistRssi,
				wsCcRfWiredWebAuthHostEntryDelete, wsCcRfWiredWebAuthHostVlan, wsCcRfWiredWebAuthHostIp, wsCcRfWiredWebAuthHostState, wsCcRfWiredWebAuthHostIndex,
				wsCcRfWiredWebAuthHostMac, wsCcRfMuQosInfo, wsCcRfRadioCfgMethod, wsCcRfRadioWmmAdmissionDeviceMax, wsCcRfMuProbeConfigIndex,
				wsCcRfMuProbeConfigMac, wsCcRfMuProbeConfigStatus, wsCcRfMuHistoryStatusRadioIndex, wsCcRfMuHistoryStatusWlanIndex, wsCcRfMuHistoryStatusTimestamp,
				wsCcRfMuHistoryStatusEvent, wsCcRfMuHistoryStatusMac, wsCcRfMuHistoryStatusIndex, wsCcRfWlanCount, wsCcRfIdsDetectionWindow,
				wsCcRfMuTunnelIndex, wsCcRfMuProbeStatusIndex, wsCcRfMuProbeStatusMac, wsCcRfMuProbeStatusTimeticks, wsCcRfMuProbeStatusSignalStrength,
				wsCcRfMuProbeStatusHeardRadio }
			STATUS current
			DESCRIPTION
				" "
			::= { wsCcRfGroups 1 }


		-- 1.3.6.1.4.1.388.14.3.2.1.100.2.2
		wsCcRfDeprecatedGroup OBJECT-GROUP
			OBJECTS { wsCcRfIdsMaxExcsvProbes, wsCcRfWlanDisallowMuToMu, wsCcRfHotspotPageLocation, wsCcRfWlanWeight, wsCcRfIdsMaxExcsvAssos,
				wsCcRfIdsMaxExcsvProbs, wsCcRfIdsMaxExcsvDisassos, wsCcRfIdsMaxExcsvAuthFailures, wsCcRfIdsMaxExcsvCryptoReplays, wsCcRfIdsMaxExcsv80211Replays,
				wsCcRfIdsMaxExcsvDecryptFails, wsCcRfIdsAnmlySrcMacEqDestMac, wsCcRfIdsAnmlyNullDestination, wsCcRfIdsAnmlySrcMulticastMac, wsCcRfIdsAnmlyWeakWepIv,
				wsCcRfIdsMuFilterAgeOutTime, wsCcRfIdsStatusFilteredMacMax, wsCcRfIdsEventPeriod, wsCcRfRapMaxRogue, wsCcRfRapTimeout,
				wsCcRfRadioStatusCfgMethod, wsCcRfWlanWmmAdmissionDeviceMax, wsCcRfWlanWmmAdmissionCtrl, wsCfRfMuProbeHistoryMac, wsCfRfMuProbeHistoryIndex,
				wsCfRfMuProbeHistoryTimeticks, wsCfRfMuProbeHistorySignalStrength, wsCfRfMuProbeHeardRadio, wsCcRfMuHistoryIndex, wsCcRfMuHistoryMac,
				wsCcRfMuHistoryRadioIndex, wsCcRfMuHistoryWlanIndex, wsCcRfMuHistoryTimestamp, wsCcRfMuHistoryEvent, wsCcRfRadioCcaLevel, wsCcRfRadioCcaMode, wsCcRfIdsMuFilterAgeOut,
				wsCcRfIdsMaxExcsvAssoc }
			STATUS deprecated
			DESCRIPTION
				"Group of deprecated objects."
			::= { wsCcRfGroups 2 }



	END

--
-- WS-CC-RF-MIB.my
--
