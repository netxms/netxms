RADLAN-rndMng DEFINITIONS ::= BEGIN

-- Title:      RADLAN Management Private Extension
-- Version:    7.45
-- Date:       19 Dec 2006
-- 28-Feb-2005  Added   rlCpuUtilEnable
-- 28-Feb-2005  Added   rlCpuUtilDuringLastSecond
-- 28-Feb-2005  Added   rlCpuUtilDuringLastMinute
-- 28-Feb-2005  Added   rlCpuUtilDuringLast5Minutes
-- 13-Jun-2006  Added   value {none} of rndAction
-- 20-Jun-2006  Added   rlRebootDelay
-- 19-Dec-2006  Added   resetToFactoryDefaults

IMPORTS
    rnd                                                     FROM RADLAN-MIB
    DisplayString                                           FROM SNMPv2-TC
    Unsigned32,
    MODULE-IDENTITY, OBJECT-TYPE, TimeTicks                 FROM SNMPv2-SMI
    RowStatus, TruthValue,
    TEXTUAL-CONVENTION                                      FROM SNMPv2-TC;


rndMng  MODULE-IDENTITY
        LAST-UPDATED "200606200000Z"
        ORGANIZATION "Radlan Computer Communications Ltd."
        CONTACT-INFO
             "radlan.com"
        DESCRIPTION
             "The private MIB module definition for RND general management MIB."
        REVISION "200606200000Z"
        DESCRIPTION
             "Added rlRebootDelay object"
        REVISION "200406010000Z"
        DESCRIPTION
             "Initial version of this MIB."
        ::= { rnd 1 }


rndSysId OBJECT-TYPE
    SYNTAX  INTEGER
    MAX-ACCESS  read-only
    STATUS      current
    DESCRIPTION
      "Identification of an RND device. The device type for each
      integer clarifies the sysObjectID in MIB - II."
    ::= { rndMng 1  }

rndAction OBJECT-TYPE
    SYNTAX  INTEGER {
       reset(1),
       sendNetworkTab(2),
       deleteNetworkTab(3),
       sendRoutingTab(4),    -- Level II
       deleteRoutingTab(5),
       sendLanTab(6),
       deleteLanTab(7),
       deleteArpTab(8),
       sendArpTab(9),
       deleteRouteTab(10),   -- Level III
       sendRouteTab(11),
       backupSPFRoutingTab(12),
       backupIPRoutingTab(13),
       backupNetworkTab(14),
       backupLanTab(15),
       backupArpTab(16),
       backupIPXRipTab(17),
       backupIPXSAPTab(18),
       resetStartupCDB(19),
       eraseStartupCDB(20),
       deleteZeroHopRoutingAllocTab(21),
       slipDisconnect(22),
       deleteDynamicLanTab(23),
       eraseRunningCDB(24),
       copyStartupToRunning(25),
       none(26),
       resetToFactoryDefaults(27)
     }
    MAX-ACCESS  read-write
    STATUS      current
    DESCRIPTION
      "This variable enables the operator to perform one of the
      specified actions on the tables maintained by the network device.
      Send actions require support of proprietery File exchange
      protocol."
   ::= { rndMng 2  }

rndFileName OBJECT-TYPE
    SYNTAX OCTET STRING -- SIZE 256
    MAX-ACCESS  read-write
    STATUS      current
    DESCRIPTION
      "The name of the file used internally by RND for transferring
      tables maintained by network devices, using a prorietary File
      exchange protocol."
    ::=  { rndMng 3  }

rlSnmpVersionSupported OBJECT-TYPE
    SYNTAX      OCTET STRING (SIZE(1))
    MAX-ACCESS  read-only
    STATUS      current
    DESCRIPTION
        "Indicates the snmp versions that are supported by
        this device."
    ::= { rndMng 4 }

rlSnmpMibVersion OBJECT-TYPE
    SYNTAX      INTEGER
    MAX-ACCESS  read-only
    STATUS      current
    DESCRIPTION
        "Indicates the snmp support version that is supported by
        this device."
    ::= { rndMng 5 }

rlCpuUtilEnable OBJECT-TYPE
    SYNTAX TruthValue
    MAX-ACCESS  read-write
    STATUS      current
    DESCRIPTION
        "Enables measurement of the device CPU utilization.
         In order to get real values for rlCpuUtilDuringLastSecond, rlCpuUtilDuringLastMinute
         and rlCpuUtilDuringLast5Minutes, the value of this object must be true."
    DEFVAL { true }
    ::= { rndMng 6 }

rlCpuUtilDuringLastSecond OBJECT-TYPE
    SYNTAX INTEGER (0..101)
    MAX-ACCESS  read-only
    STATUS      current
    DESCRIPTION
        "Percentage of the device CPU utilization during last second.
         The value 101 is a dummy value, indicating that the CPU utilization was
         not measured (since measurement is disabled or was disabled during last second)."
    ::= { rndMng 7 }

rlCpuUtilDuringLastMinute OBJECT-TYPE
    SYNTAX INTEGER (0..101)
    MAX-ACCESS  read-only
    STATUS      current
    DESCRIPTION
        "Percentage of the device CPU utilization during last minute.
         The value 101 is a dummy value, indicating that the CPU utilization was
         not measured (since measurement is disabled or was disabled during last minute)."
    ::= { rndMng 8 }

rlCpuUtilDuringLast5Minutes OBJECT-TYPE
    SYNTAX INTEGER (0..101)
    MAX-ACCESS  read-only
    STATUS      current
    DESCRIPTION
        "Percentage of the device CPU utilization during the last 5 minutes.
         The value 101 is a dummy value, indicating that the CPU utilization was
         not measured (since measurement is disabled or was disabled during last 5 minutes)."
    ::= { rndMng 9 }

rlRebootDelay OBJECT-TYPE
    SYNTAX TimeTicks
    MAX-ACCESS  read-write
    STATUS      current
    DESCRIPTION
        "Setting the variable will cause the device to reboot rlRebootDelay timeticks
         from the moment this variable was set.
         If not set, the variable will return a value of 4294967295.
         If set to 4294967295, reboot action is cancelled.
         The maximum delay is set by the host parameter: reboot_delay_max"
    ::= { rndMng 10 }

END
