-- OUTBOUND TELNET MIB overview:
-- OUTBOUND TELNET MIB falls under dnOS MIB node of the private subtree.



DNOS-OUTBOUNDTELNET-PRIVATE-MIB DEFINITIONS ::= BEGIN

-- Dell DNOS OUTBOUND TELNET MIB
-- Copyright Dell (2002-2007)  All rights reserved.

-- This SNMP Management Information Specification
-- embodies Dell's confidential and proprietary
-- intellectual property.  Dell retains all title
-- and ownership in the Specification including any revisions.

-- This Specification is supplied "AS IS", Dell
-- makes no warranty, either expressed or implied,
-- as to the use, operation, condition, or performance of the
-- Specification.



IMPORTS
    MODULE-IDENTITY, OBJECT-TYPE, Integer32               FROM SNMPv2-SMI
    dnOS                                              FROM DELL-REF-MIB;

    fastPathOutboundTelnetPrivate MODULE-IDENTITY
           LAST-UPDATED "201101260000Z" -- 26 January 2011 12:00:00 GMT
           ORGANIZATION "Dell, Inc."
           CONTACT-INFO ""
      DESCRIPTION
          "The Broadcom Private MIB for DNOS Outbound Telnet"

      -- Revision history.
      REVISION
          "201101260000Z" -- 26 January 2011 12:00:00 GMT
      DESCRIPTION
          "Add new Postal address change."
      REVISION
          "200705230000Z" -- 23 May 2007 12:00:00 GMT
      DESCRIPTION
          "Dell branding related changes."

      ::= { dnOS 19 }


     --**************************************************************************************
    -- agentOutboundTelnetGroup -> contains MIB objects displaying various properties of a Outbound Telnet
    --
    --**************************************************************************************

    agentOutboundTelnetGroup       OBJECT IDENTIFIER ::= { fastPathOutboundTelnetPrivate 1 }

    agentOutboundTelnetAdminMode OBJECT-TYPE
      SYNTAX      INTEGER {
                  enable(1),
                  disable(2)
                  }
      MAX-ACCESS read-write
      STATUS     current
      DESCRIPTION
       " Admin-mode of the Outbound Telnet."
      DEFVAL { enable }
    ::= { agentOutboundTelnetGroup 1 }


    agentOutboundTelnetMaxNoOfSessions OBJECT-TYPE
      SYNTAX     INTEGER (0..5)
      MAX-ACCESS read-write
      STATUS     current
      DESCRIPTION
       " The maximum no. of Outbound Telnet sessions allowed."
      DEFVAL { 5 }
    ::= { agentOutboundTelnetGroup 2 }

    agentOutboundTelnetTimeout OBJECT-TYPE
    SYNTAX  INTEGER (0..65535)
                MAX-ACCESS read-write
                STATUS current
                DESCRIPTION
                        "The login inactivity timeout value for Outbound Telnet."
    ::= { agentOutboundTelnetGroup 3 }
END
