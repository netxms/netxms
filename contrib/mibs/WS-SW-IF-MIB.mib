-- vim: syntax=mib
--
-- WS-SW-IF-MIB.my
-- MIB generated by MG-SOFT Visual MIB Builder Version 6.0  Build 88
-- Friday, November 03, 2006 at 13:59:03
--

	WS-SW-IF-MIB DEFINITIONS ::= BEGIN

		IMPORTS
			OBJECT-GROUP, MODULE-COMPLIANCE
				FROM SNMPv2-CONF
			Integer32, OBJECT-TYPE, MODULE-IDENTITY
				FROM SNMPv2-SMI
			TruthValue, DisplayString, PhysAddress, RowStatus
				FROM SNMPv2-TC
			wsSwIf
				FROM WS-SW-SMI;


		-- 1.3.6.1.4.1.388.14.2.4.1
		wsIfModule MODULE-IDENTITY
			LAST-UPDATED "200505051458Z"		-- May 05, 2005 at 14:58 GMT
			ORGANIZATION
				"Symbol Technologies"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"WS IF Module"
			REVISION "200611031358Z"		-- November 03, 2006 at 13:58 GMT
			DESCRIPTION
				"02a14"
			REVISION "200611011005Z"		-- November 01, 2006 at 10:05 GMT
			DESCRIPTION
				"02a13"
			REVISION "200610311213Z"		-- October 31, 2006 at 12:13 GMT
			DESCRIPTION
				"02a12"
			REVISION "200610311118Z"		-- October 31, 2006 at 11:18 GMT
			DESCRIPTION
				"02a11"
			REVISION "200610301708Z"		-- October 30, 2006 at 17:08 GMT
			DESCRIPTION
				"02a10"
			REVISION "200610301103Z"		-- October 30, 2006 at 11:03 GMT
			DESCRIPTION
				"02a09"
			REVISION "200610271237Z"		-- October 27, 2006 at 12:37 GMT
			DESCRIPTION
				"02a08"
			REVISION "200610261018Z"		-- October 26, 2006 at 10:18 GMT
			DESCRIPTION
				"02a07"
			REVISION "200610251558Z"		-- October 25, 2006 at 15:58 GMT
			DESCRIPTION
				"02a06"
			REVISION "200610251101Z"		-- October 25, 2006 at 11:01 GMT
			DESCRIPTION
				"02a05"
			REVISION "200610201759Z"		-- October 20, 2006 at 17:59 GMT
			DESCRIPTION
				"02a04"
			REVISION "200605241656Z"		-- May 24, 2006 at 16:56 GMT
			DESCRIPTION
				"02a03"
			REVISION "200604271521Z"		-- April 27, 2006 at 15:21 GMT
			DESCRIPTION
				"02a02"
			REVISION "200604171412Z"		-- April 17, 2006 at 14:12 GMT
			DESCRIPTION
				"02a01"
			REVISION "200603211309Z"		-- March 21, 2006 at 13:09 GMT
			DESCRIPTION
				"01a12"
			REVISION "200603021122Z"		-- March 02, 2006 at 11:22 GMT
			DESCRIPTION
				"01a11"
			REVISION "200508031128Z"		-- August 03, 2005 at 11:28 GMT
			DESCRIPTION
				"01a10"
			REVISION "200506141810Z"		-- June 14, 2005 at 18:10 GMT
			DESCRIPTION
				"01a09"
			REVISION "200506141707Z"		-- June 14, 2005 at 17:07 GMT
			DESCRIPTION
				"01a08"
			REVISION "200506141635Z"		-- June 14, 2005 at 16:35 GMT
			DESCRIPTION
				"01a07"
			REVISION "200506021110Z"		-- June 02, 2005 at 11:10 GMT
			DESCRIPTION
				"01a06"
			REVISION "200506011025Z"		-- June 01, 2005 at 10:25 GMT
			DESCRIPTION
				"01a05"
			REVISION "200505311716Z"		-- May 31, 2005 at 17:16 GMT
			DESCRIPTION
				"01a04,rename the mib"
			REVISION "200505241734Z"		-- May 24, 2005 at 17:34 GMT
			DESCRIPTION
				"01a03"
			REVISION "200505241336Z"		-- May 24, 2005 at 13:36 GMT
			DESCRIPTION
				"01a02"
			REVISION "200505121342Z"		-- May 12, 2005 at 13:42 GMT
			DESCRIPTION
				"01a01"
			::= { wsSwIf 1 }
--




--
-- Node definitions
--

		-- 1.3.6.1.4.1.388.14.2.4.1.1
		wsIfTable OBJECT-TYPE
			SYNTAX SEQUENCE OF WsIfEntry
			MAX-ACCESS not-accessible
			STATUS current
			DESCRIPTION
				"ws IF table"
			::= { wsIfModule 1 }


		-- 1.3.6.1.4.1.388.14.2.4.1.1.1
		wsIfEntry OBJECT-TYPE
			SYNTAX WsIfEntry
			MAX-ACCESS not-accessible
			STATUS current
			DESCRIPTION
				"ws IF table entry"
			INDEX { wsIfHWType, wsIfNumber }
			::= { wsIfTable 1 }


		WsIfEntry ::=
			SEQUENCE {
				wsIfHWType
					INTEGER,
				wsIfNumber
					INTEGER,
				wsIfMTU
					Integer32,
				wsIfSpeed
					INTEGER,
				wsIfAdminSpeed
					INTEGER,
				wsIfDuplex
					INTEGER,
				wsIfAdminDuplex
					INTEGER,
				wsIfDHCPEnable
					TruthValue,
				wsIfIndex
					Integer32,
				wsIfType
					INTEGER,
				wsIfName
					DisplayString,
				wsIfRowStatus
					RowStatus,
				wsIfDescr
					DisplayString,
				wsIfMaxSpeed
					INTEGER,
				wsIfMgmtAllowed
					TruthValue,
				wsIfMedType
					INTEGER,
				wsIfAdminMedType
					INTEGER,
				wsIfMedTypeSupported
					INTEGER,
				wsIfVlanMappingAllowed
					TruthValue
			 }

		-- 1.3.6.1.4.1.388.14.2.4.1.1.1.1
		wsIfHWType OBJECT-TYPE
			SYNTAX INTEGER
				{
				eth(1),
				loopBack(2),
				vlan(3),
				gre(4),
				mlt(5)
				}
			MAX-ACCESS read-only
			STATUS current
			DESCRIPTION
				"ws IF hardware type"
			::= { wsIfEntry 1 }


		-- 1.3.6.1.4.1.388.14.2.4.1.1.1.2
		wsIfNumber OBJECT-TYPE
			SYNTAX INTEGER (1..4095)
			MAX-ACCESS read-only
			STATUS current
			DESCRIPTION
				"ws IF number"
			::= { wsIfEntry 2 }


		-- 1.3.6.1.4.1.388.14.2.4.1.1.1.3
		wsIfMTU OBJECT-TYPE
			SYNTAX Integer32 (64..2000)
			MAX-ACCESS read-create
			STATUS current
			DESCRIPTION
				"ws IF MTU, read/write"
			::= { wsIfEntry 3 }


		-- 1.3.6.1.4.1.388.14.2.4.1.1.1.4
		wsIfSpeed OBJECT-TYPE
			SYNTAX INTEGER
				{
				unknown(0),
				tenMbps(1),
				hundredMbps(2),
				thousandMbps(3)
				}
			MAX-ACCESS read-only
			STATUS current
			DESCRIPTION
				"ws IF speed"
			::= { wsIfEntry 4 }


		-- 1.3.6.1.4.1.388.14.2.4.1.1.1.5
		wsIfAdminSpeed OBJECT-TYPE
			SYNTAX INTEGER
				{
				tenMbps(1),
				hundredMbps(2),
				thousandMbps(3),
				auto(4)
				}
			MAX-ACCESS read-create
			STATUS current
			DESCRIPTION
				"ws IF speed, read/write, not applicable in vlan"
			DEFVAL { auto }
			::= { wsIfEntry 5 }


		-- 1.3.6.1.4.1.388.14.2.4.1.1.1.6
		wsIfDuplex OBJECT-TYPE
			SYNTAX INTEGER
				{
				unknown(0),
				halfDuplex(1),
				fullDuplex(2)
				}
			MAX-ACCESS read-only
			STATUS current
			DESCRIPTION
				"ws IF duplex"
			::= { wsIfEntry 6 }


		-- 1.3.6.1.4.1.388.14.2.4.1.1.1.7
		wsIfAdminDuplex OBJECT-TYPE
			SYNTAX INTEGER
				{
				halfDuplex(1),
				fullDuplex(2),
				auto(3)
				}
			MAX-ACCESS read-create
			STATUS current
			DESCRIPTION
				"ws IF duplex, read/write, not applicable in vlan"
			::= { wsIfEntry 7 }


		-- 1.3.6.1.4.1.388.14.2.4.1.1.1.8
		wsIfDHCPEnable OBJECT-TYPE
			SYNTAX TruthValue
			MAX-ACCESS read-create
			STATUS current
			DESCRIPTION
				"ws IF DHCP enable, read/write"
			::= { wsIfEntry 8 }


		-- 1.3.6.1.4.1.388.14.2.4.1.1.1.9
		wsIfIndex OBJECT-TYPE
			SYNTAX Integer32
			MAX-ACCESS read-only
			STATUS current
			DESCRIPTION
				"if Index number"
			::= { wsIfEntry 9 }


		-- 1.3.6.1.4.1.388.14.2.4.1.1.1.10
		wsIfType OBJECT-TYPE
			SYNTAX INTEGER
				{
				layer2(1),
				layer3(2)
				}
			MAX-ACCESS read-only
			STATUS current
			DESCRIPTION
				"ws if type, specify it is layer 2 or layer 3 interface"
			::= { wsIfEntry 10 }


		-- 1.3.6.1.4.1.388.14.2.4.1.1.1.11
		wsIfName OBJECT-TYPE
			SYNTAX DisplayString
			MAX-ACCESS read-only
			STATUS current
			DESCRIPTION
				"ws if name, a display string"
			::= { wsIfEntry 11 }


		-- 1.3.6.1.4.1.388.14.2.4.1.1.1.12
		wsIfRowStatus OBJECT-TYPE
			SYNTAX RowStatus
			MAX-ACCESS read-create
			STATUS current
			DESCRIPTION
				"row status, only createAndGo, destroy, active are supported,
				and only create a vlan is supported"
			::= { wsIfEntry 12 }


		-- 1.3.6.1.4.1.388.14.2.4.1.1.1.13
		wsIfDescr OBJECT-TYPE
			SYNTAX DisplayString
			MAX-ACCESS read-create
			STATUS current
			DESCRIPTION
				"Description."
			::= { wsIfEntry 13 }


		-- 1.3.6.1.4.1.388.14.2.4.1.1.1.14
		wsIfMaxSpeed OBJECT-TYPE
			SYNTAX INTEGER
				{
				unknown(0),
				tenMBps(1),
				hundredMBps(2),
				thousandMBps(3)
				}
			MAX-ACCESS read-only
			STATUS current
			DESCRIPTION
				"Description."
			::= { wsIfEntry 14 }


		-- 1.3.6.1.4.1.388.14.2.4.1.1.1.15
		wsIfMgmtAllowed OBJECT-TYPE
			SYNTAX TruthValue
			MAX-ACCESS read-only
			STATUS current
			DESCRIPTION
				"indicates if this interface is available for mgmt port"
			::= { wsIfEntry 15 }
-- may become read-write in future platforms

		-- 1.3.6.1.4.1.388.14.2.4.1.1.1.16
		wsIfMedType OBJECT-TYPE
			SYNTAX INTEGER
				{
				fiber(1),
				copper(2),
				none(3)
				}
			MAX-ACCESS read-only
			STATUS current
			DESCRIPTION
				"the current port medium type
				 "
			::= { wsIfEntry 16 }


		-- 1.3.6.1.4.1.388.14.2.4.1.1.1.17
		wsIfAdminMedType OBJECT-TYPE
			SYNTAX INTEGER
				{
				fiber(1),
				copper(2),
				auto(3)
				}
			MAX-ACCESS read-create
			STATUS current
			DESCRIPTION
				"the admin Med Type, only settable in QS5 for ge port. "
			::= { wsIfEntry 17 }


		-- 1.3.6.1.4.1.388.14.2.4.1.1.1.18
		wsIfMedTypeSupported OBJECT-TYPE
			SYNTAX INTEGER
				{
				fiber(1),
				copper(2),
				both(3),
				none(4)
				}
			MAX-ACCESS read-only
			STATUS current
			DESCRIPTION
				"the possilbe option for the current port med type supported"
			::= { wsIfEntry 18 }


		-- 1.3.6.1.4.1.388.14.2.4.1.1.1.19
		wsIfVlanMappingAllowed OBJECT-TYPE
			SYNTAX TruthValue
			MAX-ACCESS read-only
			STATUS current
			DESCRIPTION
				"indicate if vlan mapping is allowed on this port"
			::= { wsIfEntry 19 }


		-- 1.3.6.1.4.1.388.14.2.4.1.2
		wsIfMgmtIfname OBJECT-TYPE
			SYNTAX DisplayString
			MAX-ACCESS read-write
			STATUS current
			DESCRIPTION
				"mgmt interface name of this platform"
			::= { wsIfModule 2 }


		-- 1.3.6.1.4.1.388.14.2.4.1.3
		wsIfRonIfName OBJECT-TYPE
			SYNTAX DisplayString
			MAX-ACCESS read-write
			STATUS current
			DESCRIPTION
				"Ron interface name of this platform."
			::= { wsIfModule 3 }


		-- 1.3.6.1.4.1.388.14.2.4.1.4
		wsIfWlanIfName OBJECT-TYPE
			SYNTAX DisplayString
			MAX-ACCESS read-write
			STATUS current
			DESCRIPTION
				"only applied in whistler"
			::= { wsIfModule 4 }


		-- 1.3.6.1.4.1.388.14.2.4.1.5
		wsIfMgmtOptions OBJECT-TYPE
			SYNTAX INTEGER
				{
				vlanOnly(1),
				phyOnly(2),
				both(3)
				}
			MAX-ACCESS read-only
			STATUS current
			DESCRIPTION
				"Describe what choice are available in the current platform. For whistler/monarch,
				it is vlanOnly(1).For quicksilver, it is both(3)"
			::= { wsIfModule 5 }


		-- 1.3.6.1.4.1.388.14.2.4.1.6
		wsIfMgmtOptionState OBJECT-TYPE
			SYNTAX INTEGER
				{
				vlanOnly(1),
				phyOnly(2),
				both(3)
				}
			MAX-ACCESS read-write
			STATUS current
			DESCRIPTION
				"Describe what choice are in effect in the current platform. For whistler/monarch/quicksilver,
				this attribute is read-only, setting it will get a GEN_ERR response. For whislter/monarch,
				the value is vlanOnly(1). For quicksilver, the value is both(3)
				"
			::= { wsIfModule 6 }


		-- 1.3.6.1.4.1.388.14.2.4.1.7
		wsIfMedDefault OBJECT-TYPE
			SYNTAX INTEGER
				{
				fiber(1),
				copper(2),
				none(3)
				}
			MAX-ACCESS read-write
			STATUS current
			DESCRIPTION
				"The default medium for the port. Only writable in quick silver. In whislter/monarch,
				write it will return a GEN_ERR."
			::= { wsIfModule 7 }


		-- 1.3.6.1.4.1.388.14.2.4.1.8
		wsIfMedDefaultSupported OBJECT-TYPE
			SYNTAX INTEGER
				{
				fiber(1),
				copper(2),
				both(3)
				}
			MAX-ACCESS read-only
			STATUS current
			DESCRIPTION
				"the possible option for default med type supported"
			::= { wsIfModule 8 }


		-- 1.3.6.1.4.1.388.14.2.4.1.10
		wsIfManagementSecure OBJECT-TYPE
			SYNTAX TruthValue
			MAX-ACCESS read-write
			STATUS current
			DESCRIPTION
				"When this object is set to true, the management traffic is allowed
				only through the management port on the switch.  When this object is
				set to false, the management traffic is allowed through any port on
				the switch.
				"
			::= { wsIfModule 10 }


		-- 1.3.6.1.4.1.388.14.2.4.1.11
		wsIfSwitchMacAddress OBJECT-TYPE
			SYNTAX PhysAddress
			MAX-ACCESS read-only
			STATUS current
			DESCRIPTION
				"The MAC address of the interface representative of this wireless switch."
			::= { wsIfModule 11 }


		-- 1.3.6.1.4.1.388.14.2.4.1.100
		wsIfConformance OBJECT IDENTIFIER ::= { wsIfModule 100 }


		-- 1.3.6.1.4.1.388.14.2.4.1.100.1
		wsIfCompliances OBJECT IDENTIFIER ::= { wsIfConformance 1 }


		-- 1.3.6.1.4.1.388.14.2.4.1.100.1.1
		wsIfCompliance MODULE-COMPLIANCE
			STATUS current
			DESCRIPTION
				"Description."
			MODULE -- this module
				MANDATORY-GROUPS { wsIfGroup }
			::= { wsIfCompliances 1 }


		-- 1.3.6.1.4.1.388.14.2.4.1.100.2
		wsIfGroups OBJECT IDENTIFIER ::= { wsIfConformance 2 }


		-- 1.3.6.1.4.1.388.14.2.4.1.100.2.1
		wsIfGroup OBJECT-GROUP
			OBJECTS { wsIfNumber, wsIfMTU, wsIfSpeed, wsIfAdminSpeed, wsIfDuplex,
				wsIfAdminDuplex, wsIfDHCPEnable, wsIfRowStatus, wsIfIndex, wsIfName,
				wsIfMgmtIfname, wsIfRonIfName, wsIfWlanIfName, wsIfDescr, wsIfMaxSpeed,
				wsIfMgmtAllowed, wsIfVlanMappingAllowed, wsIfMedDefaultSupported, wsIfMedTypeSupported, wsIfType,
				wsIfHWType, wsIfMedType, wsIfAdminMedType, wsIfMedDefault, wsIfMgmtOptions,
				wsIfMgmtOptionState }
			STATUS current
			DESCRIPTION
				"Description."
			::= { wsIfGroups 1 }



	END

--
-- WS-SW-IF-MIB.my
--
