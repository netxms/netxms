-- vim: syntax=mib
--
-- WS-SW-SNMP-SAVE-MIB.my
-- MIB generated by MG-SOFT Visual MIB Builder Version 6.0  Build 88
-- Thursday, June 22, 2006 at 19:03:41
--

	WS-SW-SNMP-SAVE-MIB DEFINITIONS ::= BEGIN

		IMPORTS
			OBJECT-GROUP, MODULE-COMPLIANCE
				FROM SNMPv2-CONF
			Integer32, OBJECT-TYPE, MODULE-IDENTITY
				FROM SNMPv2-SMI
			DisplayString
				FROM SNMPv2-TC
			wsSwSnmpSave
				FROM WS-SW-SMI;


		-- 1.3.6.1.4.1.388.14.2.6.1
		wsSwSnmpSaveModule MODULE-IDENTITY
			LAST-UPDATED "200606220703Z"		-- June 22, 2006 at 07:03 GMT
			ORGANIZATION
				"Symbol Technologies"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"Description."
			REVISION "200606221903Z"		-- June 22, 2006 at 19:03 GMT
			DESCRIPTION
				"01a06"
			REVISION "200606191630Z"		-- June 19, 2006 at 16:30 GMT
			DESCRIPTION
				"01a05"
			REVISION "200605261441Z"		-- May 26, 2006 at 14:41 GMT
			DESCRIPTION
				"01a04"
			REVISION "200605260116Z"		-- May 26, 2006 at 01:16 GMT
			DESCRIPTION
				"01a03"
			REVISION "200605171530Z"		-- May 17, 2006 at 15:30 GMT
			DESCRIPTION
				"01a02"
			REVISION "200509191117Z"		-- September 19, 2005 at 11:17 GMT
			DESCRIPTION
				"01a01"
			::= { wsSwSnmpSave 1 }




--
-- Node definitions
--

		-- 1.3.6.1.4.1.388.14.2.6.1.1
		wsSwSnmpSaveSet OBJECT-TYPE
			SYNTAX INTEGER
				{
				idle(1),
				save(2)
				}
			MAX-ACCESS read-write
			STATUS current
			DESCRIPTION
				"Description."
			::= { wsSwSnmpSaveModule 1 }


		-- 1.3.6.1.4.1.388.14.2.6.1.2
		wsSwSnmpSaveSavedCfgChangeCounter OBJECT-TYPE
			SYNTAX Integer32
			MAX-ACCESS read-only
			STATUS current
			DESCRIPTION
				"This value indicates the number of times the 'save config' was performed through CLI/SNMP/Applet."
			::= { wsSwSnmpSaveModule 2 }


		-- 1.3.6.1.4.1.388.14.2.6.1.3
		wsSwSnmpSaveUserRole OBJECT-TYPE
			SYNTAX BITS
				{
				monitor(0),
				helpDesk(1),
				networkAdmin(2),
				systemAdmin(3),
				webUserAdmin(4),
				superUser(5)
				}
			MAX-ACCESS read-write
			STATUS current
			DESCRIPTION
				"Specifies user privilege level for the currently logged on user."
			::= { wsSwSnmpSaveModule 3 }


		-- 1.3.6.1.4.1.388.14.2.6.1.4
		wsSwSnmpSaveStartupConfigStatus OBJECT-TYPE
			SYNTAX INTEGER
				{
				success(1),
				failure(2)
				}
			MAX-ACCESS read-only
			STATUS current
			DESCRIPTION
				"The status of config playback during startup.
				This tells the user if any of the configuration commands failed."
			::= { wsSwSnmpSaveModule 4 }


		-- 1.3.6.1.4.1.388.14.2.6.1.5
		wsSwSnmpSaveStartupConfigErroneousCmdLine OBJECT-TYPE
			SYNTAX DisplayString
			MAX-ACCESS read-only
			STATUS current
			DESCRIPTION
				"The erroneous line in the startup-config which failed to get applied at bootup."
			::= { wsSwSnmpSaveModule 5 }


		-- 1.3.6.1.4.1.388.14.2.6.1.100
		wsSwSnmpSaveComformance OBJECT IDENTIFIER ::= { wsSwSnmpSaveModule 100 }


		-- 1.3.6.1.4.1.388.14.2.6.1.100.1
		wsSwSnmpSaveComformances OBJECT IDENTIFIER ::= { wsSwSnmpSaveComformance 1 }


		-- 1.3.6.1.4.1.388.14.2.6.1.100.1.1
		wsSwSnmpSaveComformaces MODULE-COMPLIANCE
			STATUS current
			DESCRIPTION
				"Description."
			MODULE -- this module
				MANDATORY-GROUPS { wsSwSnmpSaveGroup }
			::= { wsSwSnmpSaveComformances 1 }


		-- 1.3.6.1.4.1.388.14.2.6.1.100.2
		wsSwSnmpSaveGroups OBJECT IDENTIFIER ::= { wsSwSnmpSaveComformance 2 }


		-- 1.3.6.1.4.1.388.14.2.6.1.100.2.1
		wsSwSnmpSaveGroup OBJECT-GROUP
			OBJECTS { wsSwSnmpSaveSet, wsSwSnmpSaveSavedCfgChangeCounter, wsSwSnmpSaveUserRole, wsSwSnmpSaveStartupConfigStatus, wsSwSnmpSaveStartupConfigErroneousCmdLine
				 }
			STATUS current
			DESCRIPTION
				"Description."
			::= { wsSwSnmpSaveGroups 1 }



	END

--
-- WS-SW-SNMP-SAVE-MIB.my
--
