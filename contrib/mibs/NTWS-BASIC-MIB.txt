NTWS-BASIC-MIB DEFINITIONS ::= BEGIN

IMPORTS
    MODULE-IDENTITY, OBJECT-TYPE, IpAddress
	FROM SNMPv2-SMI
    DisplayString
	FROM SNMPv2-TC
    NtwsLicenseFeature
	FROM NTWS-LICENSE-FEATURE-TC-MIB
    ntwsMibs
	FROM NTWS-ROOT-MIB;

ntwsBasic MODULE-IDENTITY
    LAST-UPDATED "200911160010Z"
    ORGANIZATION "Nortel Networks"
    CONTACT-INFO
        "www.nortelnetworks.com"
    DESCRIPTION
	"Basic objects for Nortel Networks wireless switches.

        Copyright 2009 Nortel Networks.
        All rights reserved.
        This Nortel Networks SNMP Management Information Base Specification
        (Specification) embodies Nortel Networks' confidential and
        proprietary intellectual property.

        This Specification is supplied 'AS IS' and Nortel Networks
        makes no warranty, either express or implied, as to the use,
        operation, condition, or performance of the Specification."

    REVISION "200911160010Z"
    DESCRIPTION "v3.0.0: Moved NtwsLicenseFeature into its own module
                         for easier maintenance."

    REVISION "200708160009Z"
    DESCRIPTION "v2.0.7, MRT v3: Made changes in order to make MIB compile
                 cleanly and comply with corporate MIB conventions."

    REVISION "200607100008Z"
    DESCRIPTION "v2.0.6: Fixed MAX-ACCESS of ntwsMobilityMemberEntryAddr,
                         an index that was also the only column"

    REVISION "200604140007Z"
    DESCRIPTION "v2.0.5: Revised for release"

    REVISION "200501010000Z"
    DESCRIPTION "v1: initial version"

    ::= { ntwsMibs 2 }


-- Textual Conventions


-- Object definitions

-- Basic System Information Group
ntwsBasicSystemInfo OBJECT IDENTIFIER ::= { ntwsBasic 1 }

ntwsSerialNumber OBJECT-TYPE
    SYNTAX      DisplayString (SIZE (0..32))
    MAX-ACCESS  read-only
    STATUS      current
    DESCRIPTION
	"The serial number of the switch."
    ::= { ntwsBasicSystemInfo 1 }

ntwsSwMajorVersionNumber OBJECT-TYPE
    SYNTAX      INTEGER (0..99)
    MAX-ACCESS  read-only
    STATUS      current
    DESCRIPTION
	"The major release version of the running software."
    ::= { ntwsBasicSystemInfo 2 }

ntwsSwMinorVersionNumber OBJECT-TYPE
    SYNTAX      INTEGER (0..99)
    MAX-ACCESS  read-only
    STATUS      current
    DESCRIPTION
	"The minor release version of the running software."
    ::= { ntwsBasicSystemInfo 3 }

ntwsVersionString OBJECT-TYPE
    SYNTAX      DisplayString (SIZE (0..64))
    MAX-ACCESS  read-only
    STATUS      current
    DESCRIPTION
	"The version string of the running software, including
	 the major, minor, patch and build numbers, such as
	 3.0.0.185"
    ::= { ntwsBasicSystemInfo 4 }

-- Mobility Domain Group
ntwsMobilityDomainInfo OBJECT IDENTIFIER ::= { ntwsBasic 2 }

ntwsMobilityDomainName OBJECT-TYPE
    SYNTAX      DisplayString (SIZE (0..32))
    MAX-ACCESS  read-only
    STATUS      current
    DESCRIPTION
	"The mobility domain containing the switch, or a
	zero-length string when the mobility domain is
	unknown."
    ::= { ntwsMobilityDomainInfo 1 }


ntwsMobilitySeedIp OBJECT-TYPE
    SYNTAX      IpAddress
    MAX-ACCESS  read-only
    STATUS      current
    DESCRIPTION
	"The IPv4 address of the seed switch for this switch's
	mobility domain, or the IPv4 address 0.0.0.0 if unknown."
    ::= { ntwsMobilityDomainInfo 2 }

ntwsMobilityMemberTableSize OBJECT-TYPE
    SYNTAX      INTEGER (0..64)
    MAX-ACCESS  read-only
    STATUS      current
    DESCRIPTION
	"The number of entries in the mobility member table,
	ntwsMobilityMemberTable."
    ::= { ntwsMobilityDomainInfo 3 }

ntwsMobilityMemberTable OBJECT-TYPE
    SYNTAX      SEQUENCE OF NtwsMobilityMemberEntry
    MAX-ACCESS  not-accessible
    STATUS      current
    DESCRIPTION
	"Table of members of the mobility domain, indexed
	 by the member IPv4 address."
    ::= {ntwsMobilityDomainInfo 4 }

ntwsMobilityMemberEntry OBJECT-TYPE
    SYNTAX      NtwsMobilityMemberEntry
    MAX-ACCESS  not-accessible
    STATUS      current
    DESCRIPTION
	"An entry in the ntwsMobilityMemberTable table."
    INDEX   { ntwsMobilityMemberEntryAddr }
    ::= { ntwsMobilityMemberTable 1 }

NtwsMobilityMemberEntry ::= SEQUENCE {
    ntwsMobilityMemberEntryAddr     IpAddress
    }

-- a row can't have _all_ columns with MAX-ACCESS of not-accessible
-- (would mean there is nothing to retrieve)

ntwsMobilityMemberEntryAddr OBJECT-TYPE
    SYNTAX      IpAddress
    MAX-ACCESS  read-only
    STATUS      current
    DESCRIPTION
	"IPv4 address of a member of the mobility domain."
    ::= { ntwsMobilityMemberEntry 1 }

-- License Information Group
ntwsLicenseInfoGroup OBJECT IDENTIFIER ::= { ntwsBasic 3 }

ntwsLicenseInfoTableSize OBJECT-TYPE
    SYNTAX      INTEGER (0..64)
    MAX-ACCESS  read-only
    STATUS      current
    DESCRIPTION
	"The number of entries in the license table,
	ntwsLicenseInfoTable."
    ::= { ntwsLicenseInfoGroup 1 }

ntwsLicenseInfoTable OBJECT-TYPE
    SYNTAX      SEQUENCE OF NtwsLicenseInfoEntry
    MAX-ACCESS  not-accessible
    STATUS      current
    DESCRIPTION
	"Table of installed licenses on the switch. The
	licences provide additional capabilities over
	the default capabilities of the switch."
	::= { ntwsLicenseInfoGroup 2 }

ntwsLicenseInfoEntry OBJECT-TYPE
    SYNTAX  NtwsLicenseInfoEntry
    MAX-ACCESS  not-accessible
    STATUS      current
    DESCRIPTION
	"A license table entry."
    INDEX { ntwsLicenseInfoEntryFeature }
    ::= { ntwsLicenseInfoTable 1 }

NtwsLicenseInfoEntry ::= SEQUENCE {
    ntwsLicenseInfoEntryFeature     NtwsLicenseFeature,
    ntwsLicenseInfoEntryValue       INTEGER,
    ntwsLicenseInfoEntryDescr       DisplayString
    }

ntwsLicenseInfoEntryFeature OBJECT-TYPE
    SYNTAX NtwsLicenseFeature
    MAX-ACCESS  not-accessible
    STATUS      current
    DESCRIPTION
	"The feature being reported on"
    ::= { ntwsLicenseInfoEntry 1 }

ntwsLicenseInfoEntryValue OBJECT-TYPE
    SYNTAX      INTEGER (0..4096)
    MAX-ACCESS  read-only
    STATUS      current
    DESCRIPTION
	"The value of the feature enabled, for example
	a feature may have multiple levels of licensing,
	so the value will very with the license level."
    ::= { ntwsLicenseInfoEntry 2 }

ntwsLicenseInfoEntryDescr OBJECT-TYPE
    SYNTAX      DisplayString (SIZE (0..255))
    MAX-ACCESS  read-only
    STATUS      current
    DESCRIPTION
	"A human interpretable description of this license,
	for example, '120 APs or DAPs.'"
    ::= { ntwsLicenseInfoEntry 3 }


END
