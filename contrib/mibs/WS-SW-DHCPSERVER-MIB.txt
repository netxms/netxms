-- vim: syntax=mib
--
-- WS-SW-DHCPSERVER-MIB.my
-- MIB generated by MG-SOFT Visual MIB Builder Version 6.0  Build 88
-- Wednesday, November 29, 2006 at 11:01:50
--

	WS-SW-DHCPSERVER-MIB DEFINITIONS ::= BEGIN
 
		IMPORTS
			OBJECT-GROUP, MODULE-COMPLIANCE			
				FROM SNMPv2-CONF			
			IpAddress, Unsigned32, OBJECT-TYPE, MODULE-IDENTITY			
				FROM SNMPv2-SMI			
			RowStatus, TruthValue, DisplayString			
				FROM SNMPv2-TC			
			wsSwDHCP			
				FROM WS-SW-SMI;
	
	
		-- 1.3.6.1.4.1.388.14.2.3.5
		wsSwDhcpServerModule MODULE-IDENTITY 
			LAST-UPDATED "200604141134Z"		-- April 14, 2006 at 11:34 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"This module contains DHCP server MIB definition"
			REVISION "200611291042Z"		-- November 29, 2006 at 10:42 GMT
			DESCRIPTION 
				"02a20"
			REVISION "200607120031Z"		-- July 12, 2006 at 00:31 GMT
			DESCRIPTION 
				"02a19"
			REVISION "200607110532Z"		-- July 11, 2006 at 05:32 GMT
			DESCRIPTION 
				"02a18"
			REVISION "200607080450Z"		-- July 08, 2006 at 04:50 GMT
			DESCRIPTION 
				"02a17"
			REVISION "200606051329Z"		-- June 05, 2006 at 13:29 GMT
			DESCRIPTION 
				"02a16"
			REVISION "200605241649Z"		-- May 24, 2006 at 16:49 GMT
			DESCRIPTION 
				"02a15"
			REVISION "200605161109Z"		-- May 16, 2006 at 11:09 GMT
			DESCRIPTION 
				"02a14"
			REVISION "200605121636Z"		-- May 12, 2006 at 16:36 GMT
			DESCRIPTION 
				"02a13"
			REVISION "200605121201Z"		-- May 12, 2006 at 12:01 GMT
			DESCRIPTION 
				"02a12"
			REVISION "200605121126Z"		-- May 12, 2006 at 11:26 GMT
			DESCRIPTION 
				"02a11"
			REVISION "200605121056Z"		-- May 12, 2006 at 10:56 GMT
			DESCRIPTION 
				"02a10"
			REVISION "200605111743Z"		-- May 11, 2006 at 17:43 GMT
			DESCRIPTION 
				"02a09"
			REVISION "200605101652Z"		-- May 10, 2006 at 16:52 GMT
			DESCRIPTION 
				"02a08"
			REVISION "200605031047Z"		-- May 03, 2006 at 10:47 GMT
			DESCRIPTION 
				"02a07"
			REVISION "200605011334Z"		-- May 01, 2006 at 13:34 GMT
			DESCRIPTION 
				"02a06"
			REVISION "200604271333Z"		-- April 27, 2006 at 13:33 GMT
			DESCRIPTION 
				"02a05"
			REVISION "200604251354Z"		-- April 25, 2006 at 13:54 GMT
			DESCRIPTION 
				"02a04"
			REVISION "200604201016Z"		-- April 20, 2006 at 10:16 GMT
			DESCRIPTION 
				"02a03"
			REVISION "200604191409Z"		-- April 19, 2006 at 14:09 GMT
			DESCRIPTION 
				"02a02"
			REVISION "200604141145Z"		-- April 14, 2006 at 11:45 GMT
			DESCRIPTION 
				"02a01"
			::= { wsSwDHCP 5 }

		
	
	
--
-- Node definitions
--
	
		-- 1.3.6.1.4.1.388.14.2.3.5.1
		wsSwDhcpSvrGlobal OBJECT IDENTIFIER ::= { wsSwDhcpServerModule 1 }

		
		-- 1.3.6.1.4.1.388.14.2.3.5.1.1
		wsSwDhcpSvrBootp OBJECT-TYPE
			SYNTAX TruthValue
			MAX-ACCESS read-write
			STATUS current
			DESCRIPTION
				"Allow /Ignore Bootp requests "
			::= { wsSwDhcpSvrGlobal 1 }

		
		-- 1.3.6.1.4.1.388.14.2.3.5.1.2
		wsSwDhcpSvrPingInterval OBJECT-TYPE
			SYNTAX INTEGER (1..10)
			MAX-ACCESS read-write
			STATUS current
			DESCRIPTION
				"Ping time interval"
			::= { wsSwDhcpSvrGlobal 2 }

		
		-- 1.3.6.1.4.1.388.14.2.3.5.1.3
		wsSwDhcpSvrEnable OBJECT-TYPE
			SYNTAX TruthValue
			MAX-ACCESS read-write
			STATUS current
			DESCRIPTION
				"Description."
			::= { wsSwDhcpSvrGlobal 3 }

		
		-- 1.3.6.1.4.1.388.14.2.3.5.1.4
		wsSwDhcpSvrRestart OBJECT-TYPE
			SYNTAX INTEGER
				{
				restart(1),
				idle(2)
				}
			MAX-ACCESS read-write
			STATUS current
			DESCRIPTION
				"dhcp svr restart"
			::= { wsSwDhcpSvrGlobal 4 }

		
		-- 1.3.6.1.4.1.388.14.2.3.5.1.5
		wsSwDhcpSvrStatus OBJECT-TYPE
			SYNTAX INTEGER
				{
				running(1),
				stopped(2)
				}
			MAX-ACCESS read-only
			STATUS current
			DESCRIPTION
				"Description."
			::= { wsSwDhcpSvrGlobal 5 }

		
		-- 1.3.6.1.4.1.388.14.2.3.5.1.6
		wsSwDhcpSvrLastErrorMsg OBJECT-TYPE
			SYNTAX DisplayString
			MAX-ACCESS read-only
			STATUS current
			DESCRIPTION
				"Description."
			::= { wsSwDhcpSvrGlobal 6 }

		
		-- 1.3.6.1.4.1.388.14.2.3.5.2
		wsSwDhcpSvrExcludeTable OBJECT-TYPE
			SYNTAX SEQUENCE OF WsSwDhcpSvrExcludeEntry
			MAX-ACCESS not-accessible
			STATUS current
			DESCRIPTION
				"Description."
			::= { wsSwDhcpServerModule 2 }

		
		-- 1.3.6.1.4.1.388.14.2.3.5.2.1
		wsSwDhcpSvrExcludeEntry OBJECT-TYPE
			SYNTAX WsSwDhcpSvrExcludeEntry
			MAX-ACCESS not-accessible
			STATUS current
			DESCRIPTION
				"Description."
			INDEX { wsSwDhcpSvrExcludeLowIpAddr, wsSwDhcpSvrExcludeHighIpAddr }
			::= { wsSwDhcpSvrExcludeTable 1 }

		
		WsSwDhcpSvrExcludeEntry ::=
			SEQUENCE { 
				wsSwDhcpSvrExcludeLowIpAddr
					IpAddress,
				wsSwDhcpSvrExcludeHighIpAddr
					DisplayString,
				wsSwDhcpSvrExcludeRowStatus
					RowStatus
			 }

		-- 1.3.6.1.4.1.388.14.2.3.5.2.1.1
		wsSwDhcpSvrExcludeLowIpAddr OBJECT-TYPE
			SYNTAX IpAddress
			MAX-ACCESS read-only
			STATUS current
			DESCRIPTION
				"Excluded low address"
			::= { wsSwDhcpSvrExcludeEntry 1 }

		
		-- 1.3.6.1.4.1.388.14.2.3.5.2.1.2
		wsSwDhcpSvrExcludeHighIpAddr OBJECT-TYPE
			SYNTAX DisplayString
			MAX-ACCESS read-only
			STATUS current
			DESCRIPTION
				"Excluded high address"
			::= { wsSwDhcpSvrExcludeEntry 2 }

		
		-- 1.3.6.1.4.1.388.14.2.3.5.2.1.3
		wsSwDhcpSvrExcludeRowStatus OBJECT-TYPE
			SYNTAX RowStatus
			MAX-ACCESS read-create
			STATUS current
			DESCRIPTION
				"row status of wsSwDhcpSvrExcludeEntry"
			::= { wsSwDhcpSvrExcludeEntry 3 }

		
		-- 1.3.6.1.4.1.388.14.2.3.5.3
		wsSwDhcpSvrPoolTable OBJECT-TYPE
			SYNTAX SEQUENCE OF WsSwDhcpSvrPoolEntry
			MAX-ACCESS not-accessible
			STATUS current
			DESCRIPTION
				"Description."
			::= { wsSwDhcpServerModule 3 }

		
		-- 1.3.6.1.4.1.388.14.2.3.5.3.1
		wsSwDhcpSvrPoolEntry OBJECT-TYPE
			SYNTAX WsSwDhcpSvrPoolEntry
			MAX-ACCESS not-accessible
			STATUS current
			DESCRIPTION
				"Description."
			INDEX { wsSwDhcpSvrPoolNameIndex }
			::= { wsSwDhcpSvrPoolTable 1 }

		
		WsSwDhcpSvrPoolEntry ::=
			SEQUENCE { 
				wsSwDhcpSvrPoolNameIndex
					DisplayString,
				wsSwDhcpSvrPoolType
					INTEGER,
				wsSwDhcpSvrPoolHostIp
					IpAddress,
				wsSwDhcpSvrPoolSubnetIpAndMask
					DisplayString,
				wsSwDhcpSvrPoolClientId
					OCTET STRING,
				wsSwDhcpSvrPoolClientName
					DisplayString,
				wsSwDhcpSvrPoolHardWareAddrAndType
					DisplayString,
				wsSwDhcpSvrPoolDomainName
					DisplayString,
				wsSwDhcpSvrPoolNetBiosNodeType
					INTEGER,
				wsSwDhcpSvrPoolBootfile
					DisplayString,
				wsSwDhcpSvrPoolDdnsUpdate
					INTEGER,
				wsSwDhcpSvrPoolDdnsUpdateAll
					INTEGER,
				wsSwDhcpSvrPoolDdnsIp
					DisplayString,
				wsSwDhcpSvrPoolDdnsDomainName
					DisplayString,
				wsSwDhcpSvrPoolDdnsTtl
					INTEGER,
				wsSwDhcpSvrPoolDdnsMultiUserClass
					TruthValue,
				wsSwDhcpSvrPoolDefaultRouter
					DisplayString,
				wsSwDhcpSvrPoolBootpNextSvrIP
					IpAddress,
				wsSwDhcpSvrPoolDnsSvrIP
					DisplayString,
				wsSwDhcpSvrPoolNetbiosSvrIP
					DisplayString,
				wsSwDhcpSvrPoolNoDefault
					INTEGER,
				wsSwDhcpSvrPoolLeaseTime
					DisplayString,
				wsSwDhcpSvrPoolRowStatus
					RowStatus
			 }

		-- 1.3.6.1.4.1.388.14.2.3.5.3.1.1
		wsSwDhcpSvrPoolNameIndex OBJECT-TYPE
			SYNTAX DisplayString
			MAX-ACCESS read-only
			STATUS current
			DESCRIPTION
				"index of wsSwDhcpSvrPoolTable"
			::= { wsSwDhcpSvrPoolEntry 1 }

		
		-- 1.3.6.1.4.1.388.14.2.3.5.3.1.2
		wsSwDhcpSvrPoolType OBJECT-TYPE
			SYNTAX INTEGER
				{
				unDefined(0),
				network(1),
				host(2)
				}
			MAX-ACCESS read-only
			STATUS current
			DESCRIPTION
				"Description."
			::= { wsSwDhcpSvrPoolEntry 2 }

		
		-- 1.3.6.1.4.1.388.14.2.3.5.3.1.3
		wsSwDhcpSvrPoolHostIp OBJECT-TYPE
			SYNTAX IpAddress
			MAX-ACCESS read-create
			STATUS current
			DESCRIPTION
				"Description."
			::= { wsSwDhcpSvrPoolEntry 3 }

		
		-- 1.3.6.1.4.1.388.14.2.3.5.3.1.4
		wsSwDhcpSvrPoolSubnetIpAndMask OBJECT-TYPE
			SYNTAX DisplayString
			MAX-ACCESS read-create
			STATUS current
			DESCRIPTION
				"subnet IP and mask"
			::= { wsSwDhcpSvrPoolEntry 4 }

		
		-- 1.3.6.1.4.1.388.14.2.3.5.3.1.5
		wsSwDhcpSvrPoolClientId OBJECT-TYPE
			SYNTAX OCTET STRING
			MAX-ACCESS read-create
			STATUS current
			DESCRIPTION
				"client identifier
				
				To prepend Null character use \0 at the beginning."
			::= { wsSwDhcpSvrPoolEntry 5 }

		
		-- 1.3.6.1.4.1.388.14.2.3.5.3.1.6
		wsSwDhcpSvrPoolClientName OBJECT-TYPE
			SYNTAX DisplayString
			MAX-ACCESS read-create
			STATUS current
			DESCRIPTION
				"Description."
			::= { wsSwDhcpSvrPoolEntry 6 }

		
		-- 1.3.6.1.4.1.388.14.2.3.5.3.1.7
		wsSwDhcpSvrPoolHardWareAddrAndType OBJECT-TYPE
			SYNTAX DisplayString
			MAX-ACCESS read-create
			STATUS current
			DESCRIPTION
				"Hardware address and hardware type for the pool. Hardware type is optional. Default hardware type is ethernet
				Input formats are 
				XX:XX:XX:XX:XX:XX
				or
				XX:XX:XX:XX:XX:XX,ethernet 
				or
				XX:XX:XX:XX:XX:XX,token-ring"
			::= { wsSwDhcpSvrPoolEntry 7 }

		
		-- 1.3.6.1.4.1.388.14.2.3.5.3.1.8
		wsSwDhcpSvrPoolDomainName OBJECT-TYPE
			SYNTAX DisplayString
			MAX-ACCESS read-create
			STATUS current
			DESCRIPTION
				"Domain name"
			::= { wsSwDhcpSvrPoolEntry 8 }

		
		-- 1.3.6.1.4.1.388.14.2.3.5.3.1.9
		wsSwDhcpSvrPoolNetBiosNodeType OBJECT-TYPE
			SYNTAX INTEGER
				{
				undefined(0),
				nodeB(1),
				nodeP(2),
				nodeM(4),
				nodeH(8)
				}
			MAX-ACCESS read-create
			STATUS current
			DESCRIPTION
				"etbios-node-type"
			::= { wsSwDhcpSvrPoolEntry 9 }

		
		-- 1.3.6.1.4.1.388.14.2.3.5.3.1.10
		wsSwDhcpSvrPoolBootfile OBJECT-TYPE
			SYNTAX DisplayString
			MAX-ACCESS read-create
			STATUS current
			DESCRIPTION
				"boot file name"
			::= { wsSwDhcpSvrPoolEntry 10 }

		
		-- 1.3.6.1.4.1.388.14.2.3.5.3.1.11
		wsSwDhcpSvrPoolDdnsUpdate OBJECT-TYPE
			SYNTAX INTEGER
				{
				noUpdate(0),
				serverUpdate(1),
				clientUpdate(2)
				}
			MAX-ACCESS read-create
			STATUS current
			DESCRIPTION
				"DDNS updates"
			::= { wsSwDhcpSvrPoolEntry 11 }

		
		-- 1.3.6.1.4.1.388.14.2.3.5.3.1.12
		wsSwDhcpSvrPoolDdnsUpdateAll OBJECT-TYPE
			SYNTAX INTEGER
				{
				updateAll(1),
				idle(2)
				}
			MAX-ACCESS read-create
			STATUS current
			DESCRIPTION
				"Description."
			::= { wsSwDhcpSvrPoolEntry 12 }

		
		-- 1.3.6.1.4.1.388.14.2.3.5.3.1.13
		wsSwDhcpSvrPoolDdnsIp OBJECT-TYPE
			SYNTAX DisplayString
			MAX-ACCESS read-create
			STATUS current
			DESCRIPTION
				"This can take a max of 2 IP addresses in the format IP1, IP2. 
				To remove just IP1 use any of the following formats
				,IP2   or
				0.0.0.0,IP2
				To remove just IP2 use any of the following formats
				IP1,   or
				IP1,0.0.0.0
				To remove both IP addresses use any of the following formats
				(blank string or zero length string) or
				,
				"
			::= { wsSwDhcpSvrPoolEntry 13 }

		
		-- 1.3.6.1.4.1.388.14.2.3.5.3.1.14
		wsSwDhcpSvrPoolDdnsDomainName OBJECT-TYPE
			SYNTAX DisplayString
			MAX-ACCESS read-create
			STATUS current
			DESCRIPTION
				"DDNS domain name"
			::= { wsSwDhcpSvrPoolEntry 14 }

		
		-- 1.3.6.1.4.1.388.14.2.3.5.3.1.15
		wsSwDhcpSvrPoolDdnsTtl OBJECT-TYPE
			SYNTAX INTEGER (0..65535)
			MAX-ACCESS read-create
			STATUS current
			DESCRIPTION
				"DDNS TTL value. This OID can take values in range 1 to 864000. The value -1 is used to remove the configured value."
			::= { wsSwDhcpSvrPoolEntry 15 }

		
		-- 1.3.6.1.4.1.388.14.2.3.5.3.1.16
		wsSwDhcpSvrPoolDdnsMultiUserClass OBJECT-TYPE
			SYNTAX TruthValue
			MAX-ACCESS read-create
			STATUS current
			DESCRIPTION
				"enable/disable DDNS multi user class"
			::= { wsSwDhcpSvrPoolEntry 16 }

		
		-- 1.3.6.1.4.1.388.14.2.3.5.3.1.17
		wsSwDhcpSvrPoolDefaultRouter OBJECT-TYPE
			SYNTAX DisplayString
			MAX-ACCESS read-create
			STATUS current
			DESCRIPTION
				"Default Router, the format is xxx.xxx.xxx.xxx, yyy.yyy.yyy.yy,..., the maximum number of the router entry is 8"
			::= { wsSwDhcpSvrPoolEntry 17 }

		
		-- 1.3.6.1.4.1.388.14.2.3.5.3.1.18
		wsSwDhcpSvrPoolBootpNextSvrIP OBJECT-TYPE
			SYNTAX IpAddress
			MAX-ACCESS read-create
			STATUS current
			DESCRIPTION
				"bootp next server address, set it to 0.0.0.0 means there is no bootp next server address"
			::= { wsSwDhcpSvrPoolEntry 18 }

		
		-- 1.3.6.1.4.1.388.14.2.3.5.3.1.19
		wsSwDhcpSvrPoolDnsSvrIP OBJECT-TYPE
			SYNTAX DisplayString
			MAX-ACCESS read-create
			STATUS current
			DESCRIPTION
				"dns server address, the format is xxx.xxx.xxx.xxx, yyy.yyy.yyy.yy,..., the maximum number of the server entry is 8"
			::= { wsSwDhcpSvrPoolEntry 19 }

		
		-- 1.3.6.1.4.1.388.14.2.3.5.3.1.20
		wsSwDhcpSvrPoolNetbiosSvrIP OBJECT-TYPE
			SYNTAX DisplayString
			MAX-ACCESS read-create
			STATUS current
			DESCRIPTION
				"net bios server address, the format is xxx.xxx.xxx.xxx, yyy.yyy.yyy.yy,..., the maximum number of the server entry is 8"
			::= { wsSwDhcpSvrPoolEntry 20 }

		
		-- 1.3.6.1.4.1.388.14.2.3.5.3.1.21
		wsSwDhcpSvrPoolNoDefault OBJECT-TYPE
			SYNTAX INTEGER
				{
				noDefaultRouter(1),
				noDnsSvrIP(2),
				noNetbiosSvrIP(3),
				idle(4)
				}
			MAX-ACCESS read-create
			STATUS current
			DESCRIPTION
				"No default"
			::= { wsSwDhcpSvrPoolEntry 21 }

		
		-- 1.3.6.1.4.1.388.14.2.3.5.3.1.22
		wsSwDhcpSvrPoolLeaseTime OBJECT-TYPE
			SYNTAX DisplayString
			MAX-ACCESS read-create
			STATUS current
			DESCRIPTION
				"Lease time, the format is XX:YY:ZZ, which represents days:hours:mins. 00:00:00 means infinite lease"
			::= { wsSwDhcpSvrPoolEntry 22 }

		
		-- 1.3.6.1.4.1.388.14.2.3.5.3.1.23
		wsSwDhcpSvrPoolRowStatus OBJECT-TYPE
			SYNTAX RowStatus
			MAX-ACCESS read-create
			STATUS current
			DESCRIPTION
				"row status of wsSwDhcpSvrPoolTable"
			::= { wsSwDhcpSvrPoolEntry 23 }

		
		-- 1.3.6.1.4.1.388.14.2.3.5.4
		wsSwDhcpSvrIncludeTable OBJECT-TYPE
			SYNTAX SEQUENCE OF WsSwDhcpSvrIncludeEntry
			MAX-ACCESS not-accessible
			STATUS current
			DESCRIPTION
				"Description."
			::= { wsSwDhcpServerModule 4 }

		
		-- 1.3.6.1.4.1.388.14.2.3.5.4.1
		wsSwDhcpSvrIncludeEntry OBJECT-TYPE
			SYNTAX WsSwDhcpSvrIncludeEntry
			MAX-ACCESS not-accessible
			STATUS current
			DESCRIPTION
				"Description."
			INDEX { wsSwDhcpSvrPoolNameIndex, wsSwDhcpSvrIncludeLowIP, wsSwDhcpSvrIncludeHighIP }
			::= { wsSwDhcpSvrIncludeTable 1 }

		
		WsSwDhcpSvrIncludeEntry ::=
			SEQUENCE { 
				wsSwDhcpSvrIncludeLowIP
					IpAddress,
				wsSwDhcpSvrIncludeHighIP
					DisplayString,
				wsSwDhcpSvrIncludeRowStatus
					RowStatus
			 }

		-- 1.3.6.1.4.1.388.14.2.3.5.4.1.1
		wsSwDhcpSvrIncludeLowIP OBJECT-TYPE
			SYNTAX IpAddress
			MAX-ACCESS read-only
			STATUS current
			DESCRIPTION
				"Included low address"
			::= { wsSwDhcpSvrIncludeEntry 1 }

		
		-- 1.3.6.1.4.1.388.14.2.3.5.4.1.2
		wsSwDhcpSvrIncludeHighIP OBJECT-TYPE
			SYNTAX DisplayString
			MAX-ACCESS read-only
			STATUS current
			DESCRIPTION
				"Included high address"
			::= { wsSwDhcpSvrIncludeEntry 2 }

		
		-- 1.3.6.1.4.1.388.14.2.3.5.4.1.3
		wsSwDhcpSvrIncludeRowStatus OBJECT-TYPE
			SYNTAX RowStatus
			MAX-ACCESS read-create
			STATUS current
			DESCRIPTION
				"row status of wsSwDhcpSvrIncludeTable"
			::= { wsSwDhcpSvrIncludeEntry 3 }

		
		-- 1.3.6.1.4.1.388.14.2.3.5.5
		wsSwDhcpSvrPoolOptionTable OBJECT-TYPE
			SYNTAX SEQUENCE OF WsSwDhcpSvrPoolOptionEntry
			MAX-ACCESS not-accessible
			STATUS current
			DESCRIPTION
				"Description."
			::= { wsSwDhcpServerModule 5 }

		
		-- 1.3.6.1.4.1.388.14.2.3.5.5.1
		wsSwDhcpSvrPoolOptionEntry OBJECT-TYPE
			SYNTAX WsSwDhcpSvrPoolOptionEntry
			MAX-ACCESS not-accessible
			STATUS current
			DESCRIPTION
				"Description."
			INDEX { wsSwDhcpSvrPoolNameIndex, wsSwDhcpSvrPoolOptionName, wsSwDhcpSvrPoolOptionValue }
			::= { wsSwDhcpSvrPoolOptionTable 1 }

		
		WsSwDhcpSvrPoolOptionEntry ::=
			SEQUENCE { 
				wsSwDhcpSvrPoolOptionName
					DisplayString,
				wsSwDhcpSvrPoolOptionValue
					DisplayString,
				wsSwDhcpSvrPoolOptionRowStatus
					RowStatus
			 }

		-- 1.3.6.1.4.1.388.14.2.3.5.5.1.1
		wsSwDhcpSvrPoolOptionName OBJECT-TYPE
			SYNTAX DisplayString
			MAX-ACCESS read-only
			STATUS current
			DESCRIPTION
				"option name"
			::= { wsSwDhcpSvrPoolOptionEntry 1 }

		
		-- 1.3.6.1.4.1.388.14.2.3.5.5.1.2
		wsSwDhcpSvrPoolOptionValue OBJECT-TYPE
			SYNTAX DisplayString
			MAX-ACCESS read-only
			STATUS current
			DESCRIPTION
				"option tpe"
			::= { wsSwDhcpSvrPoolOptionEntry 2 }

		
		-- 1.3.6.1.4.1.388.14.2.3.5.5.1.3
		wsSwDhcpSvrPoolOptionRowStatus OBJECT-TYPE
			SYNTAX RowStatus
			MAX-ACCESS read-create
			STATUS current
			DESCRIPTION
				"row status of the table"
			::= { wsSwDhcpSvrPoolOptionEntry 3 }

		
		-- 1.3.6.1.4.1.388.14.2.3.5.6
		wsSwDhcpBindingStatusTable OBJECT-TYPE
			SYNTAX SEQUENCE OF WsSwDhcpBindingStatusEntry
			MAX-ACCESS not-accessible
			STATUS current
			DESCRIPTION
				"Description."
			::= { wsSwDhcpServerModule 6 }

		
		-- 1.3.6.1.4.1.388.14.2.3.5.6.1
		wsSwDhcpBindingStatusEntry OBJECT-TYPE
			SYNTAX WsSwDhcpBindingStatusEntry
			MAX-ACCESS not-accessible
			STATUS current
			DESCRIPTION
				"Description."
			INDEX { wsSwDhcpBindingStatusIp }
			::= { wsSwDhcpBindingStatusTable 1 }

		
		WsSwDhcpBindingStatusEntry ::=
			SEQUENCE { 
				wsSwDhcpBindingStatusIp
					IpAddress,
				wsSwDhcpBindingStatusHardwareAddr
					DisplayString,
				wsSwDhcpBindingStatusClientID
					DisplayString,
				wsSwDhcpBindingStatusLeaseExpired
					DisplayString,
				wsSwDhcpBindingStatusLeaseType
					INTEGER,
				wsSwDhcpBindingStatusRowStatus
					RowStatus
			 }

		-- 1.3.6.1.4.1.388.14.2.3.5.6.1.1
		wsSwDhcpBindingStatusIp OBJECT-TYPE
			SYNTAX IpAddress
			MAX-ACCESS read-only
			STATUS current
			DESCRIPTION
				"IP address of binding"
			::= { wsSwDhcpBindingStatusEntry 1 }

		
		-- 1.3.6.1.4.1.388.14.2.3.5.6.1.2
		wsSwDhcpBindingStatusHardwareAddr OBJECT-TYPE
			SYNTAX DisplayString
			MAX-ACCESS read-only
			STATUS current
			DESCRIPTION
				"Hardware address"
			::= { wsSwDhcpBindingStatusEntry 2 }

		
		-- 1.3.6.1.4.1.388.14.2.3.5.6.1.3
		wsSwDhcpBindingStatusClientID OBJECT-TYPE
			SYNTAX DisplayString
			MAX-ACCESS read-only
			STATUS current
			DESCRIPTION
				"Description."
			::= { wsSwDhcpBindingStatusEntry 3 }

		
		-- 1.3.6.1.4.1.388.14.2.3.5.6.1.4
		wsSwDhcpBindingStatusLeaseExpired OBJECT-TYPE
			SYNTAX DisplayString
			MAX-ACCESS read-only
			STATUS current
			DESCRIPTION
				"Lease expiration"
			::= { wsSwDhcpBindingStatusEntry 4 }

		
		-- 1.3.6.1.4.1.388.14.2.3.5.6.1.5
		wsSwDhcpBindingStatusLeaseType OBJECT-TYPE
			SYNTAX INTEGER
				{
				automatic(0),
				manual(1)
				}
			MAX-ACCESS read-only
			STATUS current
			DESCRIPTION
				"Description."
			::= { wsSwDhcpBindingStatusEntry 5 }

		
		-- 1.3.6.1.4.1.388.14.2.3.5.6.1.6
		wsSwDhcpBindingStatusRowStatus OBJECT-TYPE
			SYNTAX RowStatus
			MAX-ACCESS read-create
			STATUS current
			DESCRIPTION
				"only delete is supported in this row-status."
			::= { wsSwDhcpBindingStatusEntry 6 }

		
		-- 1.3.6.1.4.1.388.14.2.3.5.7
		wsSwDhcpSvrGlobalOptionTable OBJECT-TYPE
			SYNTAX SEQUENCE OF WsSwDhcpSvrGlobalOptionEntry
			MAX-ACCESS not-accessible
			STATUS current
			DESCRIPTION
				"Description."
			::= { wsSwDhcpServerModule 7 }

		
		-- 1.3.6.1.4.1.388.14.2.3.5.7.1
		wsSwDhcpSvrGlobalOptionEntry OBJECT-TYPE
			SYNTAX WsSwDhcpSvrGlobalOptionEntry
			MAX-ACCESS not-accessible
			STATUS current
			DESCRIPTION
				"Description."
			INDEX { wsSwDhcpSvrGlobalOptionName, wsSwDhcpSvrGlobalOptionCode, wsSwDhcpSvrGlobalOptionType }
			::= { wsSwDhcpSvrGlobalOptionTable 1 }

		
		WsSwDhcpSvrGlobalOptionEntry ::=
			SEQUENCE { 
				wsSwDhcpSvrGlobalOptionName
					DisplayString,
				wsSwDhcpSvrGlobalOptionCode
					Unsigned32,
				wsSwDhcpSvrGlobalOptionType
					INTEGER,
				wsSwDhcpSvrGlobalOptionRowStatus
					RowStatus
			 }

		-- 1.3.6.1.4.1.388.14.2.3.5.7.1.1
		wsSwDhcpSvrGlobalOptionName OBJECT-TYPE
			SYNTAX DisplayString
			MAX-ACCESS read-only
			STATUS current
			DESCRIPTION
				"Description."
			::= { wsSwDhcpSvrGlobalOptionEntry 1 }

		
		-- 1.3.6.1.4.1.388.14.2.3.5.7.1.2
		wsSwDhcpSvrGlobalOptionCode OBJECT-TYPE
			SYNTAX Unsigned32 (0..254)
			MAX-ACCESS read-create
			STATUS current
			DESCRIPTION
				"Description."
			::= { wsSwDhcpSvrGlobalOptionEntry 2 }

		
		-- 1.3.6.1.4.1.388.14.2.3.5.7.1.3
		wsSwDhcpSvrGlobalOptionType OBJECT-TYPE
			SYNTAX INTEGER
				{
				ipAddress(0),
				text(1)
				}
			MAX-ACCESS read-create
			STATUS current
			DESCRIPTION
				"Description."
			::= { wsSwDhcpSvrGlobalOptionEntry 3 }

		
		-- 1.3.6.1.4.1.388.14.2.3.5.7.1.4
		wsSwDhcpSvrGlobalOptionRowStatus OBJECT-TYPE
			SYNTAX RowStatus
			MAX-ACCESS read-create
			STATUS current
			DESCRIPTION
				"Description."
			::= { wsSwDhcpSvrGlobalOptionEntry 4 }

		
		-- 1.3.6.1.4.1.388.14.2.3.5.8
		wsSwDhcpRelayTable OBJECT-TYPE
			SYNTAX SEQUENCE OF WsSwDhcpRelayEntry
			MAX-ACCESS not-accessible
			STATUS current
			DESCRIPTION
				"Description."
			::= { wsSwDhcpServerModule 8 }

		
		-- 1.3.6.1.4.1.388.14.2.3.5.8.1
		wsSwDhcpRelayEntry OBJECT-TYPE
			SYNTAX WsSwDhcpRelayEntry
			MAX-ACCESS not-accessible
			STATUS current
			DESCRIPTION
				"Description."
			INDEX { wsSwDhcpRelayInterface }
			::= { wsSwDhcpRelayTable 1 }

		
		WsSwDhcpRelayEntry ::=
			SEQUENCE { 
				wsSwDhcpRelayInterface
					DisplayString,
				wsSwDhcpRelayTarget
					DisplayString,
				wsSwDhcpRelayTargetSet
					DisplayString,
				wsSwDhcpRelayRowStatus
					RowStatus
			 }

		-- 1.3.6.1.4.1.388.14.2.3.5.8.1.1
		wsSwDhcpRelayInterface OBJECT-TYPE
			SYNTAX DisplayString
			MAX-ACCESS read-only
			STATUS current
			DESCRIPTION
				"Interface Name"
			::= { wsSwDhcpRelayEntry 1 }

		
		-- 1.3.6.1.4.1.388.14.2.3.5.8.1.2
		wsSwDhcpRelayTarget OBJECT-TYPE
			SYNTAX DisplayString
			MAX-ACCESS read-only
			STATUS current
			DESCRIPTION
				"This is a read-only attribute which shows the currently configured relay targets in the format Ip,interface;Ip,interface... There can be a maximum of 4 such relay targets."
			::= { wsSwDhcpRelayEntry 2 }

		
		-- 1.3.6.1.4.1.388.14.2.3.5.8.1.3
		wsSwDhcpRelayTargetSet OBJECT-TYPE
			SYNTAX DisplayString
			MAX-ACCESS read-create
			STATUS current
			DESCRIPTION
				"Relay target in the format IP,Iface, where IP is the IP address to which DHCP packets have to be relayed and Iface is the interface name on which response from the relayed DHCP Server is received.
				A maximum of 4 relay targets can be added one at a time. To remove individual relay targets, use the following format
				0:IP, Iface. If there is only one relay target then it cannot be removed. In such a case the entire row has to be deleted."
			::= { wsSwDhcpRelayEntry 3 }

		
		-- 1.3.6.1.4.1.388.14.2.3.5.8.1.4
		wsSwDhcpRelayRowStatus OBJECT-TYPE
			SYNTAX RowStatus
			MAX-ACCESS read-create
			STATUS current
			DESCRIPTION
				"Row status of DHCP Relay Table"
			::= { wsSwDhcpRelayEntry 4 }

		
		-- 1.3.6.1.4.1.388.14.2.3.5.100
		wsSwDhcpServerMIBConformance OBJECT IDENTIFIER ::= { wsSwDhcpServerModule 100 }

		
		-- 1.3.6.1.4.1.388.14.2.3.5.100.1
		wsSwDhcpServerCompliances OBJECT IDENTIFIER ::= { wsSwDhcpServerMIBConformance 1 }

		
		-- 1.3.6.1.4.1.388.14.2.3.5.100.1.1
		wsSwDhcpServerCompliance MODULE-COMPLIANCE
			STATUS current
			DESCRIPTION 
				"Description."
			MODULE -- this module
				MANDATORY-GROUPS { wsSwDhcpServerGroup }
			::= { wsSwDhcpServerCompliances 1 }

		
		-- 1.3.6.1.4.1.388.14.2.3.5.100.2
		wsSwDhcpServerGroups OBJECT IDENTIFIER ::= { wsSwDhcpServerMIBConformance 2 }

		
		-- 1.3.6.1.4.1.388.14.2.3.5.100.2.1
		wsSwDhcpServerGroup OBJECT-GROUP
			OBJECTS { wsSwDhcpSvrBootp, wsSwDhcpSvrPingInterval, wsSwDhcpSvrExcludeRowStatus, wsSwDhcpSvrPoolDomainName, wsSwDhcpSvrPoolNetBiosNodeType, 
				wsSwDhcpSvrPoolBootfile, wsSwDhcpSvrPoolDdnsUpdate, wsSwDhcpSvrPoolDdnsDomainName, wsSwDhcpSvrPoolDdnsTtl, wsSwDhcpSvrPoolDdnsMultiUserClass, 
				wsSwDhcpSvrPoolDefaultRouter, wsSwDhcpSvrPoolBootpNextSvrIP, wsSwDhcpSvrPoolDnsSvrIP, wsSwDhcpSvrPoolNetbiosSvrIP, wsSwDhcpSvrPoolNoDefault, 
				wsSwDhcpSvrPoolLeaseTime, wsSwDhcpSvrPoolRowStatus, wsSwDhcpSvrIncludeRowStatus, wsSwDhcpBindingStatusHardwareAddr, wsSwDhcpBindingStatusLeaseExpired, 
				wsSwDhcpBindingStatusRowStatus, wsSwDhcpSvrPoolDdnsIp, wsSwDhcpSvrEnable, wsSwDhcpSvrPoolHostIp, wsSwDhcpBindingStatusLeaseType, 
				wsSwDhcpSvrPoolClientId, wsSwDhcpSvrExcludeLowIpAddr, wsSwDhcpSvrExcludeHighIpAddr, wsSwDhcpSvrPoolNameIndex, wsSwDhcpSvrIncludeLowIP, 
				wsSwDhcpSvrIncludeHighIP, wsSwDhcpBindingStatusIp, wsSwDhcpSvrGlobalOptionCode, wsSwDhcpSvrGlobalOptionType, wsSwDhcpSvrGlobalOptionRowStatus, 
				wsSwDhcpSvrGlobalOptionName, wsSwDhcpBindingStatusClientID, wsSwDhcpSvrPoolDdnsUpdateAll, wsSwDhcpSvrPoolType, wsSwDhcpSvrPoolSubnetIpAndMask, 
				wsSwDhcpSvrPoolClientName, wsSwDhcpSvrPoolHardWareAddrAndType, wsSwDhcpSvrPoolOptionName, wsSwDhcpSvrPoolOptionValue, wsSwDhcpRelayInterface, 
				wsSwDhcpRelayRowStatus, wsSwDhcpRelayTargetSet, wsSwDhcpRelayTarget, wsSwDhcpSvrLastErrorMsg, wsSwDhcpSvrStatus, 
				wsSwDhcpSvrPoolOptionRowStatus, wsSwDhcpSvrRestart }
			STATUS current
			DESCRIPTION 
				"Description."
			::= { wsSwDhcpServerGroups 1 }

		
	
	END

--
-- WS-SW-DHCPSERVER-MIB.my
--
