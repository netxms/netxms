-- extracted from draft-ietf-printmib-mib-info-04.txt
-- at Mon Nov 15 17:11:21 1999

Printer-MIB DEFINITIONS ::= BEGIN

IMPORTS
    MODULE-IDENTITY, OBJECT-TYPE, Counter32, Integer32,
    TimeTicks, NOTIFICATION-TYPE,
    OBJECT-IDENTITY, mib-2 FROM SNMPv2-SMI
    TEXTUAL-CONVENTION, DisplayString FROM SNMPv2-TC
    MODULE-COMPLIANCE, OBJECT-GROUP FROM SNMPv2-CONF
    hrDeviceIndex, hrStorageIndex FROM HOST-RESOURCES-MIB;

printmib MODULE-IDENTITY
    LAST-UPDATED "9810070000Z"
    ORGANIZATION "IETF Printer MIB Working Group"
    CONTACT-INFO
            "Randy Turner
           Sharp Laboratories of America
           5750 NW Pacific Rim Blvd
           Camas, WA 98607
           rturner@sharplabs.com"
    DESCRIPTION
        "The MIB module for management of printers."
    ::= { mib-2 43 }

--
-- Textual conventions for this MIB module
--
--
-- Generic unspecific textual conventions
--

PrtMediaUnitTC ::= TEXTUAL-CONVENTION
    -- This is a type 1 enumeration.
    STATUS       current
    DESCRIPTION
        "Units of measure for media dimensions."
    SYNTAX       INTEGER {
                     tenThousandthsOfInches(3),  -- .0001
                     micrometers(4)
              }

PrtCapacityUnitTC ::= TEXTUAL-CONVENTION
    -- This is a type 1 enumeration.
    STATUS       current
    DESCRIPTION
        "Units of measure for media capacity."
    SYNTAX       INTEGER {
                     tenThousandthsOfInches(3),  -- .0001
                     micrometers(4),
                     sheets(8),
                     feet(16),
                     meters(17)
                 }

PrtPrintOrientationTC ::= TEXTUAL-CONVENTION
  -- This value is a type 1 enumeration
  STATUS  current
  DESCRIPTION
     "A generic representation for printing orientation on a
'page'."
  SYNTAX  INTEGER {
          other(1),
          portrait(3),
          landscape(4)
        }

PrtCoverStatusTC ::= TEXTUAL-CONVENTION
    -- This is a type 2 enumeration.
    STATUS     current
    DESCRIPTION
         "Values for encoding the state of a particular cover or
         access panel on the printer case or enclosure."
    SYNTAX INTEGER {
                 other(1),
                 coverOpen(3),
                 coverClosed(4),
                 interlockOpen(5),
                 interlockClosed(6)
                }

PrtSubUnitStatusTC ::= TEXTUAL-CONVENTION
    -- This is a type 1 enumeration.
    STATUS       current
    DESCRIPTION
         "Status of a printer sub-unit.

         The SubUnitStatus is an integer that is the sum of 5
         distinct values, Availability, Non-Critical, Critical,
         On-line, and Transitioning. These values are:

     Availability                           Value
            Available and Idle               0       000'b
            Available and Standby            2       010'b
            Available and Active             4       100'b
            Available and Busy               6       110'b
            Unavailable and OnRequest        1       001'b
            Unavailable because Broken       3       011'b
            Unknown                          5       101'b

    Non-Critical

            No Non-Critical Alerts           0
            Non-Critical Alerts              8

    Critical

            No Critical Alerts               0
            Critical Alerts                 16

    On-Line

            State is On-Line                 0
            State is Off-Line               32

    Transitioning

            Currently at intended state      0
            Transitioning to intended state 64  "

    SYNTAX       INTEGER (0..126)

PresentOnOff ::= TEXTUAL-CONVENTION
    -- This is a type 1 enumeration.
    STATUS       current
    DESCRIPTION
        "Presence and configuration of a device or feature."
    SYNTAX       INTEGER {
                     other(1),
                     on(3),
                     off(4),
                     notPresent(5)
                 }

CodedCharSet ::= TEXTUAL-CONVENTION
      -- This is a type 3 enumeration.
      STATUS     current
      DESCRIPTION
         "A coded character set value that specifies both a set
         of characters that may be used and an encoding (as one
         or more octets) that is used to represent the characters
         in the set. These values are to be used to identify the
         encoding employed for strings in the MIB where this is
         not fixed by the MIB.

         Some objects that allow a choice of coded character set
         are: the prtLocalizationCharacterSet object in the
         LocalizationTable and prtInterpreterDefaultCharSetIn.
         The prtGeneralCurrentLocalization and
         prtConsoleLocalization objects in turn contain the index
         in the LocalizationTable of the current localization
         (country, language, and coded character set) of the
         'description' objects and the console, respectively.

         The space of the coded character set enumeration has
         been divided into three regions. The first region (3-
         999) consists of coded character sets that have been
         standardized by some standard setting organization. This
         region is intended for standards that do not have subset
         implementations. The second region (1000-1999) is for
         the Unicode and ISO/IEC 10646 coded character sets
         together with a specification of a (set of) sub-
         repertoires that may occur.  The third region (>1999) is
         intended for vendor specific coded character sets.

         NOTE: Unicode and ISO 10646 character coded data may be
         processed and stored in either Big Endian (most
         significant octet first) or Little Endian (least
         significant octet first) order.  Intel x86, VAX, and
         Alpha/AXP architectures are examples of Little Endian
         processor architectures. Furthermore, in environments
         where either order may occur, so-called Unicode BYTE
         ORDER MARK (BOM) character (which is ISO 10646 ZERO
         WIDTH NO BREAK SPACE), coded as FEFF in two octets and
         0000FEFF in four octets is used at the beginning of the
         data as a signature to indicate the order of the
         following data (See ISO 10646 Annex F).  Thus either
         ordering and BOM may occur in print data streams sent to
         the interpreter.  However, ISO 8824/8825 (ASN.1/BER)
         used by SNMP is quite clear that Big Endian order shall
         be used and BOM shall NOT be used in transmission in the
         protocol. Transmitting Unicode in Big Endian order in
         SNMP should not prove to be a hardship for Little Endian
         machines, since SNMP ASN.1/BER requires integers to be
         transmitted in Big Endian order as well.  So SNMP
         implementations on Little Endian machines are already
         reversing the order of integers to make them Big Endian
         for transmission via SNMP.  Also Unicode characters are
         usually treated as two-octet integers, not short text
         strings, so that it will be straightforward for Little
         Endian machines to reverse the order of Unicode
         character octets as well before transmitting them and
         after receiving them via the SNMP protocol.

         Where a given coded character set may be known by more
         than one name, the most commonly known name is used as
         the name of the enumeration and other names are shown in
         the comments.  The comments also indicate where to find
         detailed information on the coded character set and
         briefly characterize its relationship to other similar
         coded character sets.

         The current list of character sets and their enumerated
         values used to reference them is contained in the IANA
         Character Set registry.  The enum value is indicated by
         the MIB enum entry in the registry.  The enum symbol is
         indicated by the Alias that starts with 'cs' for
         character set.

         The IANA character sets registry is available via
         anonymous ftp.

         The ftp server is ftp.isi.edu. The subdirectory is /in-
         notes/iana/assignments/.

         The file name is character-sets.

         To add a character set to the IANA Registry:

         1. Format an entry like those in the current list,
         omitting the MIBenum value.
         2. Send the entry with a request to add the entry to the
         character set list to iana@ISI.EDU.
         3. The IANA will supply a unique MIBenum value and
         update the list."

     SYNTAX     INTEGER {
        other(1)      -- used if the designated coded
                      -- character set is not currently in
                      -- the enumeration

      -- See IANA Registry for standard character sets in the
      -- MIBenum range of 3-999.
      -- See IANA Registry for Unicode and vendor-supplied
      -- combinations of ISO collections and character sets based
      -- on Unicode in the MIBenum range of 1000-1999.
      -- See IANA Registry for vendor developed character sets
      -- in the MIBenum range of 2000-xxxx.
   }


--
-- General Group textual-conventions
--

PrtGeneralResetTC ::= TEXTUAL-CONVENTION
    -- This value is a type 3 enumeration
    STATUS     current
    DESCRIPTION
      "Values for reading and writing the prtGeneralReset object.

       If a device does not have NVRAM, the device shall none the
       less respond to a SET with the value resetToNVRAM(5) with
       some sort of warm reset that resets the device to some
       implementation-defined state that is preferably under
       control of the system administrator by some means outside
       the scope of this MIB specification."
       SYNTAX     INTEGER {
                   notResetting(3),
                   powerCycleReset(4), -- Cold Start
                   resetToNVRAM(5), -- Warm Start
                   resetToFactoryDefaults(6) -- Reset contents of
                                             -- NVRAM to factory
                                             -- defaults
               }

--
-- Channel Group textual-conventions
--

PrtChannelStateTC ::= TEXTUAL-CONVENTION
    -- This value is a type 1 enumeration
    STATUS       current
    DESCRIPTION
         "The state of this print job delivery channel. The value
         determine whether control information and print data is
         allowed through this channel."
   SYNTAX     INTEGER {
                   other(1),
                   printDataAccepted(3),
                   noDataAccepted(4)

               }

PrtChannelTypeTC ::= TEXTUAL-CONVENTION
    --  This is a type 2 enumeration.
    STATUS     current
    DESCRIPTION
        "This enumeration indicates the type of channel that is
        receiving jobs."
    SYNTAX     INTEGER {
               other(1),
               chSerialPort(3),
               chParallelPort(4),
               chIEEE1284Port(5),
               chSCSIPort(6),
               chAppleTalkPAP(7),
                 -- AppleTalk Printer
                 -- Access Protocol (PAP)
                 --
                 -- prtChannelInformation entry:
                 --
                 -- Printer Name
                 --   Keyword:       Name
                 --   Syntax:        Name
                 --   Status:   Optional
                 --   Multiplicity: Single
                 --   Description:  The name of the
                 --     printer within the AppleTalk
                 --     naming scope
               chLPDServer(8),
                 -- prtChannelInformation entry:
                 --
                 -- Printer queue name
                 --   Keyword:       Queue
                 --   Syntax:        Name
                 --   Status:        Mandatory
                 --   Multiplicity:  Single
                 --   Description: queue name as
                 --     defined in RFC 1179.
               chNetwareRPrinter(9),
                 -- Novell, Inc.
                 -- For each entry of this type, the
                 -- prtChannelInformation must have a pair
                 -- of keywords. For Netware 3.x channels
                 -- this must be a (PServer, Printer) pair.
                 -- For Netware 4.x channels and for
                 -- IntranetWare channels this must be a
                 -- (NDSTree, NDSPrinter) pair.
                 --
                 -- prtChannelInformation entries:

                 -- Print Server Name
                 --   Keyword:        PServer
                 --   Syntax:    Name
                 --   Status:         Mandatory
                 --   Multiplicity: Single
                 --   Description:  The Pserver's SAP name
                 --
                 -- Printer Number
                 --   Keyword:        Printer
                 --   Syntax:         Integer
                 --   Status:    Mandatory
                 --   Multiplicity: Single
                 --   Description:  The printer number
                 --
                 -- NDSTree
                 --   Keyword:      NDSTree
                 --   Syntax:       Name
                 --   Multiplicity: Single
                 --   Description:  The tree's SAP name
                 --
                 -- NDS Printer object
                 --   Keyword:      NDSPrinter
                 --   Syntax:       Text (Unicode)
                 --   Status:       Mandatory
                 --   Multiplicity: Single
                 --   Description:  The fully qualified
                 --     name of the Printer
                 --
                 -- In the Netware 3.x environment, the
                 -- client checks the Bindery object
                 -- representing the named PServer. The
                 -- client then checks for queues which
                 -- are associated with the numbered
                 -- printer. In the 4.x and IntraNetware
                 -- environment, the client looks up the
                 -- queues which are associated with the
                 -- NDS Printer Object in the named Tree.
                 -- Depending on client access rights to
                 -- those queues, the client submits jobs
                 -- to the appropriate queue.
               chNetwarePServer(10),
                 -- Novell,Inc.
                 -- For each entry of this type, the
                 -- prtChannelInformation must have a pair
                 -- of keywords. For Netware 3.x channels
                 -- this must be a (Server, PServer) pair.
                 -- For Netware 4.x and IntranetWare
                 -- channels, this must be a
                 -- (NDSTree, NDSPServer) pair.
                 --
                 -- prtChannelInformation entries:
                 --
                 -- Server Name
                 --   Keyword:       Server
                 --   Syntax:   Name
                 --   Status:        Mandatory
                 --   Multiplicity: Single
                 --   Description:  The SAP name of the
                 --   server for which the PServer is
                 --   defined.
                 --
                 -- PServer
                 --   Keyword:      PServer
                 --   Syntax:       Name
                 --   Status:       Mandatory
                 --   Multiplicity: Single
                 --   Description:  The bindery name of
                 --     the PServer
                 --
                 -- NDS Tree
                 --   Keyword:      NDSTree
                 --   Syntax:       Name
                 --   Status:       Mandatory
                 --   Multiplicity: Single
                 --   Description:  The NDS Tree name
                 --
                 -- PServer
                 --   Keyword:      NDSPServer
                 --   Syntax:       Text (Unicode)
                 --   Status:       Mandatory
                 --   Multiplicity: Single
                 --   Description:  The fully qualified
                 --     name of the PServer object in the
                 --     tree.
                 --
                 -- In the 3.x environment, the client
                 -- checks the bindery object
                 -- representing the named PServer on the
                 -- named Server. In the 4.x and
                 -- IntranetWare environment,
                 -- the client checks the NDS object
                 -- representing the named PServer in the
                 -- named Tree. In either case, the
                 -- client then checks for all queues
                 -- associated with the Pserver object.
                 -- Depending on client access rights
                 -- to those queues, the client submits
                 -- jobs to the appropriate queue.
               chPort9100(11),
                 -- DEPRECATED
               chAppSocket(12),
                 -- A bi-directional, LPD-like,
                 -- protocol using 9101 for
                 -- control and 9100 for data.
                 -- Adobe Systems, Inc.
               chFTP(13),         -- RFC 959
               chTFTP(14),        -- RFC 1350
               chDLCLLCPort(15),
               chIBM3270(16),     -- IBM Coax
               chIBM5250(17),     -- IBM Twinax
               chFax(18),
               chIEEE1394(19),
               chTransport1(20),
                 -- TCP port 35, see reserved TCP port list
                 -- in RFC 1700 or current "Assigned
                 -- Numbers" RFC. This RFC should also be
                 -- referenced for other channel
                 -- enumerations utilizing TCP port
                 -- numbers 0 through 1024.
               chCPAP(21),      -- TCP port 170, Digital
                                -- Equipment Corp.
               chPCPrint(26),   -- Banyan
               chServerMessageBlock(27),
                 -- File/Print sharing protocol used by
                 -- various network operating systems
                 -- from IBM 3Com, Microsoft and others
                 --
                 -- prtChannelInformation entry:
                 --
                 -- Service Name
                 --   Keyword:       Name
                 --   Syntax:       Name
                 --   Status:   Optional
                 --   Multiplicity: Single
                 --   Description:  The service name of
                 --     the printer
               chPSM(28),       -- Printing Systems
                                -- Manager, IBM
               chSystemObjectManager(31), -- IBM
               chDECLAT(32),
                 -- Digital Equipment Corp.
                 --
                 -- prtChannelInformation entries:
                 --
                 -- Port Name
                 --   Keyword:      Port
                 --   Syntax:       Name
                 --   Status:       Conditionally
                 --                 Mandatory
                 --                 (see note below)
                 --   Multiplicity: Single
                 --   Description:  LAT port name
                 --
                 -- Service Name
                 --    Keyword:      Service
                 --    Syntax:       Name
                 --    Status:       Conditionally
                 --                  Mandatory
                 --    Multiplicity: Single
                 --    Description:  LAT service
                 --      name
                 --
                 -- The LAT channel may be
                 -- identified by either a port or
                 -- service, so either a
                 -- Port or Service entry must be
                 -- specified, but not both.
               chNPAP(33),
               chUSB(34),    -- Universal Serial Bus
               chIRDA(35),   -- Infrared Data Assoc. Prot.
               chPrintXChange(36), -- PrintXChange Protocol
               chPortTCP(37),
                 -- A unidirectional "raw" TCP
                 -- channel that uses an administratively
                 -- assigned TCP port address.
                 --
                 -- prtChannelInformation entry:
                 --
                 -- Port Number
                 --    Keyword:      Port
                 --    Syntax:       decimal number
                 --    Status:       Mandatory
                 --    Multiplicity: Single
                 --    Description:  TCP port number
               chBidirPortTCP(38),
                 -- A bi-directional version of chPortTCP
                 --
                 -- prtChannelInformation entries:
                 -- (See chPortTCP)
               chUNPP(39),
                 -- Universal Network Printing
                 -- Protocol(UNPP). A bi-directional,
                 -- multiport network printing
                 -- application protocol available on
                 -- multiple transport protocols.
                 -- Underscore, Inc.
                 -- Contact: info@underscore.com
               chAppleTalkADSP(40),
                 -- AppleTalk Data Stream Protocol.
                 -- ADSP is part of the AppleTalk
                 -- suite of protocols.
                 -- It is a symmetric, connection-
                 -- oriented protocol that makes
                 -- possible the establishment
                 -- and maintenance of full-duplex
                 -- streams of data bytes between
                 -- two sockets in an AppleTalk
                 -- internet.
                 -- See Inside AppleTalk, second
                 -- Edition, by Sidhu, Andrews and
                 -- Oppenheimer.
               chPortSPX(41),
                 -- Sequenced Packet Exchange (SPX)
                 -- socket.
                 -- Novell, Inc. Similar to TCP, a
                 -- bi-directional data pipe using
                 -- Novell SPX as a transport.
                 --
                 -- prtChannelInformation entries:
                 --
                 -- Network Number
                 --   Keyword:       Net
                 --   Syntax:   HexString
                 --   Status:   Mandatory
                 --   Multiplicity: Single
                 --   Description:  The network number
                 --
                 -- Node Number
                 --   Keyword:       Node
                 --   Syntax:   HexString
                 --   Status:   Mandatory
                 --   Multiplicity: Single
                 --   Description:  The node number
                 --
                 -- Socket Number
                 --   Keyword:       Socket
                 --   Syntax:   HexString
                 --   Status:   Mandatory
                 --   Multiplicity: Single
                 --   Description:  The SPX socket number
                 --
                 -- There must be exactly one "Net" and
                 -- one "Node" and one "Socket" entry. A
                 -- HexString is a binary value
                 -- represented as a string of
                 -- ASCII characters using hexadecimal
                 -- notation.
               chPortHTTP(42),
                 -- Hypertext Transfer Protocol. See IETF
                 -- documents relating to HTTP 1.0/1.1
                 -- (RFCs 1945 and 2068,etc.)
               chNDPS(43)
                 -- Novell, Inc.
                 --
                 -- prtChannelInformation entry:
                 --
                 -- Printer Agent Name
                 --   Keyword:      PA
                 --   Syntax:   Name
                 --   Status:   Mandatory
                 --   Multiplicity: Single
                 --   Description:  The NDPS Printer
                 --      Agent Name
    }
-- Interpreter Group textual conventions

PrtInterpreterLangFamilyTC ::= TEXTUAL-CONVENTION
    -- This value is a type 2 enumeration.
    STATUS     current
    DESCRIPTION
      "This enumeration indicates the type of interpreter that is
       receiving jobs."
    SYNTAX     INTEGER {
        other(1),
        unknown(2),
        langPCL(3),      -- PCL.  Starting with PCL version 5,
                         -- HP-GL/2 is included as part of the
                         -- PCL language.
                         -- PCL and HP-GL/2 are registered
                         -- trademarks of Hewlett-Packard
                         -- Company.
        langHPGL(4),     -- Hewlett-Packard Graphics Language.
                         -- HP-GL is a registered trademark of
                         -- Hewlett-Packard Company.
        langPJL(5),      -- Peripheral Job Language. Appears in
                         -- the data stream between data intended
                         -- for a page description language.
                         -- Hewlett-Packard Co.
        langPS(6),       -- PostScript (tm) Language
                         -- Postscript - a trademark of Adobe
                         -- Systems Incorporated which may be
                         -- registered in certain jurisdictions
        langIPDS(7),     -- Intelligent Printer Data Stream
                         -- Bi-directional print data stream for
                         -- documents consisting of data objects
                         -- (text, image, graphics, bar codes),
                         -- resources (fonts, overlays) and page,
                         -- form and finishing instructions.
                         -- Facilitates system level device
                         -- control, document tracking and error
                         -- recovery throughout the print
                         -- process.
                         -- Pennant Systems, IBM
        langPPDS(8),     -- IBM Personal Printer Data Stream.
                         -- Originally called IBM ASCII, the name
                         -- was changed to PPDS when the Laser
                         -- Printer was introduced in 1989.
                         -- Lexmark International, Inc.
        langEscapeP(9),  -- Epson Corp.
        langEpson(10),
        langDDIF(11),    -- Digital Document Interchange Format
                         -- Digital Equipment Corp., Maynard MA
        langInterpress(12),
                         -- Xerox Corp.
        langISO6429(13), -- ISO 6429.  Control functions for
                         -- Coded Character Sets (has ASCII
                         -- control characters, plus additional
                         -- controls for
                         -- character imaging devices.)
                         -- ISO Standard, Geneva, Switzerland
        langLineData(14),-- line-data:  Lines of data as
                         -- separate ASCII or EBCDIC records
                         -- and containing no control functions
                         -- (no CR, LF, HT, FF, etc.)
                         -- For use with traditional line
                         -- printers.  May use CR and/or LF to
                         -- delimit lines, instead of records.
                         -- See ISO 10175 Document Printing
                         -- Application(DPA)
                         -- ISO standard, Geneva, Switzerland
        langMODCA(15),   -- Mixed Object Document Content
                         -- Architecture
                         -- Definitions that allow the
                         -- composition, interchange, and
                         -- presentation of final form
                         -- documents as a collection of data
                         -- objects (text, image, graphics, bar
                         -- codes), resources (fonts, overlays)
                         -- and page, form and finishing
                         -- instructions.
                         -- Pennant Systems, IBM
        langREGIS(16),   -- Remote Graphics Instruction Set,
                         -- Digital Equipment Corp., Maynard MA
        langSCS(17),     -- SNA Character String
                         -- Bi-directional print data stream for
                         -- SNA LU-1 mode of communication.
                         -- IBM
        langSPDL(18),    -- ISO 10180 Standard Page Description
                         -- Language
                         -- ISO Standard
        langTEK4014(19), -- Tektronix Corp.
        langPDS(20),
        langIGP(21),     -- Printronix Corp.
        langCodeV(22),   -- Magnum Code-V, Image and printer
                         -- control language used to control
                         -- impact/dot-matrix printers.
                         -- QMS, Inc., Mobile AL
        langDSCDSE(23),  -- DSC-DSE:  Data Stream Compatible and
                         -- Emulation Bi-directional print data
                         -- stream for non-SNA (DSC) and SNA LU-3
                         -- 3270 controller (DSE) communications
                         -- IBM
        langWPS(24),     -- Windows Printing System, Resource
                         -- based command/data stream used by
                         -- Microsoft At Work Peripherals.
                         -- Developed by the Microsoft
                         -- Corporation.
        langLN03(25),    -- Early DEC-PPL3, Digital Equipment
                         -- Corp.
        langCCITT(26),
        langQUIC(27),    -- QUIC (Quality Information Code), Page
                         -- Description Language for laser
                         -- printers. Included graphics, printer
                         -- control capability and emulation of
                         -- other well-known printer .
                         -- QMS, Inc.
        langCPAP(28),    -- Common Printer Access Protocol
                         -- Digital Equipment Corp.
        langDecPPL(29),  -- Digital ANSI-Compliant Printing
                         -- Protocol
                         -- (DEC-PPL)
                         -- Digital Equipment Corp.

        langSimpleText(30),
                         -- simple-text:  character coded data,
                         -- including NUL, CR , LF, HT, and FF
                         -- control characters.  See ISO 10175
                         -- Document Printing Application (DPA)
                         -- ISO standard, Geneva, Switzerland
        langNPAP(31),    -- Network Printer Alliance Protocol
                         -- (NPAP). This protocol has been
                         -- superseded by the IEEE 1284.1 TIPSI
                         -- Std (ref. LangTIPSI(49)).
        langDOC(32),     -- Document Option Commands, Appears in
                         -- the data stream between data
                         -- intended for a page description .
                         -- QMS, Inc.
        langimPress(33), -- imPRESS, Page description language
                         -- originally developed for the
                         -- ImageServer product line. A binary
                         -- language providing representations
                         -- of text, simple graphics, and some
                         -- large forms (simple
                         -- bit-map and CCITT group /
                         -- encoded).The
                         -- language was intended to be sent over
                         -- an 8-bit channel and supported early
                         -- document preparation languages (e.g.
                         -- TeX and TROFF).
                         -- QMS, Inc.
        langPinwriter(34),
                         -- 24 wire dot matrix printer  for
                         -- USA, Europe, and Asia except
                         -- Japan.
                         -- More widely used in Germany, and
                         -- some Asian countries than in US.
                         -- NEC
        langNPDL(35),    -- Page printer  for Japanese market.
                         -- NEC
        langNEC201PL(36),-- Serial printer language used in
                         -- the Japanese market.
                         -- NEC
        langAutomatic(37),
                         -- Automatic PDL sensing.  Automatic
                         -- sensing of the interpreter
                         -- language family by the printer
                         -- examining the document content.
                         -- Which actual interpreter language
                         -- families are sensed depends on
                         -- the printer implementation.
        langPages(38),   -- Page printer Advanced Graphic
                         -- Escape Set
                         -- IBM Japan
        langLIPS(39),    -- LBP Image Processing System
        langTIFF(40),    -- Tagged Image File Format (Aldus)
        langDiagnostic(41),
                         -- A hex dump of the input to the
                         -- interpreter
        langPSPrinter(42),
                         -- The PostScript Language used for
                         -- control (with any PDLs)
                         -- Adobe Systems Incorporated
        langCaPSL(43),   -- Canon Print Systems Language
        langEXCL(44),    -- Extended Command Language
                         -- Talaris Systems Inc.
        langLCDS(45),    -- Line Conditioned Data Stream
                         -- Xerox Corporation
        langXES(46),     -- Xerox Escape Sequences
                         -- Xerox Corporation
        langPCLXL(47),   -- Printer Control Language. Extended
                         -- language features for printing, and
                         -- printer control.
                         -- Hewlett-Packard Co.
        langART(48),     -- Advanced Rendering Tools (ART).
                         -- Page Description language
                         -- originally developed for the Laser
                         -- Press printers.
                         -- Technical reference manual: "ART IV
                         -- Reference Manual", No F33M.
                         -- Fuji Xerox Co., Ltd.
        langTIPSI(49),   -- Transport Independent Printer
                         -- System Interface (ref. IEEE Std.
                         -- 1284.1)
        langPrescribe(50),
                         -- Page description and printer
                         -- control language. It can be
                         -- described with ordinary ASCII
                         -- Technical reference manual:
                         -- "PRESCRIBE II Programming Manual"
        langLinePrinter(51),
                         -- A simple-text character stream which
                         -- supports the control codes LF, VT,
                         -- FF, and plus Centronics or
                         -- Dataproducts Vertical Format Unit
                         -- (VFU) language is commonly used on
                         -- many older model line and matrix
                         -- printers.
        langIDP(52),     -- Imaging Device Protocol
                         -- Apple Computer.

        langXJCL(53),    -- Xerox Job Control Language (JCL).
                         -- A Job Control language originally
                         -- developed for the LaserPress printers
                         -- and is capable of switching PDLs.
                         -- Technical reference manual:
                         -- "ART IV Reference Manual", No F33M.
                         -- Fuji Xerox Co., Ltd.
        langPDF(54),     -- Adobe Portable Document Format
                         -- Adobe Systems, Inc.
        langRPDL(55),    -- Ricoh Page Description Language for
                         -- printers.
                         -- Technical manual "RPDL command
                         -- reference" No.307029
                         -- RICOH, Co. LTD
        langIntermecIPL(56),
                         -- Intermec Printer Language for label
                         -- printers.
                         -- Technical Manual: "IPL Programmers
                         -- Reference Manual"
                         -- Intermec Corporation
        langUBIFingerprint(57),
                         -- An intelligent basic-like programming
                         -- language for label printers.
                         -- Reference Manual: "UBI Fingerprint
                         -- 7.1", No. 1-960434-00
                         -- United Barcode Industries
        langUBIDirectProtocol(58),
                         -- An intelligent control language for
                         -- label printers.
                         -- Programmers guide: " UBI Direct
                         -- Protocol", No. 1-960419-00
                         -- United Barcode Industries
        langFujitsu(59)
                         -- Fujitsu Printer Language
                         -- Reference Manual:
                         -- "FM Printer Sequence" No. 80HP-0770
                         -- FUJITSU LIMITED
}

--
-- Input/Output Group Textual Conventions
--

PrtInputTypeTC ::= TEXTUAL-CONVENTION
    -- This is a type 2 enumeration
    STATUS current
    DESCRIPTION
         "The type of technology (discriminated primarily
         according to feeder mechanism type) employed by a
         specific component or components."
    SYNTAX INTEGER {
                other(1),
                unknown(2),
                sheetFeedAutoRemovableTray(3),
                sheetFeedAutoNonRemovableTray(4),
                sheetFeedManual(5),
                continuousRoll(6),
                continuousFanFold(7)
                   }

PrtOutputTypeTC ::= TEXTUAL-CONVENTION
     -- This is a type 2 enumeration
     STATUS current
     DESCRIPTION
          "The Type of technology supported by this output sub-
         unit"
     SYNTAX INTEGER {
                    other(1),
                    unknown(2),
                    removableBin(3),
                    unRemovableBin(4),
                    continuousRollDevice(5),
                    mailBox(6),
                    continuousFanFold(7)
                 }

PrtOutputStackingOrderTC ::= TEXTUAL-CONVENTION
     -- This is a type 1 enumeration
     STATUS current
     DESCRIPTION
         "The current state of the stacking order for the
         associated output sub-unit. 'firstToLast' means that as
         pages are output, the front of the next page is placed
         against the back of the previous page. 'lastToFirst'
         means that as pages are output, the back of the next
         page is placed against the front of the previous page."
     SYNTAX INTEGER {
                    unknown(2),
                    firstToLast(3),
                    lastToFirst(4)
                 }

PrtOutputPageDeliveryOrientationTC ::= TEXTUAL-CONVENTION
     -- This is a type 1 enumeration
     STATUS current
     DESCRIPTION
         "The reading surface that will be 'up' when pages are
         delivered to the associated output sub-unit. Values are
         Face-Up and Face-Down (Note: interpretation of these
         values is, in general, context-dependent based on
         locale; presentation of these values to an end-user
         should be normalized to the expectations of the user."
     SYNTAX INTEGER {
                    faceUp(3),
                    faceDown(4)
                 }

--
-- Marker Group Textual Conventions
--

PrtMarkerMarkTechTC ::= TEXTUAL-CONVENTION
     -- This value is a type 2 enumeration
     STATUS current
     DESCRIPTION
         "The type of marking technology used for this marking
         sub-unit"
     SYNTAX     INTEGER {
                   other(1),
                   unknown(2),
                   electrophotographicLED(3),
                   electrophotographicLaser(4),
                   electrophotographicOther(5),
                   impactMovingHeadDotMatrix9pin(6),
                   impactMovingHeadDotMatrix24pin(7),
                   impactMovingHeadDotMatrixOther(8),
                   impactMovingHeadFullyFormed(9),
                   impactBand(10),
                   impactOther(11),
                   inkjetAqueous(12),
                   inkjetSolid(13),
                   inkjetOther(14),
                   pen(15),
                   thermalTransfer(16),
                   thermalSensitive(17),
                   thermalDiffusion(18),
                   thermalOther(19),
                   electroerosion(20),
                   electrostatic(21),
                   photographicMicrofiche(22),
                   photographicImagesetter(23),
                   photographicOther(24),
                   ionDeposition(25),
                   eBeam(26),
                   typesetter(27)
               }

PrtMarkerCounterUnitTC ::= TEXTUAL-CONVENTION
    -- This value is a type 1 enumeration
    STATUS     current
    DESCRIPTION
        "The unit that will be used by the printer when reporting
        counter values for this marking sub-unit.  The
        time units of measure are provided for a device like a
        strip recorder that does not or cannot track the physical
        dimensions of the media and does not use characters,
        lines or sheets."

    SYNTAX     INTEGER {
                   tenThousandthsOfInches(3),  -- .0001
                   micrometers(4),
                   characters(5),
                   lines(6),
                   impressions(7),
                   sheets(8),
                   dotRow(9),
                   hours(11),
                   feet(16),
                   meters(17)
               }

PrtMarkerSuppliesTypeTC ::= TEXTUAL-CONVENTION
    --   This value is a type 3 enumeration
    STATUS     current
    DESCRIPTION
        "The type of this supply."
    SYNTAX     INTEGER {
                   other(1),
                   unknown(2),
                   toner(3),
                   wasteToner(4),
                   ink(5),
                   inkCartridge(6),
                   inkRibbon(7),
                   wasteInk(8),
                   opc(9), -- photo conductor
                   developer(10),
                   fuserOil(11),
                   solidWax(12),
                   ribbonWax(13),
                   wasteWax(14),
                   fuser(15),
                   coronaWire(16),
                   fuserOilWick(17),
                   cleanerUnit(18),
                   fuserCleaningPad(19),
                   transferUnit(20),
                   tonerCartridge(21),
                   fuserOiler(22),
            -- Values for Finisher MIB
                   water(23),
                   wasteWater(24),
                   glueWaterAdditive(25),
                   wastePaper(26),
                   bindingSupply(27),
                   bandingSupply(28),
                   stitchingWire(29),
                   shrinkWrap(30),
                   paperWrap(31),
                   staples(32),
                   inserts(33),
                   covers(34)
            -- End of values for Finisher MIB
               }

PrtMarkerSuppliesSupplyUnitTC ::= TEXTUAL-CONVENTION
    -- This value is a type 1 enumeration
    STATUS     current
    DESCRIPTION
        "Unit of this marker supply container/receptacle."
    SYNTAX     INTEGER {
                  tenThousandthsOfInches(3),  -- .0001
                  micrometers(4),
                  impressions(7),
                  sheets(8),
                  hours(11),
                  thousandthsOfOunces(12),
                  tenthsOfGrams(13),
                  hundrethsOfFluidOunces(14),
                  tenthsOfMilliliters(15),
                  feet(16),
                  meters(17),
           -- Value for Finisher MIB
                  items(18)        -- e.g. number of staples
            }

PrtMarkerSuppliesClassTC ::= TEXTUAL-CONVENTION
    --  This value is a type 1 enumeration
    STATUS     current
    DESCRIPTION
        "Indicates whether this supply entity represents a supply
        that is consumed or a receptacle that is filled."
    SYNTAX     INTEGER {
                   other(1),
                   supplyThatIsConsumed(3),
                   receptacleThatIsFilled(4)
               }

PrtMarkerColorantRoleTC ::= TEXTUAL-CONVENTION
    -- This value is a type 1 enumeration
    STATUS       current
    DESCRIPTION
         "The role played by this colorant."
    SYNTAX     INTEGER { --  Colorant Role
                   other(1),
                   process(3),
                   spot(4)
               }

--
-- Media Path Textual Conventions
--

PrtMediaPathMaxSpeedPrintUnitTC ::= TEXTUAL-CONVENTION
    -- This value is a type 1 enumeration
    STATUS       current
    DESCRIPTION
         "The unit of measure used in specifying the speed of all
         media paths in the printer."
    SYNTAX     INTEGER {
                   tenThousandthsOfInchesPerHour(3),-- .0001/hour
                   micrometersPerHour(4),
                   charactersPerHour(5),
                   linesPerHour(6),
                   impressionsPerHour(7),
                   sheetsPerHour(8),
                   dotRowPerHour(9),
                   feetPerHour(16),
                   metersPerHour(17)
               }

PrtMediaPathTypeTC ::= TEXTUAL-CONVENTION
    --   This value is a type 2 enumeration
    STATUS     current
    DESCRIPTION
        "The type of the media path for this media path."
    SYNTAX     INTEGER {
                   other(1),
                   unknown(2),
                   longEdgeBindingDuplex(3),
                   shortEdgeBindingDuplex(4),
                   simplex(5)
               }

--
-- Interpreter Group Textual Conventions
--


PrtInterpreterTwoWayTC ::= TEXTUAL-CONVENTION
    -- This is a type 1 enumeration
    STATUS current
    DESCRIPTION
         "Indicates whether or not this interpreter returns
         information back to the host."
    SYNTAX          INTEGER {
                    yes(3),
                    no(4)
                }

--
-- Console Group Textual Conventions
--

PrtConsoleColorTC ::= TEXTUAL-CONVENTION
    -- This value is a type 2 enumeration
    STATUS     current
    DESCRIPTION
        "The color of this light."
    SYNTAX INTEGER {
               other(1),
               unknown(2),
               white(3),
               red(4),
               green(5),
               blue(6),
               cyan(7),
               magenta(8),
               yellow(9),
               orange(10)
             }


--
-- Alert Group Textual Conventions
--

PrtAlertSeverityLevelTC ::= TEXTUAL-CONVENTION
    -- This value is a type 1 enumeration
    STATUS     current
    DESCRIPTION
         "The level of severity of this alert table entry.  The
         printer determines the severity level assigned to each
         entry into the table. A warning is defined to be a non-
         critical alert. The value also indicates whether the
         event is a binary change event or a unary change event."
    SYNTAX     INTEGER {
                   other(1),
                   criticalBinaryChangeEvent(3),
                   warningUnaryChangeEvent(4),
                   warningBinaryChangeEvent(5)
               }

PrtAlertTrainingLevelTC ::= TEXTUAL-CONVENTION
    -- This value is a type 2 enumeration
    STATUS     current
    DESCRIPTION
         "The level of training required to handle this alert, if
         human intervention is required. The
         noInterventionRequired value should be used if the event
         does not require any human intervention. The training
         level is an enumeration that is determined and assigned
         by the printer manufacturer based on the information or
         the training required to handle this alert.  The printer
         will break alerts into these different training levels.
         It is the responsibility of the management application
         in the system to determine how a particular alert is
         handled and how and to whom that alert is routed.  The
         following are the four training levels of alerts:

         Field Service - Alerts that typically require advanced
                         training and technical knowledge of the
                         printer and its sub-units. An example of
                         a technical person would be a
                         manufacturer's Field Service
                         representative, or other person formally
                         trained by the manufacturer or similar
                         representative.
         Trained -       Alerts that require an intermediate or
                         moderate level of knowledge of the
                         printer and its sub-units. A typical
                         examples of alerts that a trained
                         operator can handle is replacing
                         toner cartridges.
         Untrained -     Alerts that can be fixed without prior
                         training either because the action to
                         correct the alert is obvious or the
                         printer can help the untrained person
                         fix the problem. A typical example of
                         such an alert is reloading paper trays
                         and emptying output bins on a low end
                         printer.
         Management -    Alerts that have to do with overall
                         operation of and configuration of the
                         printer. Examples of management events
                         are configuration change of sub-units."
    SYNTAX     INTEGER {
                   other(1),
                   unknown(2),
                   untrained(3),
                   trained(4),
                   fieldService(5),
                   management(6),
                   noInterventionRequired(7)
               }

PrtAlertGroupTC ::= TEXTUAL-CONVENTION
    -- This value is a type 1 enumeration for values in the range
    -- 1 to 29.
    -- Values of 30 and greater are type 2 enumerations and are
    -- for use in other MIBs that augment tables in the Printer
    -- MIB. Therefore, other MIBs may assign alert codes of 30 or
    -- higher to use the alert table from the Printer MIB without
    -- requiring revising and re-publishing this document.
    STATUS     current
    DESCRIPTION
         "The type of sub-unit within the printer model that this
         alert is related.  Input, output, and markers are
         examples of printer model groups, i.e., examples of
         types of sub-units. Wherever possible, these
         enumerations match the sub-identifier that identifies
         the relevant table in the printer MIB.

         NOTE: Alert type codes have been added for the host
         resources MIB storage table and device table. These
         additional types are for situations in which the
         printer's storage and device objects
         must generate alerts (and possibly traps for critical
         alerts)."
    SYNTAX     INTEGER {
                   other(1),
                   hostResourcesMIBStorageTable(3),
                   hostResourcesMIBDeviceTable(4),
                   generalPrinter(5),
                   cover(6),
                   localization(7),
                   input(8),
                   output(9),
                   marker(10),
                   markerSupplies(11),
                   markerColorant(12),
                   mediaPath(13),
                   channel(14),
                   interpreter(15),
                   consoleDisplayBuffer(16),
                   consoleLights(17),
                   alert(18),
           -- Values for Finisher MIB
                   finDevice(30),
                   finSupply(31),
                   finSupplyMediaInput(32),
                   finAttributeTable(33)
           -- End of values for Finisher MIB
               }

PrtAlertCodeTC ::= TEXTUAL-CONVENTION
    -- This value is a type 2 enumeration
    STATUS     current
    DESCRIPTION
         "The code that describes the type of alert for this
         entry in the table. Binary change event alerts describe
         states of the subunit while unary change event alerts
         describe a single event. The same alert code can be used
         for a binary change event or a unary change event,
         depending on implementation. Also, the same alert code
         can be used to indicate a critical or a non-critical
         (warning) alert, depending on implementation. The value
         of prtAlertSeverityLevel specifies binary vs. unary and
         critical vs. non-critical for each event for the
         implementation.

         While there are some specific codes for many subunits,
         the generic codes should be used for most subunit
         alerts. The network management station can then query
         the subunit specified by prtAlertGroup to determine
         further subunit status and other subunit information.

         An agent shall not add two entries to the alert table
         for the same event, one containing a generic event code
         and the other containing a specific event code; the
         agent shall add only one entry in the alert table for
         each event; either generic (preferred) or specific, not
         both.

         Implementation of the unary change event
         alertRemovalOfBinaryChangeEntry(1801) is optional. When
         implemented, this alert code shall indicate to network
         management stations that the trailing edge of a binary
         change event has occurred and the corresponding alert
         entry has been removed from the alert table. As with all
         events, the alertRemovalOfBinaryChangeEntry(1801) alert
         shall be placed at the end of the alert table. Such an
         alert table entry shall specify the following
         information:

         prtAlertSeverityLevel   warningUnaryChangeEvent(4)
         prtAlertTrainingLevel   noInterventionRequired(7)
         prtAlertGroup           alert(18)
         prtAlertGroupIndex      the index of the row in the
                                 alert table of the binary
                                 change event that this event
                                 has removed.
         prtAlertLocation        unknown (-2)
         prtAlertCode       alertRemovalOfBinaryChangeEntry(1801)
         prtAlertDescription     <description or null string>
         prtAlertTime            the value of sysUpTime at
                                 the time of the removal of the
                                 binary change event from the
                                 alert table.

         Optionally, the agent may generate a trap coincident
         with removing the binary change event and placing the
         unary change event alertRemovalOfBinaryChangeEntry(1801)
         in the alert table. For such a trap, the prtAlertIndex
         sent with the above trap parameters shall be the index
         of the alertRemovalOfBinaryChangeEvent row that was
         added to the prtAlertTable; not the index of the row
         that was removed from the prtAlertTable."
    SYNTAX     INTEGER {
                   other(1),
                        -- an event that is not represented
                        -- by one of the alert codes
                        -- specified below.
                   unknown(2),
                        -- The following generic codes are common
                        -- to multiple groups. The NMS may
                        -- examine the prtAlertGroup object
                        -- to determine what group to query for
                        -- further information.
                coverOpened(3),
                coverClosed(4),
                interlockOpened(5),
                interlockClosed(6),
                configurationChanged(7),
                jammed(8),
                subunitMissing(9),
                        -- The subunit tray, bin, etc.
                        -- has been removed.
                subunitLifeAlmostOver(10),
                subunitLifeOver(11),
                subunitAlmostEmpty(12),
                subunitEmpty(13),
                subunitAlmostFull(14),
                subunitFull(15),
                subunitNearLimit(16),
                subunitAtLimit(17),
                subunitOpened(18),
                subunitClosed(19),
                subunitTurnedOn(20),
                subunitTurnedOff(21),
                subunitOffline(22),
                subunitPowerSaver(23),
                subunitWarmingUp(24),
                subunitAdded(25),
                subunitRemoved(26),
                subunitResourceAdded(27),
                subunitResourceRemoved(28),
                subunitRecoverableFailure(29),
                subunitUnrecoverableFailure(30),
                subunitRecoverableStorageError(31),
                subunitUnrecoverableStorageError(32),
                subunitMotorFailure(33),
                subunitMemoryExhausted(34),
                subunitUnderTemperature(35),
                subunitOverTemperature(36),
                subunitTimingFailure(37),
                subunitThermistorFailure(38),
            -- general Printer group
                doorOpen(501),    -- DEPRECATED
                                  -- Use coverOpened(3)
                doorClosed(502),  -- DEPRECATED
                                  -- Use coverClosed(4)
                poweredUp(503),
                poweredDown(504),
                printerNMSReset(505),
                        -- The printer has been reset by some
                        -- network management station(NMS)
                        -- writing into 'prtGeneralReset'.
                printerManualReset(506),
                        -- The printer has been reset manually.
                printerReadyToPrint(507),
                        -- The printer is ready to print. (i.e.,
                        -- not warming up, not in power save
                        -- state, not adjusting print quality,
                        -- etc.).

            -- Input Group
                inputMediaTrayMissing(801),
                inputMediaSizeChanged(802),
                inputMediaWeightChanged(803),
                inputMediaTypeChanged(804),
                inputMediaColorChanged(805),
                inputMediaFormPartsChange(806),
                inputMediaSupplyLow(807),
                inputMediaSupplyEmpty(808),
                inputMediaChangeRequest(809),
                    -- An interpreter has detected that a 
                    -- different medium is need in this input
                    -- tray subunit. The prtAlertDescription may
                    -- be used to convey a human readable
                    -- description of the medium required to
                    -- satisfy the request.
                inputManualInputRequest(810),
                    -- An interpreter has detected that manual
                    -- input is required in this subunit. The
                    -- prtAlertDescription may be used to convey
                    -- a human readable description of the medium
                    -- required to satisfy the request.
                inputTrayPositionFailure(811),
                    -- The input tray failed to position 
                    -- correctly.
                inputTrayElevationFailure(812),
                inputCannotFeedSizeSelected(813),
            -- Output Group
                outputMediaTrayMissing(901),
                outputMediaTrayAlmostFull(902),
                outputMediaTrayFull(903),
                outputMailboxSelectFailure(904),
            -- Marker group
                markerFuserUnderTemperature(1001),
                markerFuserOverTemperature(1002),
                markerFuserTimingFailure(1003),
                markerFuserThermistorFailure(1004),
                markerAdjustingPrintQuality(1005),
            -- Marker Supplies group
                markerTonerEmpty(1101),
                markerInkEmpty(1102),
                markerPrintRibbonEmpty(1103),
                markerTonerAlmostEmpty(1104),
                markerInkAlmostEmpty(1105),
                markerPrintRibbonAlmostEmpty(1106),
                markerWasteTonerReceptacleAlmostFull(1107),
                markerWasteInkReceptacleAlmostFull(1108),
                markerWasteTonerReceptacleFull(1109),
                markerWasteInkReceptacleFull(1110),
                markerOpcLifeAlmostOver(1111),
                markerOpcLifeOver(1112),
                markerDeveloperAlmostEmpty(1113),
                markerDeveloperEmpty(1114),
                markerTonerCartridgeMissing(1115),
            -- Media Path Device Group
                mediaPathMediaTrayMissing(1301),
                mediaPathMediaTrayAlmostFull(1302),
                mediaPathMediaTrayFull(1303),
            -- Interpreter Group
                interpreterMemoryIncreased(1501),
                interpreterMemoryDecreased(1502),
                interpreterCartridgeAdded(1503),
                interpreterCartridgeDeleted(1504),
                interpreterResourceAdded(1505),
                interpreterResourceDeleted(1506),
                interpreterResourceUnavailable(1507),
                interpreterComplexPageEncountered(1509),
                    -- The interpreter has encountered a page
                    -- that is too complex for the resources that
                    -- are available.
            -- Alert Group
                alertRemovalOfBinaryChangeEntry(1801)
                    -- A binary change event entry has been
                    -- removed from the alert table. This unary
                    -- change alert table entry is added to the
                    -- end of the alert table.
      }


-- The General Printer Group
--
-- The general printer sub-unit is responsible for the overall
-- control and status of the printer.  There is exactly one
-- general printer sub-unit in a printer.
--
-- Implementation of every object in this group is mandatory.

prtGeneral  OBJECT IDENTIFIER ::= { printmib 5 }

prtGeneralTable OBJECT-TYPE
    SYNTAX     SEQUENCE OF PrtGeneralEntry
    MAX-ACCESS not-accessible
    STATUS     current
    DESCRIPTION
        "A table of general information per printer.
        Objects in this table are defined in various
        places in the MIB, nearby the groups to
        which they apply.  They are all defined
        here to minimize the number of tables that would
        otherwise need to exist."
    ::= { prtGeneral 1 }

prtGeneralEntry OBJECT-TYPE
    SYNTAX      PrtGeneralEntry
    MAX-ACCESS  not-accessible
    STATUS      current
    DESCRIPTION
         "An entry exists in this table for each device entry in
         the host resources MIB device table with a device type
         of 'printer'"
    INDEX  { hrDeviceIndex }
    ::= { prtGeneralTable 1 }

PrtGeneralEntry ::= SEQUENCE {
    -- Note that not all of the objects in this sequence are in
    -- the general printer group. The group to which a
    -- object belongs is tagged with a label "General", "Input"
    -- "Output", etc. after each entry in the following sequence
    --
    prtGeneralConfigChanges         Counter32, -- General
    prtGeneralCurrentLocalization   Integer32, -- General
    prtGeneralReset                 PrtGeneralResetTC,
                                               -- General
    prtGeneralCurrentOperator       OCTET STRING,
                                        -- Responsible Party
    prtGeneralServicePerson         OCTET STRING,
                                        -- Responsible Party
    prtInputDefaultIndex            Integer32, -- Input
    prtOutputDefaultIndex           Integer32, -- Output
    prtMarkerDefaultIndex           Integer32, -- Marker
    prtMediaPathDefaultIndex        Integer32, -- Media Path
    prtConsoleLocalization          Integer32, -- Console
    prtConsoleNumberOfDisplayLines  Integer32, -- Console
    prtConsoleNumberOfDisplayChars  Integer32, -- Console
    prtConsoleDisable               INTEGER,   -- Console,
    prtAuxiliarySheetStartupPage    PresentOnOff,
                                               -- AuxiliarySheet
    prtAuxiliarySheetBannerPage     PresentOnOff,
                                               -- AuxiliarySheet,
    prtGeneralPrinterName           OCTET STRING,
                                               -- General
    prtGeneralSerialNumber          OCTET STRING,
                                               -- General
    prtAlertCriticalEvents          Counter32, -- Alert
    prtAlertAllEvents               Counter32  -- Alert
}

prtGeneralConfigChanges OBJECT-TYPE
    SYNTAX     Counter32
    MAX-ACCESS read-only
    STATUS     current
    DESCRIPTION
         "Counts configuration changes within the printer. A
         configuration change is defined to be an action that
         results in a change to any MIB object other than those
         that reflect status or level, or those that act as
         counters or gauges. In addition, any action that results
         in a row being added or deleted from any table in the
         Printer MIB is considered a configuration change. Such
         changes will often affect the capability of the printer
         to service certain types of print jobs. Management
         applications may cache infrequently changed
         configuration information about sub-units within the
         printer. This object should be incremented whenever the
         agent wishes to notify management applications that any
         cached configuration information for this device is to
         be considered 'stale'. At this point, the management
         application should flush any configuration information
         cached about this device and fetch new configuration
         information.

         The following are examples of actions that would cause
         the prtGeneralConfigChanges object to be incremented:

         - Adding an output bin
         - Changing the media in a sensing input tray
         - Changing the value of prtInputMediaType
         Note that the prtGeneralConfigChanges counter would not
         be incremented when an input tray is removed, or the
         level of an input device changes."

    ::= { prtGeneralEntry 1 }

prtGeneralCurrentLocalization OBJECT-TYPE
    SYNTAX     Integer32 (1..65535)
    MAX-ACCESS read-write
    STATUS     current
    DESCRIPTION
          "The value of the prtLocalizationIndex corresponding to
          the current language, country, and character set to be
          used for localized string values that are identified as
          being dependent on the value of this object.  Note that
          this object does not apply to localized strings in the
          prtConsole group or to any object that is not
          explicitly identified as being localized according to
          prtGeneralCurrentLocalization."
    ::= { prtGeneralEntry 2 }

 prtGeneralReset OBJECT-TYPE
    -- This value is a type 3 enumeration
    SYNTAX     PrtGeneralResetTC 
    MAX-ACCESS read-write
    STATUS     current
    DESCRIPTION
         "Setting this value to 'powerCycleReset',
         'resetToNVRAM', or 'resetToFactoryDefaults' will result
         in the resetting of the printer.  When read, this object
         will always have the value 'notResetting(3)', and a SET
         of the value 'notResetting' shall have no effect on the
         printer.  Some of the defined values are optional.
         However, every implementation must support at least the
         values 'notResetting' and 'resetToNVRAM'."
    ::= { prtGeneralEntry 3 }

-- The Responsible Party group
--
-- This group is optional.  However, to claim conformance to this
-- group, it is necessary to implement every object in the group.

prtGeneralCurrentOperator OBJECT-TYPE
    SYNTAX     OCTET STRING (SIZE(0..127))
    MAX-ACCESS read-write
    STATUS     current
    DESCRIPTION
         "The name of the person who is responsible for operating
         this printer. It is suggested that this string include
         information that would enable other humans to reach the
         operator, such as a phone number. As a convention to
         facilitate automatic notification of the operator by the
         agent or the network management station, the phone
         number, fax number or email address should be placed on
         a separate line starting with ASCII LF (hex 0x0A) and
         the ASCII text string (without the quotes): 'phone: ',
         'fax: ', and 'email: ', respectively. Phone numbers may
         contain digits, spaces and parentheses, which shall be
         ignored. Phone numbers may also include ASCII comma
         characters(hex 2C) that are used to indicate a two-
         second pause during the dialing sequence. If either the
         phone, fax, or email information is not available, then
         a line should not be included for this information.

         NOTE: For interoperability purposes, it is advisable to
         use email addresses formatted according to RFC 822
         requirements."
    ::= { prtGeneralEntry 4 }

prtGeneralServicePerson OBJECT-TYPE
    SYNTAX     OCTET STRING (SIZE(0..127))
    MAX-ACCESS read-write
    STATUS     current
    DESCRIPTION
         "The name of the person responsible for servicing this
         printer. It is suggested that this string include
         information that would enable other humans to reach the
         service person, such as a phone number. As a convention
         to facilitate automatic notification of the service
         person by the agent or a network management station, the
         phone number, fax number or email address should be
         placed on a separate line starting with ASCII LF (hex
         0x0A) and the ASCII text string (without the quotes):
         'phone: ', 'fax: ', and 'email: ', respectively. Phone
         numbers may contain digits, spaces and parentheses,
         which shall be ignored. Phone numbers can also include
         one or more ASCII comma characters(hex 2C) to indicate a
         two-second pause during the dialing sequence. If either
         the phone, fax, or email information is not available,
         then a line should not included for this information.

         NOTE: For interoperability purposes, it is advisable to
         use email addresses formatted according to RFC 822
         requirements."
    ::= { prtGeneralEntry 5 }

-- Default indexes section
--
-- The following four objects are used to specify the indexes of
-- certain subunits used as defaults during the printing process.

prtInputDefaultIndex OBJECT-TYPE
    SYNTAX     Integer32
    MAX-ACCESS read-write
    STATUS     current
    DESCRIPTION
         "The value of prtInputIndex corresponding to the default
         input sub-unit: that is, this object selects the default
         source of input media.

         This value shall be -1 if there is no default input
         subunit specified for the printer as a whole.  In this
         case, the actual default input subunit may be specified
         by means outside the scope of this MIB, such as by each
         interpreter in a printer with multiple interpreters."

    ::= { prtGeneralEntry 6 }

prtOutputDefaultIndex OBJECT-TYPE
    SYNTAX     Integer32
    MAX-ACCESS read-write
    STATUS     current
    DESCRIPTION
         "The value of prtOutputIndex corresponding to the
         default output sub-unit; that is, this object selects
         the default output destination.

         This value shall be -1 if there is no default output
         subunit specified for the printer as a whole.  In this
         case, the actual default output subunit may be specified
         by means outside the scope of this MIB, such as by each
         interpreter in a printer with multiple interpreters."

    ::= { prtGeneralEntry 7 }

prtMarkerDefaultIndex OBJECT-TYPE
    SYNTAX     Integer32 (1..65535)
    MAX-ACCESS read-write
    STATUS     current
    DESCRIPTION
        "The value of prtMarkerIndex corresponding to the
        default marker sub-unit; that is, this object selects the
        default marker."
    ::= { prtGeneralEntry 8 }

prtMediaPathDefaultIndex OBJECT-TYPE
    SYNTAX     Integer32 (1..65535)
    MAX-ACCESS read-write
    STATUS     current
    DESCRIPTION
        "The value of prtMediaPathIndex corresponding to
        the default media path; that is, the selection of the
        default media path."
    ::= { prtGeneralEntry 9 }

-- Console general section
--
-- The following four objects describe overall parameters of the
-- printer console subsystem.

prtConsoleLocalization OBJECT-TYPE
    SYNTAX     Integer32 (1..65535)
    MAX-ACCESS read-write
    STATUS     current
    DESCRIPTION
         "The value of the prtLocalizationIndex corresponding to
         the language, country, and character set to be used for
         the console.  This localization applies both to the
         actual display on the console as well as the encoding of
         these console objects in management operations."
    ::= { prtGeneralEntry 10 }

prtConsoleNumberOfDisplayLines OBJECT-TYPE
    SYNTAX     Integer32 (0..65535)
    MAX-ACCESS read-only
    STATUS     current
    DESCRIPTION
        "The number of lines on the printer's physical
        display.  This value is 0 if there are no lines on the
        physical display or if there is no physical display"
    ::= { prtGeneralEntry 11 }

prtConsoleNumberOfDisplayChars OBJECT-TYPE
    SYNTAX     Integer32 (0..65535)
    MAX-ACCESS read-only
    STATUS     current
    DESCRIPTION
         "The number of characters per line displayed on the
         physical display. This value is 0 if there are no lines
         on the physical display or if there is no physical
         display"
    ::= { prtGeneralEntry 12 }

prtConsoleDisable OBJECT-TYPE
    SYNTAX     INTEGER {
                   operatorConsoleEnabled (3),
                   operatorConsoleDisabled (4),
                   operatorConsoleEnabledLevel1 (5),
                   operatorConsoleEnabledLevel2 (6),
                   operatorConsoleEnabledLevel3 (7)
               }
    MAX-ACCESS read-write
    STATUS     current
    DESCRIPTION
         "If the object prtConsoleDisable has value
         'operatorConsoleDisabled' then input is not accepted
         from the operator console. If the object
         prtConsoleDisable has the value 'operatorConsoleEnabled'
         then input is accepted from the operator console. If the
         object prtConsoleDisable has the value
         'operatorConsoleEnabledLevel1',
         'operatorConsoleEnabledLevel2' or
         'operatorConsoleEnabledLevel3' then limited input is
         accepted from the operator console; the limitations are
         product specific, however, the limitations are generally
         less restrictive for operatorConsoleEnabledLevel1 than
         for operatorConsoleEnabledLeve2, which is less
         restrictive than operatorConsoleEnabledLevel3.

         The value of the prtConsoleDisable object is a type-2
         enumeration."
    ::= { prtGeneralEntry 13 }


-- The Auxiliary Sheet Group
--
-- The auxiliary sheet group allows the administrator to control
-- the production of auxiliary sheets by the printer. This group
-- contains only the "prtAuxiliarySheetStartupPage" and
-- "prtAuxiliarySheetBannerPage" objects.
--
-- This group is optional. However, to claim conformance to this
-- group it is necessary to implement every object in the group.

prtAuxiliarySheetStartupPage OBJECT-TYPE
     SYNTAX     PresentOnOff
     MAX-ACCESS read-write
     STATUS     current
     DESCRIPTION
         "Used to enable or disable printing a startup page. If
         enabled, a startup page will be printed shortly after
         power-up, when the device is ready. Typical startup
         pages include test patterns and/or printer configuration
         information."
     ::= { prtGeneralEntry 14 }

prtAuxiliarySheetBannerPage OBJECT-TYPE
     SYNTAX     PresentOnOff
     MAX-ACCESS read-write
     STATUS     current
     DESCRIPTION
         "Used to enable or disable printing banner pages at the
         beginning of jobs. This is a master switch which applies
         to all jobs, regardless of interpreter."
     ::= { prtGeneralEntry 15 }

-- Administrative section
--
-- The following two objects are used to specify administrative
-- information assigned to the printer.

prtGeneralPrinterName OBJECT-TYPE
     SYNTAX     OCTET STRING (SIZE (0..127))
     MAX-ACCESS read-write
     STATUS     current
     DESCRIPTION
         "An administrator-specified name for this printer.
         Depending upon implementation of this printer, the value
         of this object may or may not be same as the value for
         the MIB-II 'SysName' object."
     ::= { prtGeneralEntry 16 }

prtGeneralSerialNumber OBJECT-TYPE
     SYNTAX     OCTET STRING (SIZE (0..255))
     MAX-ACCESS read-write
     STATUS     current
     DESCRIPTION
         "A recorded serial number for this device that indexes
         some type device catalog or inventory. This value is
         usually set by the device manufacturer but the MIB
         supports the option of writing for this object for site-
         specific administration of device inventory or
         tracking."
    ::= { prtGeneralEntry 17 }

-- General alert table section
--
-- The following two objects are used to specify counters
-- associated with the Alert Table.

prtAlertCriticalEvents OBJECT-TYPE
    SYNTAX     Counter32
    MAX-ACCESS read-only
    STATUS     current
    DESCRIPTION
         "A running counter of the number of critical alert
         events that have been recorded in the alert table. The
         value of this object is RESET in the event of a power
         cycle operation (i.e., the value is not persistent."
    ::= { prtGeneralEntry 18 }

prtAlertAllEvents OBJECT-TYPE
    SYNTAX     Counter32
    MAX-ACCESS read-only
    STATUS     current
    DESCRIPTION
         "A running counter of the total number of alert event
         entries (critical and non-critical) that have been
         recorded in the alert table"
    ::= { prtGeneralEntry 19 }


-- The Cover Table
--
-- The cover portion of the General print sub-unit describes the
-- covers and interlocks of the printer.  The Cover Table has an
-- entry for each cover and interlock.

prtCover    OBJECT IDENTIFIER ::= { printmib 6 }

prtCoverTable OBJECT-TYPE
    SYNTAX     SEQUENCE OF PrtCoverEntry
    MAX-ACCESS not-accessible
    STATUS     current
    DESCRIPTION
        "A table of the covers and interlocks of the printer."
    ::= { prtCover 1 }

prtCoverEntry OBJECT-TYPE
    SYNTAX     PrtCoverEntry
    MAX-ACCESS not-accessible
    STATUS     current
    DESCRIPTION
        "Information about a cover or interlock.
        Entries may exist in the table for each device
        index with a device type of 'printer'."
    INDEX  { hrDeviceIndex, prtCoverIndex }
    ::= { prtCoverTable 1 }

PrtCoverEntry ::= SEQUENCE {
    prtCoverIndex            Integer32,
    prtCoverDescription      OCTET STRING,
    prtCoverStatus           PrtCoverStatusTC
}

prtCoverIndex OBJECT-TYPE
    SYNTAX     Integer32 (1..65535)
    MAX-ACCESS not-accessible
    STATUS     current
    DESCRIPTION
         "A unique value used by the printer to identify this
         Cover sub-unit.  Although these values may change due to
         a major reconfiguration of the device (e.g. the addition
         of new cover sub-units to the printer), values are
         expected to remain stable across successive printer
         power cycles."
    ::= { prtCoverEntry 1 }

prtCoverDescription OBJECT-TYPE
    SYNTAX     OCTET STRING (SIZE(0..255))
    MAX-ACCESS read-only
    STATUS     current
    DESCRIPTION
         "The manufacturer provided cover sub-mechanism name in
         the localization specified by
         prtGeneralCurrentLocalization."
    ::= { prtCoverEntry 2 }

prtCoverStatus  OBJECT-TYPE
    --  This value is a type 2 enumeration
    SYNTAX     PrtCoverStatusTC
    MAX-ACCESS read-only
    STATUS     current
    DESCRIPTION
        "The status of this cover sub-unit."
    ::= { prtCoverEntry 3 }

-- The Localization Table
--
-- The localization portion of the General printer sub-unit is
-- responsible for identifying the natural language, country, and
-- character set in which character strings are expressed. There
-- may be one or more localizations supported per printer. The
-- available localizations are represented by the Localization
-- table.

prtLocalization  OBJECT IDENTIFIER ::= { printmib 7 }

prtLocalizationTable OBJECT-TYPE
    SYNTAX     SEQUENCE OF PrtLocalizationEntry
    MAX-ACCESS not-accessible
    STATUS     current
    DESCRIPTION
        "The available localizations in this printer."
    ::= { prtLocalization 1 }

prtLocalizationEntry OBJECT-TYPE
    SYNTAX     PrtLocalizationEntry
    MAX-ACCESS not-accessible
    STATUS     current
    DESCRIPTION
        "A description of a localization.
        Entries may exist in the table for each device
        index with a device type of 'printer'."
    INDEX  { hrDeviceIndex, prtLocalizationIndex }
    ::= { prtLocalizationTable 1 }

PrtLocalizationEntry ::= SEQUENCE {
        prtLocalizationIndex          Integer32,
        prtLocalizationLanguage       DisplayString,
        prtLocalizationCountry        DisplayString,
        prtLocalizationCharacterSet   CodedCharSet
}

prtLocalizationIndex OBJECT-TYPE
    SYNTAX     Integer32 (1..65535)
    MAX-ACCESS not-accessible
    STATUS     current
    DESCRIPTION
         "A unique value used by the printer to identify this
         localization entry.  Although these values may change
         due to a major reconfiguration of the device (e.g., the
         addition of new localization data to the printer),
         values are expected to remain stable across successive
         printer power cycles."
    ::= { prtLocalizationEntry 1 }

prtLocalizationLanguage OBJECT-TYPE
    SYNTAX     DisplayString (SIZE(0..2))
    MAX-ACCESS read-only
    STATUS     current
    DESCRIPTION
         "A two character language code from ISO 639.  Examples
         en, gb, ca, fr, de."
    ::= { prtLocalizationEntry 2 }

prtLocalizationCountry OBJECT-TYPE
    SYNTAX     DisplayString (SIZE(0..2))
    MAX-ACCESS read-only
    STATUS     current
    DESCRIPTION
         "A two character country code from ISO 3166, a blank
         string (two space characters) shall indicate that the
         country is not defined.  Examples: US, FR, DE, ..."
    ::= { prtLocalizationEntry 3 }

prtLocalizationCharacterSet OBJECT-TYPE
    SYNTAX     CodedCharSet
    MAX-ACCESS read-only
    STATUS     current
    DESCRIPTION
      "The coded character set used for this localization."
    ::= { prtLocalizationEntry 4 }

-- The System Resources Tables
--
-- The Printer MIB makes use of the Host Resources MIB to
-- define system resources by referencing the storage
-- and device groups of the print group.  In order to
-- determine, amongst multiple printers serviced by
-- one agent, which printer owns a particular resource,
-- the prtStorageRef and prtDeviceRef tables associate
-- particular storage and device entries to printers.

prtStorageRefTable OBJECT-TYPE
    SYNTAX     SEQUENCE OF PrtStorageRefEntry
    MAX-ACCESS not-accessible
    STATUS     current
    DESCRIPTION
        ""
    ::= { prtGeneral 2 }

prtStorageRefEntry OBJECT-TYPE
    SYNTAX     PrtStorageRefEntry
    MAX-ACCESS not-accessible
    STATUS     current
    DESCRIPTION
         "This table will have an entry for each entry in the
         Host Resources MIB storage table that represents storage
         associated with a printer managed by this agent."
    INDEX      { hrStorageIndex, prtStorageRefSeqNumber }
    ::= { prtStorageRefTable 1 }

PrtStorageRefEntry ::= SEQUENCE {
    prtStorageRefSeqNumber  Integer32,
    prtStorageRefIndex      Integer32
}

prtStorageRefSeqNumber OBJECT-TYPE
    SYNTAX     Integer32 (1..65535)
    MAX-ACCESS not-accessible
    STATUS     current
    DESCRIPTION
         "This value will be unique amongst all entries with a
         common value of hrStorageIndex. This object allows a
         storage entry to point to the multiple printer devices
         with which it is associated."

    ::= { prtStorageRefEntry 1 }

prtStorageRefIndex OBJECT-TYPE
    SYNTAX     Integer32 (1..65535)
    MAX-ACCESS read-only
    STATUS     current
    DESCRIPTION
         "The value of the hrDeviceIndex of the printer device
         that this storageEntry is associated with."
    ::= { prtStorageRefEntry 2 }

prtDeviceRefTable OBJECT-TYPE
    SYNTAX     SEQUENCE OF PrtDeviceRefEntry
    MAX-ACCESS not-accessible
    STATUS     current
    DESCRIPTION
        ""
    ::= { prtGeneral 3 }

prtDeviceRefEntry OBJECT-TYPE
    SYNTAX     PrtDeviceRefEntry
    MAX-ACCESS not-accessible
    STATUS     current
    DESCRIPTION
         "This table will have an entry for each entry in the
         Host Resources MIB device table that represents a device
         associated with a printer managed by this agent."

    INDEX      { hrDeviceIndex, prtDeviceRefSeqNumber }
    ::= { prtDeviceRefTable 1 }

PrtDeviceRefEntry ::= SEQUENCE {
    prtDeviceRefSeqNumber   Integer32,
    prtDeviceRefIndex       Integer32
}

prtDeviceRefSeqNumber OBJECT-TYPE
    SYNTAX     Integer32 (1..65535)
    MAX-ACCESS not-accessible
    STATUS     current
    DESCRIPTION
         "This value will be unique amongst all entries with a
         common value of hrDeviceIndex. This object allows a
         device entry to point to the multiple printer devices
         with which it is associated."
    ::= { prtDeviceRefEntry 1 }

prtDeviceRefIndex OBJECT-TYPE
    SYNTAX     Integer32 (1..65535)
    MAX-ACCESS read-only
    STATUS     current
    DESCRIPTION
         "The value of the hrDeviceIndex of the printer device
         that this deviceEntry is associated with."
    ::= { prtDeviceRefEntry 2 }


-- The Input Group
--
-- Input sub-units are managed as a tabular, indexed collection
-- of possible devices capable of providing media for input to
-- the printing process. Input sub-units typically have a
-- location, a type, an identifier, a set of constraints on
-- possible media sizes and potentially other media
-- characteristics, and may be capable of indicating current
-- status or capacity.
--
-- Implementation of every object in this group is mandatory.


prtInput   OBJECT IDENTIFIER ::= { printmib 8 }


prtInputTable OBJECT-TYPE
    SYNTAX     SEQUENCE OF PrtInputEntry
    MAX-ACCESS not-accessible
    STATUS     current
    DESCRIPTION
         "A table of the devices capable of providing media for
         input to the printing process."
    ::= { prtInput 2 }

prtInputEntry OBJECT-TYPE
    SYNTAX     PrtInputEntry
    MAX-ACCESS not-accessible
    STATUS     current
    DESCRIPTION
         "Attributes of a device capable of providing media for
         input to the printing process. Entries may exist in the
         table for each device index with a device type of
         'printer'."
    INDEX  { hrDeviceIndex, prtInputIndex }
    ::= { prtInputTable 1 }

PrtInputEntry ::= SEQUENCE {
        prtInputIndex                     Integer32,
        prtInputType                      PrtInputTypeTC,
        prtInputDimUnit                   PrtMediaUnitTC,
        prtInputMediaDimFeedDirDeclared   Integer32,
        prtInputMediaDimXFeedDirDeclared  Integer32,
        prtInputMediaDimFeedDirChosen     Integer32,
        prtInputMediaDimXFeedDirChosen    Integer32,
        prtInputCapacityUnit              PrtCapacityUnitTC,
        prtInputMaxCapacity               Integer32,
        prtInputCurrentLevel              Integer32,
        prtInputStatus                    PrtSubUnitStatusTC,
        prtInputMediaName                 OCTET STRING,
        prtInputName                      OCTET STRING,
        prtInputVendorName                OCTET STRING,
        prtInputModel                     OCTET STRING,
        prtInputVersion                   OCTET STRING,
        prtInputSerialNumber              OCTET STRING,
        prtInputDescription               OCTET STRING,
        prtInputSecurity                  PresentOnOff,
        prtInputMediaWeight               Integer32,
        prtInputMediaType                 OCTET STRING,
        prtInputMediaColor                OCTET STRING,
        prtInputMediaFormParts            Integer32,
        prtInputMediaLoadTimeout          Integer32,
        prtInputNextIndex                 Integer32
}

prtInputIndex OBJECT-TYPE
    SYNTAX     Integer32 (1..65535)
    MAX-ACCESS not-accessible
    STATUS     current
    DESCRIPTION
         "A unique value used by the printer to identify this
         input sub-unit. Although these values may change due to
         a major reconfiguration of the device (e.g. the addition
         of n input sub-units to the printer), values are
         expected to remain stable across successive printer
         power cycles."
    ::= { prtInputEntry 1 }

prtInputType OBJECT-TYPE
    SYNTAX     PrtInputTypeTC
    MAX-ACCESS read-only
    STATUS     current
    DESCRIPTION
         "The type of technology (discriminated primarily
         according to feeder mechanism type) employed by the
         input sub-unit.  Note, the Optional Input Class provides
         for a descriptor field to further qualify the other
         choice."
    ::= { prtInputEntry 2 }

prtInputDimUnit OBJECT-TYPE
    SYNTAX     PrtMediaUnitTC
    MAX-ACCESS read-only
    STATUS     current
    DESCRIPTION
        "The unit of measurement for use calculating and relaying
         dimensional values for this input sub-unit."
    ::= { prtInputEntry 3 }

prtInputMediaDimFeedDirDeclared OBJECT-TYPE
    SYNTAX     Integer32
    MAX-ACCESS read-write
    STATUS     current
    DESCRIPTION
         "This object provides the value of the declared
         dimension, in the feed direction, of the media that is
         (or, if empty, was or will be) in this input sub-unit.
         The feed direction is the direction in which the media
         is fed on this sub-unit.  This dimension is measured in
         input sub-unit dimensional units (prtInputDimUnit).  If
         this input sub-unit can reliably sense this value, the
         value is sensed by the printer and may not be changed by
         management requests.  Otherwise, the value may be
         changed. The value (-1) means other and specifically
         means that this sub-unit places no restriction on this
         parameter.

         The value (-2) indicates unknown."
    ::= { prtInputEntry 4 }

prtInputMediaDimXFeedDirDeclared OBJECT-TYPE
    SYNTAX     Integer32
    MAX-ACCESS read-write
    STATUS     current
    DESCRIPTION
         "This object provides the value of the declared
         dimension, in the cross feed direction, of the media
         that is (or, if empty, was or will be) in this input
         sub-unit.  The cross  feed direction is ninety degrees
         relative to the feed direction associated with this sub-
         unit. This dimension is measured in input sub-unit
         dimensional units (prtInputDimUnit).  If this input sub-
         unit can reliably sense this value, the value is sensed
         by the printer and may not be changed by management
         requests. Otherwise, the value may be changed. The value
         (-1) means other and specifically means that this sub-
         unit places no restriction on this parameter. The value
         (-2) indicates unknown."
    ::= { prtInputEntry 5 }

prtInputMediaDimFeedDirChosen OBJECT-TYPE
    SYNTAX     Integer32
    MAX-ACCESS read-only
    STATUS     current
    DESCRIPTION
         "The printer will act as if media of the chosen
         dimension (in the feed direction) is present in this
         input source.  Note that this value will be used even if
         the input tray is empty. Feed dimension measurements are
         taken relative to the feed direction associated with
         that sub-unit and are in input sub-unit dimensional
         units (MediaUnit). If the printer supports the declared
         dimension, the granted dimension is the same as the
         declared dimension. If not, the granted dimension is set
         to the closest dimension that the printer supports when
         the declared dimension is set. The value (-1) means
         other and specifically indicates that this sub-unit
         places no restriction on this parameter. The value (-2)
         indicates unknown."
    ::= { prtInputEntry 6 }

prtInputMediaDimXFeedDirChosen OBJECT-TYPE
    SYNTAX     Integer32
    MAX-ACCESS read-only
    STATUS     current
    DESCRIPTION
         "The printer will act as if media of the chosen
         dimension (in the cross feed direction) is present in
         this input source. Note that this value will be used
         even if the input tray is empty.  The cross feed
         direction is ninety degrees relative to the feed
         direction associated with this sub-unit. This dimension
         is measured in input sub-unit dimensional units
         (MediaUnit).  If the printer supports the declare
         dimension, the granted dimension is the same as the
         declared dimension. If not, the granted dimension is set
         to the closest dimension that the printer supports when
         the declared dimension is set. The value (-1) means
         other and specifically indicates that this sub-unit
         places no restriction on this parameter.  The value (-2)
         indicates unknown."
    ::= { prtInputEntry 7 }

prtInputCapacityUnit OBJECT-TYPE
    SYNTAX     PrtCapacityUnitTC
    MAX-ACCESS read-only
    STATUS     current
    DESCRIPTION
         "The unit of measurement for use in calculating and
         relaying capacity values for this input sub-unit."
    ::= { prtInputEntry 8 }

prtInputMaxCapacity OBJECT-TYPE
    SYNTAX     Integer32
    MAX-ACCESS read-write
    STATUS     current
    DESCRIPTION
         "The maximum capacity of the input sub-unit in input
         sub-unit capacity units (PrtCapacityUnitTC).  There is
         no convention associated with the media itself so this
         value reflects claimed capacity. If this input sub-unit
         can reliably sense this value, the value is sensed by
         the printer and may not be changed by management
         requests; otherwise, the value may be written (by a
         Remote Control Panel or a Management Application). The
         value (-1) means other and specifically indicates that
         the sub-unit places no restrictions on this parameter.
         The value (-2) means unknown."
    ::= { prtInputEntry 9 }

prtInputCurrentLevel OBJECT-TYPE
    SYNTAX     Integer32 --    in capacity units
                         --   (PrtCapacityUnitTC).
    MAX-ACCESS read-write
    STATUS     current
    DESCRIPTION
         "The current capacity of the input sub-unit in input
         sub-unit capacity units (PrtCapacityUnitTC). If this
         input sub-unit can reliably sense this value, the value
         is sensed by the printer and may not be changed by
         management requests; otherwise, the value may be written
         (by a Remote Control Panel or a Management Application).
         The value (-1) means other and specifically indicates
         that the sub-unit places no restrictions on this
         parameter. The value (-2) means unknown. The value (-3)
         means that the printer knows that at least one unit
         remains."
    ::= { prtInputEntry 10 }

prtInputStatus OBJECT-TYPE
    SYNTAX     PrtSubUnitStatusTC
    MAX-ACCESS read-only
    STATUS     current
    DESCRIPTION
        "The current status of this input sub-unit."
    ::= { prtInputEntry 11 }

prtInputMediaName OBJECT-TYPE
    SYNTAX     OCTET STRING (SIZE(0..63))
    MAX-ACCESS read-write
    STATUS     current
    DESCRIPTION
         "A description of the media contained in this input sub-
         unit; This description is intended for display to a
         human operator. This description is not processed by the
         printer.  It is used to provide information not
         expressible in terms of the other media attributes (e.g.
         prtInputMediaDimFeedDirChosen,
         prtInputMediaDimXFeedDirChosen, prtInputMediaWeight,
         prtInputMediaType). An example would be 'legal tender
         bond paper'."
    REFERENCE
         "See Appendix C, 'Media Names'."
    ::= { prtInputEntry 12 }

--             INPUT MEASUREMENT
--
--     _______ |               |
--      ^      |               |
--      |      |               |                 |
--      |      |_ _ _ _ _ _ _ _| _______________ |direction
--      |      |               |      ^          v
-- MaxCapacity |    Sheets     |      |
--      |      |     left      | CurrentLevel
--      |      |      in       |      |
--      v      |     tray      |      v
--     _______ +_______________+ _______


-- The Extended Input Group
--
-- This group is optional.  However, to claim conformance to this
-- group, it is necessary to implement every object in the group.


prtInputName OBJECT-TYPE
    SYNTAX     OCTET STRING (SIZE(0..63))
    MAX-ACCESS read-write
    STATUS     current
    DESCRIPTION
        "The name assigned to this input sub-unit."
    ::= { prtInputEntry 13 }

prtInputVendorName OBJECT-TYPE
    SYNTAX     OCTET STRING (SIZE(0..63))
    MAX-ACCESS read-only
    STATUS     current
    DESCRIPTION
        "The vendor name of this input sub-unit."
    ::= { prtInputEntry 14 }

prtInputModel OBJECT-TYPE
    SYNTAX     OCTET STRING (SIZE(0..63))
    MAX-ACCESS read-only
    STATUS     current
    DESCRIPTION
        "The model name of this input sub-unit."
    ::= { prtInputEntry 15 }

prtInputVersion OBJECT-TYPE
    SYNTAX     OCTET STRING (SIZE(0..63))
    MAX-ACCESS read-only
    STATUS     current
    DESCRIPTION
        "The version of this input sub-unit."
    ::= { prtInputEntry 16 }

prtInputSerialNumber OBJECT-TYPE
    SYNTAX     OCTET STRING (SIZE(0..63))
    MAX-ACCESS read-only
    STATUS     current
    DESCRIPTION
        "The serial number assigned to this input sub-unit."
    ::= { prtInputEntry 17 }

prtInputDescription OBJECT-TYPE
    SYNTAX     OCTET STRING (SIZE(0..255))
    MAX-ACCESS read-only
    STATUS     current
    DESCRIPTION
         "A free-form text description of this input sub-unit in
         the localization specified by
         prtGeneralCurrentLocalization."
    ::= { prtInputEntry 18 }

prtInputSecurity OBJECT-TYPE
    SYNTAX     PresentOnOff
    MAX-ACCESS read-write
    STATUS     current
    DESCRIPTION
         "Indicates if this input sub-unit has some security
         associated with it."
    ::= { prtInputEntry 19 }

-- The Input Media Group
--
-- The Input Media Group supports identification of media
-- installed or available for use on a printing device.
-- Medium resources are identified by name, and include a
-- collection of characteristic attributes that may further be
-- used for selection and management of them.
-- The Input Media group consists of a set of optional
-- "columns" in the Input Table. In this manner, a minimally
-- conforming implementation may choose to not support reporting
-- of media resources if it cannot do so.
--
-- This group is optional.  However, to claim conformance to this
-- group, it is necessary to implement every object in the group.

prtInputMediaWeight  OBJECT-TYPE
    SYNTAX     Integer32
    MAX-ACCESS read-write
    STATUS     current
    DESCRIPTION
         "The weight of the medium associated with this input
         sub-unit in grams / per meter squared. The value (-2)
         means unknown."
    ::= { prtInputEntry 20 }

prtInputMediaType OBJECT-TYPE
    SYNTAX     OCTET STRING (SIZE(0..63))
    MAX-ACCESS read-write
    STATUS     current
    DESCRIPTION
         "The name of the type of medium associated with this
         input sub-unit. This name need not be processed by the
         printer; it might simply be displayed to an operator.
         The standardized string values from ISO 10175 (DPA) and
         ISO 10180 (SPDL) are:

         stationery       Separately cut sheets of an opaque
                          material
         transparency     Separately cut sheets of a transparent
                          material
         envelope         Envelopes that can be used for
                          conventional mailing purposes
         envelope-plain   Envelopes that are not preprinted and
                          have no windows
         envelope-window  Envelopes that have windows for
                          addressing purposes
         continuous-long  Continuously connected sheets of an
                          opaque material connected along the
                          long edge
         continuous-short Continuously connected sheets of an
                          opaque material connected along the
                          short edge
         tab-stock        Media with tabs
         multi-part-form  Form medium composed of multiple layers
                          not pre-attached to one another; each
                          sheet may be drawn separately from an
                          input source
         labels           Label stock
         multi-layer      Form medium composed of multiple layers
                          which are pre-attached to one another;
                          e.g., for use with impact printers.

         Implementers may add additional string values. The
         naming
         conventions in ISO 9070 are recommended in order to
         avoid
         potential name clashes."
    ::= { prtInputEntry 21 }

prtInputMediaColor OBJECT-TYPE
    SYNTAX     OCTET STRING (SIZE(0..63))
    MAX-ACCESS read-write
    STATUS     current
    DESCRIPTION
        "The name of the color of the medium associated with
        this input sub-unit using standardized string values
        from ISO 10175 (DPA) and ISO 10180 (SPDL) which are:

        other
        unknown
        white
        pink
        yellow
        buff
        goldenrod
        blue
        green
        transparent

        Implementers may add additional string values. The naming
        conventions in ISO 9070 are recommended in order to avoid
        potential name clashes."
    ::= { prtInputEntry 22 }

prtInputMediaFormParts OBJECT-TYPE
    SYNTAX     Integer32
    MAX-ACCESS read-write
    STATUS     current
    DESCRIPTION
         "The number of parts associated with the medium
         associated with this input sub-unit if the medium is a
         multi-part form.  The value (-1) means other and
         specifically indicates that the device places no
         restrictions on this parameter.  The value (-2) means
         unknown."
    ::= { prtInputEntry 23 }

-- The Input Switching Group
--
-- The input switching group allows the administrator to set the
-- input subunit time-out for the printer and to control the
-- automatic input subunit switching by the printer when an input
-- subunit becomes empty.
--
-- This group is optional. However, to claim conformance to this
-- group, it is required to implement every object in the group.

prtInputMediaLoadTimeout OBJECT-TYPE
   SYNTAX     Integer32
   MAX-ACCESS read-write
   STATUS     current
   DESCRIPTION
         "When the printer is not able to print due to a subunit
         being empty or the requested media must be manually
         loaded, the printer will wait for the duration (in
         seconds) specified by this object. Upon expiration of
         the time-out, the printer will take the action specified
         by prtInputNextIndex.

         The event which causes the printer to enter the waiting
         state is product specific. If the printer is not waiting
         for manually fed media, it may switch from an empty
         subunit to a different subunit without waiting for the
         time-out to expire.

         A value of (-1) implies 'other' or 'infinite' which
         translates to 'wait forever'. The action which causes
         printing to continue is product specific. A value of (-
         2) implies 'unknown'."

   ::= { prtInputEntry 24 }

prtInputNextIndex OBJECT-TYPE
   SYNTAX     Integer32
   MAX-ACCESS read-write
   STATUS     current
   DESCRIPTION
         "The value of prtInputIndex corresponding to the input
         subunit which will be used when this input subunit is
         emptied and the time-out specified by
         prtInputMediaLoadTimeout expires. A value of zero(0)
         indicates that auto input switching will not occur when
         this input subunit is emptied. If the time-out specified
         by prtInputLoadMediaTimeout expires and this value is
         zero(0), the job will be aborted. A value of (-1) means
         other. The value (-2) means 'unknown' and specifically
         indicates that an implementation specific method will
         determine the next input subunit to use at the time this
         subunit is emptied and the time-out expires. The value(-
         3) means input switching is not supported for this
         subunit."
   ::= { prtInputEntry 25 }

-- The Output Group
--
-- Output sub-units are managed as a tabular, indexed collection
-- of possible devices capable of receiving media delivered from
-- the printing process.  Output sub-units typically have a
-- location, a type, an identifier, a set of constraints on
-- possible media sizes and potentially other characteristics,
-- and may be capable of indicating current status or capacity.
--
-- Implementation of every object in this group is mandatory.

prtOutput  OBJECT IDENTIFIER ::= { printmib 9 }


prtOutputTable OBJECT-TYPE
    SYNTAX     SEQUENCE OF PrtOutputEntry
    MAX-ACCESS not-accessible
    STATUS     current
    DESCRIPTION
         "A table of the devices capable of receiving media
         delivered from the printing process."
    ::= { prtOutput 2 }

prtOutputEntry OBJECT-TYPE
    SYNTAX     PrtOutputEntry
    MAX-ACCESS not-accessible
    STATUS     current
    DESCRIPTION
         "Attributes of a device capable of receiving media
         delivered from the printing process. Entries may exist
         in the table for each device index with a device type of
         'printer'."
    INDEX  { hrDeviceIndex, prtOutputIndex }
    ::= { prtOutputTable 1 }

PrtOutputEntry ::= SEQUENCE {
        prtOutputIndex                    Integer32,
        prtOutputType                     PrtOutputTypeTC,
        prtOutputCapacityUnit             PrtCapacityUnitTC,
        prtOutputMaxCapacity              Integer32,
        prtOutputRemainingCapacity        Integer32,
        prtOutputStatus                   PrtSubUnitStatusTC,
        prtOutputName                     OCTET STRING,
        prtOutputVendorName               OCTET STRING,
        prtOutputModel                    OCTET STRING,
        prtOutputVersion                  OCTET STRING,
        prtOutputSerialNumber             OCTET STRING,
        prtOutputDescription              OCTET STRING,
        prtOutputSecurity                 PresentOnOff,
        prtOutputDimUnit                  PrtMediaUnitTC,
        prtOutputMaxDimFeedDir            Integer32,
        prtOutputMaxDimXFeedDir           Integer32,
        prtOutputMinDimFeedDir            Integer32,
        prtOutputMinDimXFeedDir           Integer32,
        prtOutputStackingOrder        PrtOutputStackingOrderTC,
        prtOutputPageDeliveryOrientation
                            PrtOutputPageDeliveryOrientationTC,
        prtOutputBursting                 PresentOnOff,
        prtOutputDecollating              PresentOnOff,
        prtOutputPageCollated             PresentOnOff,
        prtOutputOffsetStacking           PresentOnOff
}

prtOutputIndex OBJECT-TYPE
    SYNTAX     Integer32 (1..65535)
    MAX-ACCESS not-accessible
    STATUS     current
    DESCRIPTION
        "A unique value used by this printer to identify this
        output sub-unit. Although these values may change due
        to a major reconfiguration of the sub-unit (e.g.  the
        addition of new output devices to the printer), values
        are expected to remain stable across successive printer
        power cycles."
    ::= { prtOutputEntry 1 }

prtOutputType OBJECT-TYPE
    -- This value is a type 2 enumeration
    SYNTAX     PrtOutputTypeTC
    MAX-ACCESS read-only
    STATUS     current
    DESCRIPTION
         "The type of technology supported by this output sub-
         unit."
    ::= { prtOutputEntry 2 }

prtOutputCapacityUnit OBJECT-TYPE
    SYNTAX     PrtCapacityUnitTC
    MAX-ACCESS read-only
    STATUS     current
    DESCRIPTION
         "The unit of measurement for use in calculating and
         relaying capacity values for this output sub-unit."
    ::= { prtOutputEntry 3 }

prtOutputMaxCapacity OBJECT-TYPE
    SYNTAX     Integer32
    MAX-ACCESS read-write
    STATUS     current
    DESCRIPTION
         "The maximum capacity of this output sub-unit in output
         sub-unit capacity units (PrtCapacityUnitTC). There is no
         convention associated with the media itself so this
         value essentially reflects claimed capacity. If this
         output sub-unit can reliably sense this value, the value
         is sensed by the printer and may not be changed by
         management requests; otherwise, the value may be written
         (by a Remote Control Panel or a Management Application).
         The value (-1) means other and specifically indicates
         that the sub-unit places no restrictions on this
         parameter. The value (-2) means unknown."
    ::= { prtOutputEntry 4 }

prtOutputRemainingCapacity OBJECT-TYPE
    SYNTAX     Integer32
    MAX-ACCESS read-write
    STATUS     current
    DESCRIPTION
         "The remaining capacity of the possible output sub-unit
         capacity in output sub-unit capacity units
         (PrtCapacityUnitTC)of this output sub-unit. If this
         output sub-unit can reliably sense this value, the value
         is sensed by the printer and may not be modified by
         management requests; otherwise, the value may be written
         (by a Remote Control Panel or a Management Application).
         The value (-1) means other and specifically indicates
         that the sub-unit places no restrictions on this
         parameter.  The value (-2) means unknown.  The value (-
         3) means that the printer knows that there remains
         capacity for at least one unit."
    ::= { prtOutputEntry 5 }

prtOutputStatus OBJECT-TYPE
    SYNTAX     PrtSubUnitStatusTC
    MAX-ACCESS read-only
    STATUS     current
    DESCRIPTION
        "The current status of this output sub-unit."
    ::= { prtOutputEntry 6 }

--            OUTPUT MEASUREMENT
--
--   _______  |                | ________
--      ^     |                |     ^
--      |     |                |     |
--      |     |                |RemainingCapacity
-- MaxCapacity|                |     |
--      |     |                |     v           ^
--      |     |_ _ _ _ _ _ _ _ | _______________ |direction
--      |     |    Sheets      |                 |
--      |     |      in        |
--      v     |    Output      |
--   _______  +________________+


-- The Extended Output Group
--
-- This group is optional.  However, to claim conformance to this
-- group, it is necessary to implement every object in the group.

prtOutputName OBJECT-TYPE
    SYNTAX     OCTET STRING (SIZE(0..63))
    MAX-ACCESS read-write
    STATUS     current
    DESCRIPTION
        "The name assigned to this output sub-unit."
    ::= { prtOutputEntry 7 }

prtOutputVendorName OBJECT-TYPE
    SYNTAX     OCTET STRING (SIZE(0..63))
    MAX-ACCESS read-only
    STATUS     current
    DESCRIPTION
        "The vendor name of this output sub-unit."
    ::= { prtOutputEntry 8 }

prtOutputModel OBJECT-TYPE
    SYNTAX     OCTET STRING (SIZE(0..63))
    MAX-ACCESS read-only
    STATUS     current
    DESCRIPTION
        "The model name assigned to this output sub-unit."
    ::= { prtOutputEntry 9 }

prtOutputVersion OBJECT-TYPE
    SYNTAX     OCTET STRING (SIZE(0..63))
    MAX-ACCESS read-only
    STATUS     current
    DESCRIPTION
        "The version of this output sub-unit."
    ::= { prtOutputEntry 10 }

prtOutputSerialNumber OBJECT-TYPE
    SYNTAX     OCTET STRING (SIZE(0..63))
    MAX-ACCESS read-only
    STATUS     current
    DESCRIPTION
        "The serial number assigned to this output sub-unit."
    ::= { prtOutputEntry 11 }

prtOutputDescription OBJECT-TYPE
    SYNTAX     OCTET STRING (SIZE(0..255))
    MAX-ACCESS read-only
    STATUS     current
    DESCRIPTION
         "A free-form text description of this output sub-unit in
         the localization specified by
         prtGeneralCurrentLocalization."
    ::= { prtOutputEntry 12 }

prtOutputSecurity OBJECT-TYPE
    SYNTAX     PresentOnOff
    MAX-ACCESS read-write
    STATUS     current
    DESCRIPTION
         "Indicates if this output sub-unit has some security
         associated with it and if that security is enabled or
         not."
    ::= { prtOutputEntry 13 }

-- The Output Dimensions Group
--
-- This group is optional.  However, to claim conformance to this
-- group, it is necessary to implement every object in the group.

prtOutputDimUnit OBJECT-TYPE
    SYNTAX     PrtMediaUnitTC
    MAX-ACCESS read-only
    STATUS     current
    DESCRIPTION
         "The unit of measurement for use in calculating and
         relaying dimensional values for this output sub-unit."
    ::= { prtOutputEntry 14 }

prtOutputMaxDimFeedDir OBJECT-TYPE
    SYNTAX     Integer32
    MAX-ACCESS read-write
    STATUS     current
    DESCRIPTION
        "The maximum dimensions supported by this output sub-unit
        for measurements taken parallel relative to the feed
        direction associated with that sub-unit in output
        sub-unit dimensional units (MediaUnit). If this output
        sub-unit can reliably sense this value, the value is
        sensed by the printer and may not be changed with
        management protocol operations."
    ::= { prtOutputEntry 15 }

prtOutputMaxDimXFeedDir OBJECT-TYPE
    SYNTAX     Integer32
    MAX-ACCESS read-write
    STATUS     current
    DESCRIPTION
        "The maximum dimensions supported by this output sub-unit
        for measurements taken ninety degrees relative to the
        feed direction associated with that sub-unit in output
        sub-unit dimensional units (MediaUnit). If this output
        sub-unit can reliably sense this value, the value is
        sensed by the printer and may not be changed with
        management protocol operations."
    ::= { prtOutputEntry 16 }

prtOutputMinDimFeedDir OBJECT-TYPE
    SYNTAX     Integer32
    MAX-ACCESS read-write
    STATUS     current
    DESCRIPTION
        "The minimum dimensions supported by this output sub-unit
        for measurements taken parallel relative to the feed
        direction associated with that sub-unit in output
        sub-unit dimensional units (DimUnit).  If this output
        sub-unit can reliably sense this value, the value is
        sensed by the printer and may not be changed with
        management protocol operations."
    ::= { prtOutputEntry 17 }

prtOutputMinDimXFeedDir OBJECT-TYPE
    SYNTAX     Integer32
    MAX-ACCESS read-write
    STATUS     current
    DESCRIPTION
        "The minimum dimensions supported by this output sub-unit
        for measurements taken ninety degrees relative to the
        feed direction associated with that sub-unit in output
        sub-unit dimensional units (DimUnit). If this output
        sub-unit can reliably sense this value, the value is
        sensed by the printer and may not be changed with
        management protocol operations."
    ::= { prtOutputEntry 18 }

-- The Output Features Group
--
-- This group is optional.  However, to claim conformance to this
-- group, it is necessary to implement every object in the group.

prtOutputStackingOrder OBJECT-TYPE
    --  This value is a type 1 enumeration
    SYNTAX     PrtOutputStackingOrderTC
    MAX-ACCESS read-write
    STATUS     current
    DESCRIPTION
        "The current state of the stacking order for the
        associated output sub-unit. 'FirstToLast' means
        that as pages are output the front of the next page is
        placed against the back of the previous page.
        'LasttoFirst' means that as pages are output the back
        of the next page is placed against the front of the
        previous page."
    ::= { prtOutputEntry 19 }

prtOutputPageDeliveryOrientation OBJECT-TYPE
    --   This value is a type 1 enumeration
    SYNTAX     PrtOutputPageDeliveryOrientationTC
    MAX-ACCESS read-write
    STATUS     current
    DESCRIPTION
        "The reading surface that will be 'up' when pages are
        delivered to the associated output sub-unit. Values are
        faceUp and faceDown. (Note: interpretation of these
        values is in general context-dependent based on locale;
        presentation of these values to an end-user should be
        normalized to the expectations of the user)."
    ::= { prtOutputEntry 20 }

prtOutputBursting OBJECT-TYPE
    SYNTAX     PresentOnOff
    MAX-ACCESS read-write
    STATUS     current
    DESCRIPTION
         "This object indicates that the outputting sub-unit
         supports bursting, and if so, whether the feature is
         enabled. Bursting is the process by which continuous
         media is separated into individual sheets, typically by
         bursting along pre-formed perforations."
    ::= { prtOutputEntry 21 }

prtOutputDecollating OBJECT-TYPE
    SYNTAX     PresentOnOff
    MAX-ACCESS read-write
    STATUS     current
    DESCRIPTION
         "This object indicates that the output supports
         decollating, and if so, whether the feature is enabled.
         Decollating is the process by which the individual parts
         within a multi-part form are separated and sorted into
         separate stacks for each part."
    ::= { prtOutputEntry 22 }

prtOutputPageCollated OBJECT-TYPE
    SYNTAX     PresentOnOff
    MAX-ACCESS read-write
    STATUS     current
    DESCRIPTION
         "This object indicates that the output sub-unit supports
         page collation, and if so, whether the feature is
         enabled. See glossary for definition of how this
         document defines collation."
    ::= { prtOutputEntry 23 }

prtOutputOffsetStacking OBJECT-TYPE
    SYNTAX     PresentOnOff
    MAX-ACCESS read-write
    STATUS     current
    DESCRIPTION
         "This object indicates that the output supports offset
         stacking, and if so, whether the feature is enabled. See
         glossary for how Offset Stacking is defined by this
         document."
    ::= { prtOutputEntry 24 }

-- The Marker Group
--
-- A marker is the mechanism that produces marks on the print
-- media. The marker sub-units and their associated supplies are
-- represented by the Marker Group in the model.  A printer can
-- contain one or more marking mechanisms.  Some examples of
-- multiple marker sub-units are: a printer
-- with separate markers for normal and magnetic ink or an
-- imagesetter that can output to both a proofing device and
-- final film. Each marking device can have its own set of
-- characteristics associated with it, such as marking technology
-- and resolution.
--
-- Implementation of every object in this group is mandatory.


prtMarker OBJECT IDENTIFIER ::= { printmib 10 }


-- The printable area margins as listed below define an area of
-- the print media which is guaranteed to be printable for all
-- combinations of input, media paths, and interpreters for this
-- marker.

prtMarkerTable OBJECT-TYPE
    SYNTAX     SEQUENCE OF PrtMarkerEntry
    MAX-ACCESS not-accessible
    STATUS     current
    DESCRIPTION
        ""
    ::= { prtMarker 2 }

prtMarkerEntry OBJECT-TYPE
    SYNTAX     PrtMarkerEntry
    MAX-ACCESS not-accessible
    STATUS     current
    DESCRIPTION
         "Entries may exist in the table for each device index
         with a device type of 'printer'."
    INDEX  { hrDeviceIndex, prtMarkerIndex }
    ::= { prtMarkerTable 1 }

PrtMarkerEntry ::= SEQUENCE {
        prtMarkerIndex                  Integer32,
        prtMarkerMarkTech               PrtMarkerMarkTechTC,
        prtMarkerCounterUnit            PrtMarkerCounterUnitTC,
        prtMarkerLifeCount              Counter32,
        prtMarkerPowerOnCount           Counter32,
        prtMarkerProcessColorants       Integer32,
        prtMarkerSpotColorants          Integer32,
        prtMarkerAddressabilityUnit     INTEGER,
        prtMarkerAddressabilityFeedDir  Integer32,
        prtMarkerAddressabilityXFeedDir Integer32,
        prtMarkerNorthMargin            Integer32,
        prtMarkerSouthMargin            Integer32,
        prtMarkerWestMargin             Integer32,
        prtMarkerEastMargin             Integer32,
        prtMarkerStatus                 PrtSubUnitStatusTC
}


prtMarkerIndex OBJECT-TYPE
    SYNTAX     Integer32 (1..65535)
    MAX-ACCESS not-accessible
    STATUS     current
    DESCRIPTION
         "A unique value used by the printer to identify this
         marking SubUnit.  Although these values may change due
         to a major reconfiguration of the device (e.g. the
         addition of new marking sub-units to the printer),
         values are expected to remain stable across successive
         printer power cycles."
    ::= { prtMarkerEntry 1 }

prtMarkerMarkTech OBJECT-TYPE
    -- This value is a type 2 enumeration
    SYNTAX     PrtMarkerMarkTechTC
    MAX-ACCESS read-only
    STATUS     current
    DESCRIPTION
         "The type of marking technology used for this marking
         sub-unit."
    ::= { prtMarkerEntry 2 }

prtMarkerCounterUnit OBJECT-TYPE
    -- This value is a type 1 enumeration
    SYNTAX     PrtMarkerCounterUnitTC
    MAX-ACCESS read-only
    STATUS     current
    DESCRIPTION
         "The unit that will be used by the printer when
         reporting counter values for this marking sub-unit.  The
         time units of measure are provided for a device like a
         strip recorder that does not or cannot track the
         physical dimensions of the media and does not use
         characters, lines or sheets."
    ::= { prtMarkerEntry 3}

prtMarkerLifeCount OBJECT-TYPE
    SYNTAX     Counter32
    MAX-ACCESS read-only
    STATUS     current
    DESCRIPTION
         "The count of the number of units of measure counted
         during the life of printer using units of measure as
         specified by prtMarkerCounterUnit."
    ::= { prtMarkerEntry 4 }

prtMarkerPowerOnCount OBJECT-TYPE
    SYNTAX     Counter32
    MAX-ACCESS read-only
    STATUS     current
    DESCRIPTION
         "The count of the number of units of measure counted
         since the equipment was most recently powered on using
         units of measure as specified by prtMarkerCounterUnit."
    ::= { prtMarkerEntry 5 }

prtMarkerProcessColorants OBJECT-TYPE
    SYNTAX     Integer32 (0..65535)
    MAX-ACCESS read-only
    STATUS     current
    DESCRIPTION
         "The number of process colors supported by this marker.
         A process color of 1 implies monochrome.  The value of
         this object and prtMarkerSpotColorants cannot both be 0.
         The value of prtMarkerProcessColorants must be 0 or
         greater."
    ::= { prtMarkerEntry 6 }

prtMarkerSpotColorants OBJECT-TYPE
    SYNTAX     Integer32 (0..65535)
    MAX-ACCESS read-only
    STATUS     current
    DESCRIPTION
         "The number of spot colors supported by this marker. The
         value of this object and prtMarkerProcessColorants
         cannot both be 0.  Must be 0 or greater."
    ::= { prtMarkerEntry 7 }

prtMarkerAddressabilityUnit OBJECT-TYPE
    --   This value is a type 1 enumeration
    SYNTAX     INTEGER {
                   tenThousandthsOfInches(3),  -- .0001
                   micrometers(4)
               }
    MAX-ACCESS read-only
    STATUS     current
    DESCRIPTION
         "The unit of measure of distances, as applied to the
         marker's resolution."
    ::= { prtMarkerEntry 8 }

prtMarkerAddressabilityFeedDir OBJECT-TYPE
    SYNTAX     Integer32
    MAX-ACCESS read-only
    STATUS     current
    DESCRIPTION
         "The maximum number of addressable marking positions in
         the feed direction per 10000 units of measure specified
         by prtMarkerAddressabilityUnit.  A value of (-1) implies
         'other' or 'infinite' while a value of (-2) implies
         'unknown'."
    ::= { prtMarkerEntry 9 }

prtMarkerAddressabilityXFeedDir OBJECT-TYPE
    SYNTAX     Integer32
    MAX-ACCESS read-only
    STATUS     current
    DESCRIPTION
         "The maximum number of addressable marking positions in
         the cross feed direction in 10000 units of measure
         specified by prtMarkerAddressabilityUnit.  A value of (-
         1) implies 'other' or 'infinite' while a value of (-2)
         implies 'unknown'."
    ::= { prtMarkerEntry 10 }

prtMarkerNorthMargin OBJECT-TYPE
    SYNTAX     Integer32
    MAX-ACCESS read-only
    STATUS     current
    DESCRIPTION
         "The margin, in units identified by
         prtMarkerAddressabilityUnit, from the leading edge of
         the medium as the medium flows through the marking
         engine with the side to be imaged facing the observer.
         The leading edge is the North edge and the other edges
         are defined by the normal compass layout of  directions
         with the compass facing the observer.  Printing within
         the area bounded by all four margins is guaranteed for
         all interpreters.   The value (-2) means unknown."
    ::= { prtMarkerEntry 11 }

prtMarkerSouthMargin OBJECT-TYPE
    SYNTAX     Integer32
    MAX-ACCESS read-only
    STATUS     current
    DESCRIPTION
         "The margin from the South edge  (see
         prtMarkerNorthMargin) of the medium in units identified
         by prtMarkerAddressabilityUnit.  Printing within the
         area bounded by all four margins  is guaranteed for all
         interpreters. The value (-2) means unknown."
    ::= { prtMarkerEntry 12 }

prtMarkerWestMargin OBJECT-TYPE
    SYNTAX     Integer32
    MAX-ACCESS read-only
    STATUS     current
    DESCRIPTION
         "The margin from the West edge (see
         prtMarkerNorthMargin) of the medium in units identified
         by prtMarkerAddressabilityUnit. Printing within the area
         bounded by all four margins is guaranteed for all
         interpreters. The value (-2) means unknown."
    ::= { prtMarkerEntry 13 }

prtMarkerEastMargin OBJECT-TYPE
    SYNTAX     Integer32
    MAX-ACCESS read-only
    STATUS     current
    DESCRIPTION
         "The margin from the East edge (see
         prtMarkerNorthMargin) of the medium in units identified
         by prtMarkerAddressabilityUnit. Printing within the area
         bounded by all four margins is guaranteed for all
         interpreters. The value (-2) means unknown."
    ::= { prtMarkerEntry 14 }

prtMarkerStatus OBJECT-TYPE
    SYNTAX     PrtSubUnitStatusTC
    MAX-ACCESS read-only
    STATUS     current
    DESCRIPTION
        "The current status of this marker sub-unit."
    ::= { prtMarkerEntry 15 }

-- The Marker Supplies Group
--
-- This group is optional.  However, to claim conformance to this
-- group, it is necessary to implement every object in the group.

prtMarkerSupplies OBJECT IDENTIFIER ::= { printmib 11 }

prtMarkerSuppliesTable OBJECT-TYPE
    SYNTAX     SEQUENCE OF PrtMarkerSuppliesEntry
    MAX-ACCESS not-accessible
    STATUS     current
    DESCRIPTION
         "A table of the marker supplies available on this
         printer."
    ::= { prtMarkerSupplies 1 }

prtMarkerSuppliesEntry OBJECT-TYPE
    SYNTAX     PrtMarkerSuppliesEntry
    MAX-ACCESS not-accessible
    STATUS     current
    DESCRIPTION
         "Attributes of a marker supply. Entries may exist in the
         table for each device index with a device type of
         'printer'."
    INDEX  { hrDeviceIndex, prtMarkerSuppliesIndex }
    ::= { prtMarkerSuppliesTable 1 }

PrtMarkerSuppliesEntry ::= SEQUENCE {
    prtMarkerSuppliesIndex          Integer32,
    prtMarkerSuppliesMarkerIndex    Integer32,
    prtMarkerSuppliesColorantIndex  Integer32,
    prtMarkerSuppliesClass          PrtMarkerSuppliesClassTC,
    prtMarkerSuppliesType           PrtMarkerSuppliesTypeTC,
    prtMarkerSuppliesDescription    OCTET STRING,
    prtMarkerSuppliesSupplyUnit    PrtMarkerSuppliesSupplyUnitTC,
    prtMarkerSuppliesMaxCapacity    Integer32,
    prtMarkerSuppliesLevel          Integer32
}


prtMarkerSuppliesIndex OBJECT-TYPE
    SYNTAX     Integer32 (1..65535)
    MAX-ACCESS not-accessible
    STATUS     current
    DESCRIPTION
         "A unique value used by the printer to identify this
         marker supply.  Although these values may change due to
         a major reconfiguration of the device (e.g. the addition
         of new marker supplies to the printer), values are
         expected to remain stable across successive power
         cycles."
::= { prtMarkerSuppliesEntry 1 }

prtMarkerSuppliesMarkerIndex OBJECT-TYPE
    SYNTAX     Integer32 (0..65535)
    MAX-ACCESS read-only
    STATUS     current
    DESCRIPTION
         "The value of prtMarkerIndex corresponding to the
         marking sub-unit with which this marker supply sub-unit
         is associated."
    ::= { prtMarkerSuppliesEntry 2 }

prtMarkerSuppliesColorantIndex OBJECT-TYPE
    SYNTAX     Integer32 (0..65535)
    MAX-ACCESS read-only
    STATUS     current
    DESCRIPTION
         "The value of prtMarkerColorantIndex corresponding to
         the colorant with which this marker supply sub-unit is
         associated.  This value shall be 0 if there is no
         colorant table or if this supply does not depend on a
         single specified colorant."
    ::= { prtMarkerSuppliesEntry 3 }

prtMarkerSuppliesClass OBJECT-TYPE
    --  This value is a type 1 enumeration
    SYNTAX     PrtMarkerSuppliesClassTC
    MAX-ACCESS read-only
    STATUS     current
    DESCRIPTION
         "Indicates whether this supply entity represents a
         supply that is consumed or a receptacle that is filled."
    ::= { prtMarkerSuppliesEntry 4 }

prtMarkerSuppliesType OBJECT-TYPE
    --   This value is a type 3 enumeration
    SYNTAX     PrtMarkerSuppliesTypeTC
    MAX-ACCESS read-only
    STATUS     current
    DESCRIPTION
        "The type of this supply."
    ::= { prtMarkerSuppliesEntry 5 }

prtMarkerSuppliesDescription OBJECT-TYPE
    SYNTAX     OCTET STRING (SIZE(0..255))
    MAX-ACCESS read-only
    STATUS     current
    DESCRIPTION
         "The description of this supply container/receptacle in
         the localization specified by
         prtGeneralCurrentLocalization."
    ::= { prtMarkerSuppliesEntry 6 }

prtMarkerSuppliesSupplyUnit OBJECT-TYPE
    -- This value is a type 1 enumeration
    SYNTAX     PrtMarkerSuppliesSupplyUnitTC
    MAX-ACCESS read-only
    STATUS     current
    DESCRIPTION
         "Unit of measure of this marker supply
         container/receptacle."
    ::= { prtMarkerSuppliesEntry 7 }

prtMarkerSuppliesMaxCapacity OBJECT-TYPE
    SYNTAX     Integer32
    MAX-ACCESS read-write
    STATUS     current
    DESCRIPTION
         "The maximum capacity of this supply
         container/receptacle expressed in
         prtMarkerSuppliesSupplyUnit. If this supply
         container/receptacle can reliably sense this value, the
         value is reported by the printer and is read-only;
         otherwise, the value may be written (by a Remote Control
         Panel or a Management Application). The value (-1) means
         other and specifically indicates that the sub-unit
         places no restrictions on this parameter. The value (-2)
         means unknown."
    ::= { prtMarkerSuppliesEntry 8 }

prtMarkerSuppliesLevel OBJECT-TYPE
    SYNTAX     Integer32
    MAX-ACCESS read-write
    STATUS     current
    DESCRIPTION
         "The current level if this supply is a container;
         remaining space if this supply is a receptacle. If this
         supply container/receptacle can reliably sense this
         value, the value is reported by the printer and is read-
         only; otherwise, the value may be written (by a Remote
         Control Panel or a Management Application). The value (-
         1) means other and specifically indicates that the sub-
         unit places no restrictions on this parameter. The value
         (-2) means unknown.  A value of (-3) means that the
         printer knows that there is some supply/remaining space,
         respectively."
    ::= { prtMarkerSuppliesEntry 9 }

-- The Marker Colorant Group
--
-- This group is optional.  However, to claim conformance to this
-- group, it is necessary to implement every object in the group.
prtMarkerColorant OBJECT IDENTIFIER ::= { printmib 12 }

prtMarkerColorantTable OBJECT-TYPE
    SYNTAX     SEQUENCE OF PrtMarkerColorantEntry
    MAX-ACCESS not-accessible
    STATUS     current
    DESCRIPTION
         "A table of all of the colorants available on the
         printer."
    ::= { prtMarkerColorant 1 }

prtMarkerColorantEntry OBJECT-TYPE
    SYNTAX     PrtMarkerColorantEntry
    MAX-ACCESS not-accessible
    STATUS     current
    DESCRIPTION
         "Attributes of a colorant available on the printer.
         Entries may exist in the table for each device index
         with a device type of 'printer'."
    INDEX { hrDeviceIndex, prtMarkerColorantIndex }
    ::= { prtMarkerColorantTable 1 }

PrtMarkerColorantEntry ::= SEQUENCE {
        prtMarkerColorantIndex          Integer32,
        prtMarkerColorantMarkerIndex    Integer32,
        prtMarkerColorantRole           PrtMarkerColorantRoleTC,
        prtMarkerColorantValue          OCTET STRING,
        prtMarkerColorantTonality       Integer32
}

prtMarkerColorantIndex OBJECT-TYPE
    SYNTAX     Integer32 (1..65535)
    MAX-ACCESS not-accessible
    STATUS     current
    DESCRIPTION
        "A unique value used by the printer to identify this
        colorant. Although these values may change due to a major
        reconfiguration of the device (e.g. the addition of new
        colorants to the printer)."
    ::= { prtMarkerColorantEntry 1 }

prtMarkerColorantMarkerIndex OBJECT-TYPE
    SYNTAX     Integer32 (0..65535)
    MAX-ACCESS read-only
    STATUS     current
    DESCRIPTION
         "The value of prtMarkerIndex corresponding to the marker
         sub-unit with which this colorant entry is associated."
    ::= { prtMarkerColorantEntry 2 }

prtMarkerColorantRole OBJECT-TYPE
    -- This value is a type 1 enumeration
    SYNTAX     PrtMarkerColorantRoleTC
    MAX-ACCESS read-only
    STATUS     current
    DESCRIPTION
        "The role played by this colorant."
    ::= { prtMarkerColorantEntry 3 }

prtMarkerColorantValue OBJECT-TYPE
    SYNTAX     OCTET STRING (SIZE(0..255))
    MAX-ACCESS read-only
    STATUS     current
    DESCRIPTION
         "The name of the color of this colorant using
         standardized string names from ISO 10175 (DPA) and ISO
         10180 (SPDL) which are:
           other
           unknown
           white
           red
           green
           blue
           cyan
           magenta
           yellow
           black
         Implementers may add additional string values. The
         naming conventions in ISO 9070 are recommended in order
         to avoid potential name clashes"
    ::= { prtMarkerColorantEntry 4 }

prtMarkerColorantTonality OBJECT-TYPE
    SYNTAX     Integer32
    MAX-ACCESS read-only
    STATUS     current
    DESCRIPTION
         "The distinct levels of tonality realizable by a marking
         sub-unit when using this colorant.  This value does not
         include the number of levels of tonal difference that an
         interpreter can obtain by techniques such as half
         toning. This value must be at least 2."
    ::= { prtMarkerColorantEntry 5 }

-- The Media Path Group
--
-- The media paths encompass the mechanisms in the printer that
-- move the media through the printer and connect all other media
-- related sub-units: inputs, outputs, markers and finishers. A
-- printer contains one or more media paths. These are
-- represented by the Media Path Group in the model. The Media
-- Path group has some attributes that apply to all
-- paths plus a table of the separate media paths.

prtMediaPath OBJECT IDENTIFIER ::= { printmib 13 }


prtMediaPathTable OBJECT-TYPE
    SYNTAX     SEQUENCE OF PrtMediaPathEntry
    MAX-ACCESS not-accessible
    STATUS     current
    DESCRIPTION
        ""
    ::= { prtMediaPath 4 }

prtMediaPathEntry OBJECT-TYPE
    SYNTAX     PrtMediaPathEntry
    MAX-ACCESS not-accessible
    STATUS     current
    DESCRIPTION
         "Entries may exist in the table for each device index
         with a device type of 'printer'."
    INDEX  { hrDeviceIndex, prtMediaPathIndex }
    ::= { prtMediaPathTable 1 }

PrtMediaPathEntry ::= SEQUENCE {
    prtMediaPathIndex               Integer32,
    prtMediaPathMaxSpeedPrintUnit
                          PrtMediaPathMaxSpeedPrintUnitTC,
    prtMediaPathMediaSizeUnit       PrtMediaUnitTC,
    prtMediaPathMaxSpeed            Integer32,
    prtMediaPathMaxMediaFeedDir     Integer32,
    prtMediaPathMaxMediaXFeedDir    Integer32,
    prtMediaPathMinMediaFeedDir     Integer32,
    prtMediaPathMinMediaXFeedDir    Integer32,
    prtMediaPathType                PrtMediaPathTypeTC,
    prtMediaPathDescription         OCTET STRING,
    prtMediaPathStatus              PrtSubUnitStatusTC
}


prtMediaPathIndex OBJECT-TYPE
    SYNTAX     Integer32 (1..65535)
    MAX-ACCESS not-accessible
    STATUS     current
    DESCRIPTION
         "A unique value used by the printer to identify this
         media path. Although these values may change due to a
         major reconfiguration of the device (e.g. the addition
         of new media paths to the printer), values are expected
         to remain stable across successive printer power
         cycles."
    ::= { prtMediaPathEntry 1 }

prtMediaPathMaxSpeedPrintUnit OBJECT-TYPE
    -- This value is a type 1 enumeration
    SYNTAX PrtMediaPathMaxSpeedPrintUnitTC
    MAX-ACCESS read-only
    STATUS     current
    DESCRIPTION
         "The unit of measure used in specifying the speed of all
         media paths in the printer."
    ::= { prtMediaPathEntry 2 }

prtMediaPathMediaSizeUnit OBJECT-TYPE
    SYNTAX     PrtMediaUnitTC
    MAX-ACCESS read-only
    STATUS     current
    DESCRIPTION
         "The units of measure of media size for use in
         calculating and relaying dimensional values for all
         media paths in the printer."
    ::= { prtMediaPathEntry 3 }

prtMediaPathMaxSpeed OBJECT-TYPE
    SYNTAX     Integer32
    MAX-ACCESS read-only
    STATUS     current
    DESCRIPTION
         "The maximum printing speed of this media path expressed
         in prtMediaPathMaxSpeedUnit's.  A value of (-1) implies
         'other'."
    ::= { prtMediaPathEntry 4 }

prtMediaPathMaxMediaFeedDir OBJECT-TYPE
    SYNTAX     Integer32
    MAX-ACCESS read-only
    STATUS     current
    DESCRIPTION
         "The maximum physical media size in the feed direction
         of this media path expressed in units of measure
         specified by PrtMediaPathMediaSizeUnit.  A value of (-1)
         implies 'unlimited' a value of (-2) implies 'unknown'"
    ::= { prtMediaPathEntry 5 }

prtMediaPathMaxMediaXFeedDir OBJECT-TYPE
    SYNTAX     Integer32
    MAX-ACCESS read-only
    STATUS     current
    DESCRIPTION
         "The maximum physical media size across the feed
         direction of this media path expressed in units of
         measure specified by prtMediaPathMediaSizeUnit.  A value
         of (-2) implies 'unknown'."
    ::= { prtMediaPathEntry 6 }

prtMediaPathMinMediaFeedDir OBJECT-TYPE
    SYNTAX     Integer32
    MAX-ACCESS read-only
    STATUS     current
    DESCRIPTION
         "The minimum physical media size in the feed direction
         of this media path expressed in units of measure
         specified by prtMediaPathMediaSizeUnit. A value of (-2)
         implies 'unknown'."
    ::= { prtMediaPathEntry 7 }

prtMediaPathMinMediaXFeedDir OBJECT-TYPE
    SYNTAX     Integer32
    MAX-ACCESS read-only
    STATUS     current
    DESCRIPTION
         "The minimum physical media size across the feed
         direction of this media path expressed in units of
         measure specified by prtMediaPathMediaSizeUnit.  A value
         of (-2) implies 'unknown'."
    ::= { prtMediaPathEntry 8 }

prtMediaPathType OBJECT-TYPE
    --   This value is a type 2 enumeration
    SYNTAX     PrtMediaPathTypeTC
    MAX-ACCESS read-only
    STATUS     current
    DESCRIPTION
        "The type of the media path for this media path."
    ::= { prtMediaPathEntry 9 }

prtMediaPathDescription OBJECT-TYPE
    SYNTAX     OCTET STRING (SIZE(0..255))
    MAX-ACCESS read-only
    STATUS     current
    DESCRIPTION
         "The manufacturer-provided description of this media
         path in the localization specified by
         prtGeneralCurrentLocalization."
    ::= { prtMediaPathEntry 10 }

prtMediaPathStatus OBJECT-TYPE
    SYNTAX     PrtSubUnitStatusTC
    MAX-ACCESS read-only
    STATUS     current
    DESCRIPTION
         "The current status of this media path."
    ::= { prtMediaPathEntry 11 }

-- The Print Job Delivery Channel Group
--
-- Implementation of every object in this group is mandatory.
--
-- Print Job Delivery Channels are independent sources of print
-- data. Here, print data is the term used for the information
-- that is used to construct printed pages and may have both data
-- and control aspects. The output of a channel is in a form
-- suitable for input to one of the interpreters as a
-- stream. A channel may be independently enabled (allowing
-- print data to flow) or disabled (stopping the flow of
-- print data). A printer may have one or more channels.
--
-- The Print Job Delivery Channel table describes the
-- capabilities of the printer and not what is currently being
-- performed by the printer
--
-- Basically, the print job delivery channel abstraction
-- describes the final processing step of getting the print data
-- to an interpreter. It might include some level of
-- decompression or decoding of print stream data.
-- channel. All of these aspects are hidden in the channel
-- abstraction.
--
-- There are many kinds of print job delivery channels; some of
-- which are based on networks and others which are not. For
-- example, a channel can be a serial (or parallel) connection;
-- it can be a service, such as the UNIX Line Printer Daemon
-- (LPD), offering services over a network connection; or
-- it could be a disk drive into which a floppy disk with
-- the print data is inserted. Each print job delivery channel is
-- identified by the electronic path and/or service protocol
-- used to deliver print data to a print data interpreter.
--
-- Channel example                   Implementation
--
-- serial port channel            bi-directional data channel
-- parallel port channel          often uni-directional channel
-- IEEE 1284 port channel         bi-directional channel
-- SCSI port channel              bi-directional
-- Apple PAP channel              may be based on LocalTalk,
--                                Ethernet or Tokentalk
-- LPD Server channel             TCP/IP based, port 515
-- Netware Remote Printer         SPX/IPX based channel
-- Netware Print Server           SPX/IPX based channel
--
-- It is easy to note that this is a mixed bag.  There are
-- some physical connections over which no (or very meager)
-- protocols are run (e.g. the serial or old parallel ports)
-- and there are services which often have elaborate
-- protocols that run over a number of protocol stacks. In
-- the end, what is important is the delivery of print data
-- through the channel.
--
-- The print job delivery channel sub-units are represented by
-- the Print Job Delivery Channel Group in the Model. It has a
-- current print job control language, which can be used to
-- specify which interpreter is to be used for the print data and
-- to query and change environment variables used by the
-- interpreters (and Management Applications). There is also a
-- default interpreter that is to be used if an interpreter is
-- not explicitly specified using the Control Language.

-- The first seven items in the Print Job Delivery Channel Table
-- define the "channel" itself.  A channel typically depends on
-- other protocols and interfaces to provide the data that flows
-- through the channel.
--
-- Control of a print job delivery channel is largely limited to
-- enabling or disabling the entire channel itself. It is likely
-- that more control of the process of accessing print data
-- will be needed over time. Thus, the ChannelType will
-- allow type-specific data to be associated with each
-- channel (using ChannelType specific groups in a fashion
-- analogous to the media specific MIBs that are associated
-- with the IANAIfType in the Interfaces Table). As a first
-- step in this direction, each channel will identify the
-- underlying Interface on which it is based. This is the
-- eighth object in each row of the table.


-- The Print Job Delivery Channel Table
--
-- The prtChannelTable represents the set of input data sources
-- which can provide print data to one or more of the
-- interpreters available on a printer


prtChannel OBJECT IDENTIFIER ::= { printmib 14 }

prtChannelTable OBJECT-TYPE
    SYNTAX     SEQUENCE OF PrtChannelEntry
    MAX-ACCESS not-accessible
    STATUS     current
    DESCRIPTION
        ""
    ::= { prtChannel 1 }

prtChannelEntry OBJECT-TYPE
    SYNTAX     PrtChannelEntry
    MAX-ACCESS not-accessible
    STATUS     current
    DESCRIPTION
         "Entries may exist in the table for each device index
         with a device type of 'printer'."
    INDEX  { hrDeviceIndex, prtChannelIndex }
    ::= { prtChannelTable 1 }

PrtChannelEntry ::= SEQUENCE {
    prtChannelIndex                     Integer32,
    prtChannelType                      PrtChannelTypeTC,
    prtChannelProtocolVersion           OCTET STRING,
    prtChannelCurrentJobCntlLangIndex   Integer32,
    prtChannelDefaultPageDescLangIndex  Integer32,
    prtChannelState                     PrtChannelStateTC,
    prtChannelIfIndex                   Integer32,
    prtChannelStatus                    PrtSubUnitStatusTC,
    prtChannelInformation               OCTET STRING
}

prtChannelIndex OBJECT-TYPE
    SYNTAX     Integer32 (1..65535)
    MAX-ACCESS not-accessible
    STATUS     current
    DESCRIPTION
         "A unique value used by the printer to identify this
         data channel.  Although these values may change due to a
         major reconfiguration of the device (e.g. the addition
         of new data channels to the printer), values are
         expected to remain stable across successive printer
         power cycles."
    ::= { prtChannelEntry 1 }

prtChannelType OBJECT-TYPE
    SYNTAX     PrtChannelTypeTC
    MAX-ACCESS read-only
    STATUS     current
    DESCRIPTION
         "The type of this print data channel.  This object
         provides the linkage to ChannelType-specific groups that
         may (conceptually) extend the prtChannelTable with
         additional details about that channel."
    ::= { prtChannelEntry 2 }

prtChannelProtocolVersion OBJECT-TYPE
    SYNTAX     OCTET STRING (SIZE(0..63))
    MAX-ACCESS read-only
    STATUS     current
    DESCRIPTION
         "The version of the protocol used on this channel.  The
         format used for version numbering depends on
         prtChannelType."
    ::= { prtChannelEntry 3 }

prtChannelCurrentJobCntlLangIndex OBJECT-TYPE
    SYNTAX     Integer32
    MAX-ACCESS read-write
    STATUS     current
    DESCRIPTION
         "The value of prtInterpreterIndex corresponding to the
         Control Language Interpreter for this channel. This
         interpreter defines the syntax used for control
         functions, such as querying or changing environment
         variables and identifying job boundaries (e.g. PJL,
         PostScript, NPAP). A value of zero indicates that there
         is no current Job Control Language Interpreter for this
         channel"
    ::= { prtChannelEntry 4 }

prtChannelDefaultPageDescLangIndex OBJECT-TYPE
    SYNTAX     Integer32
    MAX-ACCESS read-write
    STATUS     current
    DESCRIPTION
         "The value of prtInterpreterIndex corresponding to the
         Page Description Language Interpreter for this channel.
         This interpreter defines the default Page Description
         Language interpreter to be used for the print data
         unless the Control Language is used to select a specific
         interpreter (e.g., PCL, PostScript Language, auto-
         sense). A value of zero indicates that there is no
         default page description language interpreter for this
         channel."
    ::= { prtChannelEntry 5 }

prtChannelState OBJECT-TYPE
    -- This value is a type 1 enumeration
    SYNTAX     PrtChannelStateTC
    MAX-ACCESS read-write
    STATUS     current
    DESCRIPTION
         "The state of this print data channel. The value
         determines whether control information and print data is
         allowed through this channel or not."
    ::= { prtChannelEntry 6 }

prtChannelIfIndex OBJECT-TYPE
    SYNTAX     Integer32
    MAX-ACCESS read-write
    STATUS     current
    DESCRIPTION
         "The value of ifIndex (in the ifTable; see the interface
         section of MIB-2/RFC 1213) which corresponds to this
         channel. When more than one row of the ifTable is
         relevant, this is the index of the row representing the
         topmost layer in the interface hierarchy.  A value of
         zero indicates that no interface is associated with this
         channel."
    ::= { prtChannelEntry 7 }

prtChannelStatus OBJECT-TYPE
    SYNTAX     PrtSubUnitStatusTC
    MAX-ACCESS read-only
    STATUS     current
    DESCRIPTION
        "The current status of the channel."
    ::= { prtChannelEntry 8 }


prtChannelInformation OBJECT-TYPE
    SYNTAX     OCTET STRING (SIZE (0..255))
    MAX-ACCESS read-only
    STATUS     current
    DESCRIPTION
         "Auxiliary information to allow a printing application
         to use the channel for data submission to the printer.
         An application capable of using a specific
         PrtChannelType should be able to use the combined
         information from the prtChannelInformation and other
         channel and interface group objects to 'bootstrap' its
         use of the channel.  prtChannelInformation is not
         intended to provide a general channel description, nor
         to provide information that is available once the
         channel is in use.

         The encoding and interpretation of the
         prtChannelInformation object is specific to channel
         type.  The description of each PrtChannelType enum value
         for which prtChannelInformation is defined specifies the
         appropriate encoding and interpretation, including
         interaction with other objects.  For channel types that
         do not specify a prtChannelInformation value, its value
         shall be null (0 length).

         When a new PrtChannelType enumeration value is
         registered, its accompanying description must specify
         the encoding and interpretation of the
         prtChannelInformation value for the channel type.
         prtChannelInformation semantics for an existing
         PrtChannelType may be added or amended in the same
         manner as described in section 2.4.1 for type 2
         enumeration values.

         The prtChannelInformation specifies values for a
         collection of channel attributes, represented as text
         according to the following rules:

         1. The prtChannelInformation is not affected by
         localization.

         2. The prtChannelInformation is a list of entries
         representing the attribute values.  Each entry consists
         of the following items, in order:

         a. a keyword, composed of alphabetic characters (A-Z,
         a-z) represented by their NVT ASCII [NVT ASCII] codes,
         that identifies a channel attribute,
         b. the NVT ASCII code for an Equals Sign (=) (code 61)
         to delimit the keyword,

         c. a data value encoded using rules specific to the
         PrtChannelType to with the prtChannelInformation applies
         which must in no case allow an octet with value 10 (the
         NVT ASCII Line Feed code),

         d. the NVT ASCII code for a Line Feed character (code
         10) to delimit the data value.

         No other octets shall be present.

         Keywords are case-sensitive.  Conventionally, keywords
         are capitalized (including each word of a multi-word
         keyword) and since they occupy space in the
         prtChannelInformation, they are kept short.

         3. If a channel attribute has multiple values, it is
         represented by multiple entries with the same keyword,
         each specifying one value. Otherwise, there shall be at
         most one entry for each attribute.

         4. By default, entries may appear in any order.  If
         there are ordering constraints for particular entries,
         these must be specified in their definitions.

         5. The prtChannelInformation value by default consists
         of text represented by NVT ASCII graphics character
         codes. However, other representations may be specified:

         a. In cases where the prtChannelInformation value
         contains information not normally coded in textual form,
         whatever symbolic representation is conventionally used
         for the information should be used for encoding the
         prtChannelInformation value. (For instance, a binary
         port value might be represented as a decimal number
         using NVT ASCII codes.) Such encoding must be specified
         in the definition of the value.

         b. The value may contain textual information in a
         character set other than NVT ASCII graphics characters.
         (For instance, an identifier might consist of ISO 10646
         text encoded using the UTF-8 encoding scheme.) Such a
         character set and its encoding must be specified in the
         definition of the value.

         6. For each PrtChannelType for which
         prtChannelInformation entries are defined, the
         descriptive text associated with the PrtChannelType
         enumeration value shall specify the following
         information for each entry:

         Title:        Brief description phrase, e.g.: 'Port
                       name', 'Service Name', etc.

         Keyword:      The keyword value, e.g.: 'Port' or
                       'Service'

         Syntax:       The encoding of the entry value if it
                       cannot be directly represented by NVT
                       ASCII.

         Status:       'Mandatory', 'Optional', or 'Conditionally
                       Mandatory'

         Multiplicity: 'Single' or 'Multiple' to indicate whether
                       the entry may be present multiple times.

         Description:  Description of the use of the entry, other
                       information required to complete the
                       definition (e.g.: ordering constraints,
                       interactions between entries).

         Applications that interpret prtChannelInformation should
         ignore unrecognized entries, so they are not affected if
         new entry types are added."

     ::= { prtChannelEntry 9 }

--
-- The Interpreter Group
--
-- The interpreter sub-units are responsible for the conversion
-- of a description of intended print instances into images that
-- are to be marked on the media. A printer may have one or more
-- interpreters. The interpreter sub-units are represented by the
-- Interpreter Group in the Model. Each interpreter is generally
-- implemented with software running on the System Controller
-- sub-unit. The Interpreter Table has one entry per interpreter
-- where the interpreters include both Page Description Language
-- (PDL) Interpreters and Control Language Interpreters.
--
-- Implementation of every object in this group is mandatory.
prtInterpreter OBJECT IDENTIFIER ::= { printmib 15 }

--       Interpreter Table
--
-- The prtInterpreterTable is a table representing the
-- interpreters in the printer.  An entry shall be placed in the
-- interpreter table for each interpreter on the printer.

prtInterpreterTable OBJECT-TYPE
    SYNTAX     SEQUENCE OF PrtInterpreterEntry
    MAX-ACCESS not-accessible
    STATUS     current
    DESCRIPTION
        ""
    ::= { prtInterpreter 1 }

prtInterpreterEntry OBJECT-TYPE
    SYNTAX     PrtInterpreterEntry
    MAX-ACCESS not-accessible
    STATUS     current
    DESCRIPTION
         "Entries may exist in the table for each device index
         with a device type of 'printer'."
    INDEX  { hrDeviceIndex, prtInterpreterIndex }
    ::= { prtInterpreterTable 1 }

PrtInterpreterEntry ::= SEQUENCE {
    prtInterpreterIndex                 Integer32,
    prtInterpreterLangFamily         PrtInterpreterLangFamilyTC,
    prtInterpreterLangLevel             OCTET STRING,
    prtInterpreterLangVersion           OCTET STRING,
    prtInterpreterDescription           OCTET STRING,
    prtInterpreterVersion               OCTET STRING,
    prtInterpreterDefaultOrientation    PrtPrintOrientationTC,
    prtInterpreterFeedAddressability    Integer32,
    prtInterpreterXFeedAddressability   Integer32,
    prtInterpreterDefaultCharSetIn      CodedCharSet,
    prtInterpreterDefaultCharSetOut     CodedCharSet,
    prtInterpreterTwoWay                PrtInterpreterTwoWayTC
}

prtInterpreterIndex OBJECT-TYPE
    SYNTAX     Integer32 (1..65535)
    MAX-ACCESS not-accessible
    STATUS     current
    DESCRIPTION
         "A unique value for each PDL or control language for
         which there exists an interpreter or emulator in the
         printer. The value is used to identify this interpreter.
         Although these values may change due to a major
         reconfiguration of the device (e.g. the addition of new
         interpreters to the printer), values are expected to
         remain stable across successive printer power cycles."
    ::= { prtInterpreterEntry 1 }

prtInterpreterLangFamily OBJECT-TYPE
    -- This value is a type 2 enumeration
    SYNTAX     PrtInterpreterLangFamilyTC
    MAX-ACCESS read-only
    STATUS     current
    DESCRIPTION
         "The family name of a Page Description Language (PDL) or
         control language which this interpreter in the printer
         can interpret or emulate."
    ::= { prtInterpreterEntry 2 }

prtInterpreterLangLevel OBJECT-TYPE
    SYNTAX     OCTET STRING (SIZE(0..31))
    MAX-ACCESS read-only
    STATUS     current
    DESCRIPTION
         "The level of the language which this interpreter is
         interpreting or emulating.  This might contain a value
         like '5e' for an interpreter which is emulating level 5e
         of the PCL language. It might contain '2' for an
         interpreter which is emulating level 2 of the PostScript
         language. Similarly it might contain '2' for an
         interpreter which is emulating level 2 of the HPGL
         language."
    ::= { prtInterpreterEntry 3 }

prtInterpreterLangVersion OBJECT-TYPE
    SYNTAX     OCTET STRING (SIZE(0..31))
    MAX-ACCESS read-only
    STATUS     current
    DESCRIPTION
         "The date code or version of the language which this
         interpreter is interpreting or emulating."
    ::= { prtInterpreterEntry 4 }

prtInterpreterDescription OBJECT-TYPE
    SYNTAX     OCTET STRING (SIZE(0..255))
    MAX-ACCESS read-only
    STATUS     current
    DESCRIPTION
         "A string to identify this interpreter in the
         localization specified by prtGeneralCurrentLocalization
         as opposed to the language which is being interpreted.
         It is anticipated that this string will allow
         manufacturers to unambiguously identify their
         interpreters."
    ::= { prtInterpreterEntry 5 }

prtInterpreterVersion OBJECT-TYPE
    SYNTAX     OCTET STRING (SIZE(0..31))
    MAX-ACCESS read-only
    STATUS     current
    DESCRIPTION
         "The date code, version number, or other product
         specific information tied to this interpreter.  This
         value is associated with the interpreter, rather than
         with the version of the language which is being
         interpreted or emulated."
    ::= { prtInterpreterEntry 6 }

prtInterpreterDefaultOrientation OBJECT-TYPE
    -- This value is a type 1 enumeration
    SYNTAX     PrtPrintOrientationTC
    MAX-ACCESS read-write
    STATUS     current
    DESCRIPTION
         "The current orientation default for this interpreter.
         This value may be overridden for a particular job (e.g.,
         by a command in the input data stream)."
    ::= { prtInterpreterEntry 7 }

prtInterpreterFeedAddressability OBJECT-TYPE
    SYNTAX     Integer32
    MAX-ACCESS read-only
    STATUS     current
    DESCRIPTION
         "The maximum interpreter addressability in the feed
         direction in 10000 prtMarkerAddressabilityUnits (see
         prtMarkerAddressabilityFeedDir ) for this interpreter.
         The value (-1) means other and specifically indicates
         that the sub-unit places no restrictions on this
         parameter."
    ::= { prtInterpreterEntry 8 }

prtInterpreterXFeedAddressability OBJECT-TYPE
    SYNTAX     Integer32
    MAX-ACCESS read-only
    STATUS     current
    DESCRIPTION
         "The maximum interpreter addressability in the cross
         feed direction in 10000 prtMarkerAddressabilityUnits
         (see prtMarkerAddressabilityXFeedDir) for this
         interpreter. The value (-1) means other and specifically
         indicates that the sub-unit places no restrictions on
         this parameter."
    ::= { prtInterpreterEntry 9 }

prtInterpreterDefaultCharSetIn OBJECT-TYPE
    SYNTAX     CodedCharSet
    MAX-ACCESS read-write
    STATUS     current
    DESCRIPTION
         "The default coded character set for input octets
         encountered outside a context in which the Page
         Description Language established the interpretation of
         the octets. (Input octets are presented to the
         interpreter through a path defined in the channel
         group.) This value shall be (2) if there is no default."
     ::= { prtInterpreterEntry 10 }

prtInterpreterDefaultCharSetOut OBJECT-TYPE
    SYNTAX     CodedCharSet
    MAX-ACCESS read-write
    STATUS     current
    DESCRIPTION
         "The default character set for data coming from this
         interpreter through the printer's output channel (i.e.
         the 'backchannel'). This value shall be (2) if there is
         no default."
    ::= { prtInterpreterEntry 11 }

prtInterpreterTwoWay OBJECT-TYPE
    -- This value is a type 1 enumeration
    SYNTAX     PrtInterpreterTwoWayTC
    MAX-ACCESS read-only
    STATUS     current
    DESCRIPTION
         "Indicates whether or not this interpreter returns
         information back to the host."
    ::= { prtInterpreterEntry 12 }

-- The Console Group
--
-- Many printers have a console on the printer, the operator
-- console, that is used to display and modify the state of the
-- printer. The console can be as simple as a few indicators and
-- switches or as complicated as full screen displays and
-- keyboards. There can be at most one such console.

-- Implementation of every object in this group is mandatory.

-- The Display Buffer Table

prtConsoleDisplayBuffer OBJECT IDENTIFIER ::= { printmib 16 }

prtConsoleDisplayBufferTable OBJECT-TYPE
    SYNTAX     SEQUENCE OF PrtConsoleDisplayBufferEntry
    MAX-ACCESS not-accessible
    STATUS     current
    DESCRIPTION
         "Physical display buffer for printer console display or
         operator panel"
    ::= { prtConsoleDisplayBuffer 5 }

prtConsoleDisplayBufferEntry OBJECT-TYPE
    SYNTAX     PrtConsoleDisplayBufferEntry
    MAX-ACCESS not-accessible
    STATUS     current
    DESCRIPTION
         "This table contains one entry for each physical line on
         the display.  Lines cannot be added or deleted. Entries
         may exist in the table for each device index with a
         device type of 'printer'."
    INDEX  { hrDeviceIndex, prtConsoleDisplayBufferIndex }
    ::= { prtConsoleDisplayBufferTable 1 }

PrtConsoleDisplayBufferEntry ::= SEQUENCE {
    prtConsoleDisplayBufferIndex    Integer32,
    prtConsoleDisplayBufferText     OCTET STRING
}

prtConsoleDisplayBufferIndex OBJECT-TYPE
    SYNTAX     Integer32 (1..65535)
    MAX-ACCESS not-accessible
    STATUS     current
    DESCRIPTION
         "A unique value for each console line in the printer.
         The value is used to identify this console line.
         Although these values may change due to a major
         reconfiguration of the device (e.g. the addition of new
         console lines to the printer). Values are normally
         expected to remain stable across successive printer
         power cycles."
    ::= { prtConsoleDisplayBufferEntry 1 }

prtConsoleDisplayBufferText OBJECT-TYPE
    SYNTAX     OCTET STRING (SIZE(0..255))
    MAX-ACCESS read-write
    STATUS     current
    DESCRIPTION
         "The content of a line in the logical display buffer of
         the operator's console of the printer.  When a write
         operation occurs, normally a critical message, to one of
         the LineText strings, the agent should make that line
         displayable if a physical display is present.  Writing a
         zero length string clears the line.  It is an
         implementation-specific matter as to whether the agent
         allows a line to be overwritten before it has been
         cleared. Printer generated strings shall be in the
         localization specified by prtConsoleLocalization.
         Management Application generated strings should be
         localized by the Management Application."
    ::= { prtConsoleDisplayBufferEntry 2 }

-- The Console Light Table

prtConsoleLights OBJECT IDENTIFIER ::= { printmib 17 }

prtConsoleLightTable OBJECT-TYPE
    SYNTAX     SEQUENCE OF PrtConsoleLightEntry
    MAX-ACCESS not-accessible
    STATUS     current
    DESCRIPTION
        ""
    ::= { prtConsoleLights 6 }

prtConsoleLightEntry OBJECT-TYPE
    SYNTAX     PrtConsoleLightEntry
    MAX-ACCESS not-accessible
    STATUS     current
    DESCRIPTION
         "Entries may exist in the table for each device index
         with a device type of 'printer'."
    INDEX  { hrDeviceIndex, prtConsoleLightIndex }
    ::= { prtConsoleLightTable 1 }

PrtConsoleLightEntry ::= SEQUENCE {
    prtConsoleLightIndex            Integer32,
    prtConsoleOnTime                Integer32,
    prtConsoleOffTime               Integer32,
    prtConsoleColor                 PrtConsoleColorTC,
    prtConsoleDescription           OCTET STRING

}

prtConsoleLightIndex OBJECT-TYPE
    SYNTAX     Integer32 (1..65535)
    MAX-ACCESS not-accessible
    STATUS     current
    DESCRIPTION
         "A unique value used by the printer to identify this
         light. Although these values may change due to a major
         reconfiguration of the device (e.g. the addition of new
         lights to the printer). Values are normally expected to
         remain stable across successive printer power cycles."
    ::= { prtConsoleLightEntry 1 }

prtConsoleOnTime OBJECT-TYPE
    SYNTAX     Integer32
    MAX-ACCESS read-write
    STATUS     current
    DESCRIPTION
         "This object, in conjunction with prtConsoleOffTime,
         defines the current status of the light.  If both
         prtConsoleOnTime and prtConsoleOffTime are non-zero, the
         lamp is blinking and the values presented define the on
         time and off time, respectively, in milliseconds. If
         prtConsoleOnTime is zero and prtConsoleOffTime is non-
         zero, the lamp is off. If prtConsoleOffTime is zero and
         prtConsoleOnTime is non-zero, the lamp is on. If both
         values are zero the lamp is off."
    ::= { prtConsoleLightEntry 2 }

prtConsoleOffTime OBJECT-TYPE
    SYNTAX     Integer32
    MAX-ACCESS read-write
    STATUS     current
    DESCRIPTION
         "This object, in conjunction with prtConsoleOnTime,
         defines the current status of the light. If both
         prtConsoleOnTime and prtConsoleOffTime are non-zero, the
         lamp is blinking and the values presented define the on
         time and off time, respectively, in milliseconds. If
         prtConsoleOnTime is zero and prtConsoleOffTime is non-
         zero, the lamp is off. If prtConsoleOffTime is zero and
         prtConsoleOnTime is non-zero, the lamp is on. If both
         values are zero the lamp is off."
    ::= { prtConsoleLightEntry 3 }

prtConsoleColor OBJECT-TYPE
    -- This value is a type 2 enumeration
    SYNTAX     PrtConsoleColorTC
    MAX-ACCESS read-only
    STATUS     current
    DESCRIPTION
        "The color of this light."
    ::= { prtConsoleLightEntry 4 }

prtConsoleDescription OBJECT-TYPE
    SYNTAX     OCTET STRING (SIZE(0..255))
    MAX-ACCESS read-only
    STATUS     current
    DESCRIPTION
         "The vendor description or label of this light in the
         localization specified by prtConsoleLocalization."
    ::= { prtConsoleLightEntry 5 }


-- The Alerts Group
--
-- The prtAlertTable lists all the critical and non-critical
-- alerts currently active in the printer.  A critical alert is
-- one that stops the printer from printing immediately and
-- printing can not continue until the critical alert condition
-- is eliminated.  Non-critical alerts are those items that do
-- not stop printing but may at some future time.
-- The table contains information on the severity, component,
-- detail location within the component, alert code and
-- description of each critical alert that is currently active
-- within the printer.  See 2.2.13 for a more complete
-- description of the alerts table and its management.
--
-- Each parameter in the Trap PDU is a full OID which itself is
-- indexed by the host resources MIB "hrDeviceIndex" object. In
-- order for a management station to obtain the correct
-- "hrDeviceIndex" associated with a particular Trap PDU, the
-- "hrDeviceIndex" value can be extracted from the returned OID
-- value in the Trap PDU when the PDU is received by the
-- Management station.
--
-- Implementation of every object in this group is mandatory.

prtAlert OBJECT IDENTIFIER ::= { printmib 18 }

prtAlertTable OBJECT-TYPE
    SYNTAX     SEQUENCE OF PrtAlertEntry
    MAX-ACCESS not-accessible
    STATUS     current
    DESCRIPTION
        ""
    ::= { prtAlert 1 }

prtAlertEntry OBJECT-TYPE
    SYNTAX     PrtAlertEntry
    MAX-ACCESS not-accessible
    STATUS     current
    DESCRIPTION
        "Entries may exist in the table for each device
        index with a device type of 'printer'."
    INDEX  { hrDeviceIndex, prtAlertIndex }
    ::= { prtAlertTable 1 }

PrtAlertEntry ::= SEQUENCE {
    prtAlertIndex               Integer32,
    prtAlertSeverityLevel       PrtAlertSeverityLevelTC,
    prtAlertTrainingLevel       PrtAlertTrainingLevelTC,
    prtAlertGroup               PrtAlertGroupTC,
    prtAlertGroupIndex          Integer32,
    prtAlertLocation            Integer32,
    prtAlertCode                PrtAlertCodeTC,
    prtAlertDescription         OCTET STRING,
    prtAlertTime                TimeTicks
}

prtAlertIndex OBJECT-TYPE
    SYNTAX     Integer32 (1..65535)
    MAX-ACCESS read-only
    STATUS     current
    DESCRIPTION
         "The index value used to determine which alerts have
         been added or removed from the alert table. This is an
         incrementing integer starting from zero every time the
         printer is reset.  When the printer adds an alert to the
         table, that alert is assigned the next higher integer
         value from the last item entered into the table.  If the
         index value reaches its maximum value, the next item
         entered will cause the index value to roll over and
         start at zero again.  The first event placed in the
         alert table after a reset of the printer shall have an
         index value of 1.  NOTE: The management application will
         read the alert table when a trap or event notification
         occurs or at a periodic rate and then parse the table to
         determine if any new entries were added by comparing the
         last known index value with the current highest index
         value. The management application will then update its
         copy of the alert table.  When the printer discovers
         that an alert is no longer active, the printer shall
         remove the row for that alert from the table and shall
         reduce the number of rows in the table.  The printer may
         add or delete any number of rows from the table at any
         time.  The management station can detect when binary
         change alerts have been deleted by requesting an
         attribute of each alert, and noting alerts as deleted
         when that retrieval is not possible."
    ::= { prtAlertEntry 1 }

prtAlertSeverityLevel OBJECT-TYPE
    -- This value is a type 1 enumeration
    SYNTAX     PrtAlertSeverityLevelTC
    MAX-ACCESS read-only
    STATUS     current
    DESCRIPTION
         "The level of severity of this alert table entry.  The
         printer determines the severity level assigned to each
         entry into the table."
    ::= { prtAlertEntry 2 }

prtAlertTrainingLevel OBJECT-TYPE
    -- This value is a type 2 enumeration
    SYNTAX     PrtAlertTrainingLevelTC
    MAX-ACCESS read-only
    STATUS     current
    DESCRIPTION
        "See textual convention PrtAlertTrainingLevelTC"
    ::= { prtAlertEntry 3 }

prtAlertGroup OBJECT-TYPE
    -- This value is a type 1 enumeration
    SYNTAX     PrtAlertGroupTC
    MAX-ACCESS read-only
    STATUS     current
    DESCRIPTION
         "The type of sub-unit within the printer model that this
         alert is related. Input, output, and markers are
         examples of printer model groups, i.e., examples of
         types of sub-units. Wherever possible, these
         enumerations match the sub-identifier that identifies
         the relevant table in the printmib."
    ::= { prtAlertEntry 4 }

prtAlertGroupIndex OBJECT-TYPE
    SYNTAX     Integer32
    MAX-ACCESS read-only
    STATUS     current
    DESCRIPTION
         "An index of the row within the principle table in the
         group identified by prtAlertGroup that represents the
         sub-unit of the printer that caused this alert.  The
         combination of the prtAlertGroup and the
         prtAlertGroupIndex defines exactly which printer sub-
         unit caused the alert; for example, Input #3, Output #2,
         and Marker #1. Every object in this MIB is indexed with
         hrDeviceIndex and optionally, another index variable.
         If this other index variable is present in the table
         that generated the alert, it will be used as the value
         for this object.  Otherwise, this value shall be -1."
    ::= { prtAlertEntry 5 }

prtAlertLocation OBJECT-TYPE
    SYNTAX     Integer32
    MAX-ACCESS read-only
    STATUS     current
    DESCRIPTION
         "The sub-unit location that is defined by the printer
         manufacturer to further refine the location of this
         alert within the designated sub-unit.  The location is
         used in conjunction with the Group and GroupIndex
         values; for example, there is an alert in Input #2 at
         location number 7. The value (-2) indicates unknown"
    ::= { prtAlertEntry 6 }

prtAlertCode OBJECT-TYPE
    -- This value is a type 2 enumeration
    SYNTAX     PrtAlertCodeTC
    MAX-ACCESS read-only
    STATUS     current
    DESCRIPTION
         "See associated textual convention PrtAlertCodeTC"
    ::= { prtAlertEntry 7}

prtAlertDescription OBJECT-TYPE
    SYNTAX     OCTET STRING (SIZE(0..255))
    MAX-ACCESS read-only
    STATUS     current
    DESCRIPTION
         "A description of this alert entry in the localization
         specified by prtGeneralCurrentLocalization.  The
         description is provided by the printer to further
         elaborate on the enumerated alert or provide information
         in the case where the code is classified as 'other' or
         'unknown'.  The printer is required to return a
         description string but the string may be a null
         string."
    ::= { prtAlertEntry 8 }

prtAlertTime OBJECT-TYPE
    SYNTAX     TimeTicks
    MAX-ACCESS read-only
    STATUS     current
    DESCRIPTION
         "The value of sysUpTime at the time that this alert was
         generated."
    ::= { prtAlertEntry 9 }


printerV1Alert OBJECT-IDENTITY
    STATUS  current
    DESCRIPTION
         "The value of the enterprise-specific OID in an SNMPv1
         trap sent signaling a critical event in the
         prtAlertTable."
    ::= { prtAlert 2 }



printerV2AlertPrefix OBJECT IDENTIFIER ::= { printerV1Alert 0 }

printerV2Alert NOTIFICATION-TYPE
    OBJECTS { prtAlertIndex, prtAlertSeverityLevel,
prtAlertGroup, prtAlertGroupIndex, prtAlertLocation, prtAlertCode
}
    STATUS  current
    DESCRIPTION
         "This trap is sent whenever a critical event is added to
         the prtAlertTable."
    ::= { printerV2AlertPrefix 1 }



-- Note that the SNMPv2 to SNMPv1 translation rules dictate that
-- the preceding structure will result in SNMPv1 traps of the
-- following form:
--
-- printerAlert TRAP-TYPE
--     ENTERPRISE printerV1Alert
--     VARIABLES { prtAlertIndex, prtAlertSeverityLevel,
--                 prtAlertGroup, prtAlertGroupIndex,
--                 prtAlertLocation, prtAlertCode }
--     DESCRIPTION
--        "This trap is sent whenever a critical event is added
--         to the prtAlertTable."
--     ::= 1
--



-- Conformance Information

prtMIBConformance OBJECT IDENTIFIER ::= { printmib 2 }

-- compliance statements
prtMIBCompliance MODULE-COMPLIANCE
    STATUS  current
    DESCRIPTION
        "The compliance statement for agents that implement the
        printer MIB."
    MODULE -- this module
    MANDATORY-GROUPS { prtGeneralGroup, prtInputGroup,
                       prtOutputGroup,
                       prtMarkerGroup, prtMediaPathGroup,
                       prtChannelGroup, prtInterpreterGroup,
                       prtConsoleGroup, prtAlertTableGroup }

        OBJECT      prtGeneralReset
        SYNTAX      INTEGER {
                        notResetting(3),
                        resetToNVRAM(5)
                    }
        DESCRIPTION
         "It is conformant to implement just these two states in
         this object.  Any additional states are optional."

       OBJECT    prtGeneralCurrentLocalization
       MIN-ACCESS  read-only
       DESCRIPTION
         "It is conformant to implement this object as read-only"

       OBJECT    prtGeneralCurrentOperator
       MIN-ACCESS  read-only
       DESCRIPTION
         "It is conformant to implement this object as read-only"

       OBJECT    prtGeneralServicePerson
       MIN-ACCESS  read-only
       DESCRIPTION
         "It is conformant to implement this object as read-only"

       OBJECT    prtAuxiliarySheetStartupPage
       MIN-ACCESS  read-only
       DESCRIPTION
         "It is conformant to implement this object as read-only"

       OBJECT    prtAuxiliarySheetBannerPage
       MIN-ACCESS  read-only
       DESCRIPTION
         "It is conformant to implement this object as read-only"

       OBJECT    prtGeneralPrinterName
       MIN-ACCESS  read-only
       DESCRIPTION
         "It is conformant to implement this object as read-only"

       OBJECT    prtGeneralSerialNumber
       MIN-ACCESS  read-only
       DESCRIPTION
         "It is conformant to implement this object as read-only"

       OBJECT    prtInputDefaultIndex
       MIN-ACCESS  read-only
       DESCRIPTION
         "It is conformant to implement this object as read-only"

       OBJECT    prtInputMediaDimFeedDirDeclared
       MIN-ACCESS  read-only
       DESCRIPTION
         "It is conformant to implement this object as read-only"

       OBJECT    prtInputMaxCapacity
       MIN-ACCESS  read-only
       DESCRIPTION
         "It is conformant to implement this object as read-only"

       OBJECT    prtInputCurrentLevel
       MIN-ACCESS  read-only
       DESCRIPTION
         "It is conformant to implement this object as read-only"

       OBJECT    prtInputMediaName
       MIN-ACCESS  read-only
       DESCRIPTION
         "It is conformant to implement this object as read-only"

       OBJECT    prtInputName
       MIN-ACCESS  read-only
       DESCRIPTION
         "It is conformant to implement this object as read-only"

       OBJECT    prtInputSecurity
       MIN-ACCESS  read-only
       DESCRIPTION
         "It is conformant to implement this object as read-only"

       OBJECT    prtInputMediaWeight
       MIN-ACCESS  read-only
       DESCRIPTION
         "It is conformant to implement this object as read-only"

       OBJECT    prtInputMediaType
       MIN-ACCESS  read-only
       DESCRIPTION
         "It is conformant to implement this object as read-only"

       OBJECT    prtInputMediaColor
       MIN-ACCESS  read-only
       DESCRIPTION
         "It is conformant to implement this object as read-only"

       OBJECT    prtInputMediaFormParts
       MIN-ACCESS  read-only
       DESCRIPTION
         "It is conformant to implement this object as read-only"

       OBJECT    prtInputMediaLoadTimeout
       MIN-ACCESS  read-only
       DESCRIPTION
         "It is conformant to implement this object as read-only"

       OBJECT    prtInputNextIndex
       MIN-ACCESS  read-only
       DESCRIPTION
         "It is conformant to implement this object as read-only"

       OBJECT    prtOutputDefaultIndex
       MIN-ACCESS  read-only
       DESCRIPTION
         "It is conformant to implement this object as read-only"

       OBJECT    prtOutputMaxCapacity
       MIN-ACCESS  read-only
       DESCRIPTION
         "It is conformant to implement this object as read-only"

       OBJECT    prtOutputRemainingCapacity
       MIN-ACCESS  read-only
       DESCRIPTION
         "It is conformant to implement this object as read-only"

       OBJECT    prtOutputName
       MIN-ACCESS  read-only
       DESCRIPTION
         "It is conformant to implement this object as read-only"

       OBJECT    prtOutputSecurity
       MIN-ACCESS  read-only
       DESCRIPTION
         "It is conformant to implement this object as read-only"

       OBJECT    prtOutputMaxDimFeedDir
       MIN-ACCESS  read-only
       DESCRIPTION
         "It is conformant to implement this object as read-only"

       OBJECT    prtOutputMaxDimXFeedDir
       MIN-ACCESS  read-only
       DESCRIPTION
         "It is conformant to implement this object as read-only"

       OBJECT    prtOutputMinDimFeedDir
       MIN-ACCESS  read-only
       DESCRIPTION
         "It is conformant to implement this object as read-only"

       OBJECT    prtOutputMinDimXFeedDir
       MIN-ACCESS  read-only
       DESCRIPTION
         "It is conformant to implement this object as read-only"

       OBJECT    prtOutputStackingOrder
       MIN-ACCESS  read-only
       DESCRIPTION
         "It is conformant to implement this object as read-only"

       OBJECT    prtOutputPageDeliveryOrientation
       MIN-ACCESS  read-only
       DESCRIPTION
         "It is conformant to implement this object as read-only"

       OBJECT    prtOutputBursting
       MIN-ACCESS  read-only
       DESCRIPTION
         "It is conformant to implement this object as read-only"

       OBJECT    prtOutputDecollating
       MIN-ACCESS  read-only
       DESCRIPTION
         "It is conformant to implement this object as read-only"

       OBJECT    prtOutputPageCollated
       MIN-ACCESS  read-only
       DESCRIPTION
         "It is conformant to implement this object as read-only"

       OBJECT    prtOutputOffsetStacking
       MIN-ACCESS  read-only
       DESCRIPTION
         "It is conformant to implement this object as read-only"

       OBJECT    prtMarkerDefaultIndex
       MIN-ACCESS  read-only
       DESCRIPTION
         "It is conformant to implement this object as read-only"

       OBJECT    prtMarkerSuppliesMaxCapacity
       MIN-ACCESS  read-only
       DESCRIPTION
         "It is conformant to implement this object as read-only"

       OBJECT    prtMarkerSuppliesLevel
       MIN-ACCESS  read-only
       DESCRIPTION
         "It is conformant to implement this object as read-only"

       OBJECT    prtMediaPathDefaultIndex
       MIN-ACCESS  read-only
       DESCRIPTION
         "It is conformant to implement this object as read-only"

       OBJECT    prtChannelCurrentJobCntlLangIndex
       MIN-ACCESS  read-only
       DESCRIPTION
         "It is conformant to implement this object as read-only"

       OBJECT    prtChannelDefaultPageDescLangIndex
       MIN-ACCESS  read-only
       DESCRIPTION
         "It is conformant to implement this object as read-only"

       OBJECT    prtChannelState
       MIN-ACCESS  read-only
       DESCRIPTION
         "It is conformant to implement this object as read-only"

       OBJECT    prtChannelIfIndex
       MIN-ACCESS  read-only
       DESCRIPTION
         "It is conformant to implement this object as read-only"

       OBJECT    prtInterpreterDefaultOrientation
       MIN-ACCESS  read-only
       DESCRIPTION
         "It is conformant to implement this object as read-only"

       OBJECT    prtInterpreterDefaultCharSetIn
       MIN-ACCESS  read-only
       DESCRIPTION
         "It is conformant to implement this object as read-only"

       OBJECT    prtInterpreterDefaultCharSetOut
       MIN-ACCESS  read-only
       DESCRIPTION
         "It is conformant to implement this object as read-only"

       OBJECT    prtConsoleLocalization
       MIN-ACCESS  read-only
       DESCRIPTION
         "It is conformant to implement this object as read-only"

       OBJECT    prtConsoleDisable
       MIN-ACCESS  read-only
       DESCRIPTION
         "It is conformant to implement this object as read-only"

       OBJECT    prtConsoleDisplayBufferText
       MIN-ACCESS  read-only
       DESCRIPTION
         "It is conformant to implement this object as read-only"

       OBJECT      prtConsoleOnTime
       MIN-ACCESS  read-only
       DESCRIPTION
         "It is conformant to implement this object as read-only"

       OBJECT      prtConsoleOffTime
       MIN-ACCESS  read-only
       DESCRIPTION
         "It is conformant to implement this object as read-only"

       GROUP       prtResponsiblePartyGroup
       DESCRIPTION
         "This group is unconditionally optional."

       GROUP       prtExtendedInputGroup
       DESCRIPTION
         "This group is unconditionally optional."

       GROUP       prtInputMediaGroup
       DESCRIPTION
         "This group is unconditionally optional."

       GROUP       prtExtendedOutputGroup
       DESCRIPTION
         "This group is unconditionally optional."

       GROUP       prtOutputDimensionsGroup
       DESCRIPTION
         "This group is unconditionally optional."

       GROUP       prtOutputFeaturesGroup
       DESCRIPTION
         "This group is unconditionally optional."

       GROUP       prtMarkerSuppliesGroup
       DESCRIPTION
         "This group is unconditionally optional."

       GROUP       prtMarkerColorantGroup
       DESCRIPTION
         "This group is unconditionally optional."

       GROUP       prtAuxiliarySheetGroup
       DESCRIPTION
         "This group is unconditionally optional."

       GROUP       prtInputSwitchingGroup
       DESCRIPTION
         "This group is unconditionally optional."

    ::= { prtMIBConformance 1 }

prtMIBGroups      OBJECT IDENTIFIER ::= { prtMIBConformance 2 }

prtGeneralGroup OBJECT-GROUP
    OBJECTS { prtGeneralConfigChanges,
              prtGeneralCurrentLocalization,
              prtGeneralReset, prtCoverDescription,
              prtCoverStatus,
              prtLocalizationLanguage, prtLocalizationCountry,
              prtLocalizationCharacterSet, prtStorageRefIndex,
              prtDeviceRefIndex, prtGeneralPrinterName,
              prtGeneralSerialNumber }
    STATUS  current
    DESCRIPTION
        "The general printer group."
    ::= { prtMIBGroups 1 }

prtResponsiblePartyGroup OBJECT-GROUP
    OBJECTS { prtGeneralCurrentOperator, prtGeneralServicePerson
}
    STATUS  current
    DESCRIPTION
         "The responsible party group contains contact
         information for humans responsible for the printer."
    ::= { prtMIBGroups 2 }

prtInputGroup OBJECT-GROUP
     OBJECTS { prtInputDefaultIndex, prtInputType,
               prtInputDimUnit, prtInputMediaDimFeedDirDeclared,
               prtInputMediaDimXFeedDirDeclared,
               prtInputMediaDimFeedDirChosen,
               prtInputMediaDimXFeedDirChosen,
               prtInputCapacityUnit, prtInputMaxCapacity,
               prtInputCurrentLevel, prtInputStatus,
               prtInputMediaName }
    STATUS  current
    DESCRIPTION
        "The input group."
    ::= { prtMIBGroups 3 }

prtExtendedInputGroup OBJECT-GROUP
     OBJECTS { prtInputName, prtInputVendorName, prtInputModel,
               prtInputVersion, prtInputSerialNumber,
               prtInputDescription, prtInputSecurity }
    STATUS  current
    DESCRIPTION
        "The extended input group."
    ::= { prtMIBGroups 4 }

prtInputMediaGroup OBJECT-GROUP
    OBJECTS { prtInputMediaWeight, prtInputMediaType,
              prtInputMediaColor, prtInputMediaFormParts }
    STATUS  current
    DESCRIPTION
        "The input media group."
    ::= { prtMIBGroups 5 }

prtOutputGroup OBJECT-GROUP
    OBJECTS { prtOutputDefaultIndex, prtOutputType,
              prtOutputCapacityUnit, prtOutputMaxCapacity,
              prtOutputRemainingCapacity,  prtOutputStatus }
    STATUS  current
    DESCRIPTION
        "The output group."
    ::= { prtMIBGroups 6 }

prtExtendedOutputGroup OBJECT-GROUP
    OBJECTS { prtOutputName, prtOutputVendorName, prtOutputModel,
              prtOutputVersion, prtOutputSerialNumber,
              prtOutputDescription, prtOutputSecurity }
    STATUS  current
    DESCRIPTION
        "The extended output group."
    ::= { prtMIBGroups 7 }

prtOutputDimensionsGroup OBJECT-GROUP
    OBJECTS { prtOutputDimUnit, prtOutputMaxDimFeedDir,
              prtOutputMaxDimXFeedDir, prtOutputMinDimFeedDir,
              prtOutputMinDimXFeedDir }
    STATUS  current
    DESCRIPTION
        "The output dimensions group"
    ::= { prtMIBGroups 8 }

prtOutputFeaturesGroup OBJECT-GROUP
    OBJECTS { prtOutputStackingOrder,
              prtOutputPageDeliveryOrientation,
              prtOutputBursting,
              prtOutputDecollating, prtOutputPageCollated,
              prtOutputOffsetStacking }
    STATUS  current
    DESCRIPTION
        "The output features group."
    ::= { prtMIBGroups 9 }

prtMarkerGroup OBJECT-GROUP
    OBJECTS { prtMarkerDefaultIndex, prtMarkerMarkTech,
              prtMarkerCounterUnit, prtMarkerLifeCount,
              prtMarkerPowerOnCount, prtMarkerProcessColorants,
              prtMarkerSpotColorants,
              prtMarkerAddressabilityUnit,
              prtMarkerAddressabilityFeedDir,
              prtMarkerAddressabilityXFeedDir,
              prtMarkerNorthMargin,
              prtMarkerSouthMargin, prtMarkerWestMargin,
              prtMarkerEastMargin, prtMarkerStatus }
    STATUS  current
    DESCRIPTION
        "The marker group."
    ::= { prtMIBGroups 10 }

prtMarkerSuppliesGroup OBJECT-GROUP
    OBJECTS { prtMarkerSuppliesMarkerIndex,
              prtMarkerSuppliesColorantIndex,
              prtMarkerSuppliesClass,
              prtMarkerSuppliesType,
              prtMarkerSuppliesDescription,
              prtMarkerSuppliesSupplyUnit,
              prtMarkerSuppliesMaxCapacity,
              prtMarkerSuppliesLevel }
    STATUS  current
    DESCRIPTION
        "The marker supplies group."
    ::= { prtMIBGroups 11 }

prtMarkerColorantGroup OBJECT-GROUP
    OBJECTS { prtMarkerColorantMarkerIndex,
              prtMarkerColorantRole,
              prtMarkerColorantValue, prtMarkerColorantTonality }
    STATUS  current
    DESCRIPTION
        "The marker colorant group."
    ::= { prtMIBGroups 12 }

prtMediaPathGroup OBJECT-GROUP
    OBJECTS { prtMediaPathDefaultIndex,
              prtMediaPathMaxSpeedPrintUnit,
              prtMediaPathMediaSizeUnit, prtMediaPathMaxSpeed,
              prtMediaPathMaxMediaFeedDir,
              prtMediaPathMaxMediaXFeedDir,
              prtMediaPathMinMediaFeedDir,
              prtMediaPathMinMediaXFeedDir, prtMediaPathType,
              prtMediaPathDescription, prtMediaPathStatus}
    STATUS  current
    DESCRIPTION
        "The media path group."
    ::= { prtMIBGroups 13 }

prtChannelGroup OBJECT-GROUP
    OBJECTS { prtChannelType, prtChannelProtocolVersion,
              prtChannelCurrentJobCntlLangIndex,
              prtChannelDefaultPageDescLangIndex,
              prtChannelState,
              prtChannelIfIndex, prtChannelStatus,
              prtChannelInformation }
    STATUS  current
    DESCRIPTION
        "The channel group."
    ::= { prtMIBGroups 14 }

prtInterpreterGroup OBJECT-GROUP
    OBJECTS { prtInterpreterLangFamily, prtInterpreterLangLevel,
              prtInterpreterLangVersion,
              prtInterpreterDescription,
              prtInterpreterVersion,
              prtInterpreterDefaultOrientation,
              prtInterpreterFeedAddressability,
              prtInterpreterXFeedAddressability,
              prtInterpreterDefaultCharSetIn,
              prtInterpreterDefaultCharSetOut,
              prtInterpreterTwoWay }
    STATUS  current
    DESCRIPTION
        "The interpreter group."
    ::= { prtMIBGroups 15 }

prtConsoleGroup OBJECT-GROUP
    OBJECTS { prtConsoleLocalization,
              prtConsoleNumberOfDisplayLines,
              prtConsoleNumberOfDisplayChars, prtConsoleDisable,
              prtConsoleDisplayBufferText, prtConsoleOnTime,
              prtConsoleOffTime, prtConsoleColor,
              prtConsoleDescription }
    STATUS  current
    DESCRIPTION
        "The console group."
    ::= { prtMIBGroups 16 }

prtAlertTableGroup OBJECT-GROUP
    OBJECTS { prtAlertIndex, prtAlertCriticalEvents,
              prtAlertAllEvents,
              prtAlertSeverityLevel, prtAlertTrainingLevel,
              prtAlertGroup, prtAlertGroupIndex,
              prtAlertLocation, prtAlertCode,
              prtAlertDescription, prtAlertTime }
    STATUS  current
    DESCRIPTION
        "The alert table group."
    ::= { prtMIBGroups 17 }

--
-- prtAlertTimeGroup has been DEPRECATED (prtMIBGroups 18 )
--

prtAuxiliarySheetGroup OBJECT-GROUP
    OBJECTS { prtAuxiliarySheetStartupPage,
              prtAuxiliarySheetBannerPage }
    STATUS  current
    DESCRIPTION
        "The auxiliary sheet group."
    ::= { prtMIBGroups 19 }

prtInputSwitchingGroup OBJECT-GROUP
    OBJECTS { prtInputMediaLoadTimeout, prtInputNextIndex }
    STATUS  current
    DESCRIPTION
     "The input switching group."
    ::= { prtMIBGroups 20 }


END
