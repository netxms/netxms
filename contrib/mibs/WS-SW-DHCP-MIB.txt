-- vim: syntax=mib
--
-- WS-SW-DHCP-MIB.my
-- MIB generated by MG-SOFT Visual MIB Builder Version 6.0  Build 88
-- Friday, July 28, 2006 at 23:42:34
--

--  WS-SW-DHCP-MIB.my
-- MIB generated by MG-SOFT Visual MIB Builder Version 6.0  Build 88
-- Wednesday, May 24, 2006 at 16:45:11
-- 

	WS-SW-DHCP-MIB DEFINITIONS ::= BEGIN
 
		IMPORTS
			OBJECT-GROUP, MODULE-COMPLIANCE			
				FROM SNMPv2-CONF			
			IpAddress, OBJECT-TYPE, MODULE-IDENTITY			
				FROM SNMPv2-SMI			
			DisplayString			
				FROM SNMPv2-TC			
			wsSwDHCP			
				FROM WS-SW-SMI;
	
	
--  1.3.6.1.4.1.388.14.2.3.4
-- May 05, 2005 at 14:14 GMT
-- May 24, 2006 at 16:44 GMT
-- May 11, 2005 at 14:54 GMT
-- May 10, 2005 at 10:48 GMT
-- May 09, 2005 at 17:36 GMT
-- May 05, 2005 at 12:57 GMT
		-- 1.3.6.1.4.1.388.14.2.3.4
		wsSWDhcpModule MODULE-IDENTITY 
			LAST-UPDATED "200505051414Z"		-- May 05, 2005 at 14:14 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"DHCP client MIB"
			REVISION "200505051257Z"		-- May 05, 2005 at 12:57 GMT
			DESCRIPTION 
				"01a01"
			REVISION "200505091736Z"		-- May 09, 2005 at 17:36 GMT
			DESCRIPTION 
				"01a02"
			REVISION "200505101048Z"		-- May 10, 2005 at 10:48 GMT
			DESCRIPTION 
				"01a03"
			REVISION "200505111454Z"		-- May 11, 2005 at 14:54 GMT
			DESCRIPTION 
				"01a04"
			REVISION "200605241644Z"		-- May 24, 2006 at 16:44 GMT
			DESCRIPTION 
				"01a05"
			::= { wsSwDHCP 4 }

		
	
	
--
-- Node definitions
--
	
--  Node definitions
-- 
-- 1.3.6.1.4.1.388.14.2.3.4.1
		-- 1.3.6.1.4.1.388.14.2.3.4.1
		wsSWDhcpClient OBJECT IDENTIFIER ::= { wsSWDhcpModule 1 }

		
--  1.3.6.1.4.1.388.14.2.3.4.1.1
		-- 1.3.6.1.4.1.388.14.2.3.4.1.1
		wsDhcpClientSvrInfor OBJECT IDENTIFIER ::= { wsSWDhcpClient 1 }

		
--  1.3.6.1.4.1.388.14.2.3.4.1.1.1
		-- 1.3.6.1.4.1.388.14.2.3.4.1.1.1
		wsDhcpClientDomainName OBJECT-TYPE
			SYNTAX DisplayString (SIZE (0..80))
			MAX-ACCESS read-only
			STATUS current
			DESCRIPTION
				"domain name from DHCP server"
			::= { wsDhcpClientSvrInfor 1 }

		
--  1.3.6.1.4.1.388.14.2.3.4.1.1.2
		-- 1.3.6.1.4.1.388.14.2.3.4.1.1.2
		wsDhcpClientDefaultGateway OBJECT-TYPE
			SYNTAX IpAddress
			MAX-ACCESS read-only
			STATUS current
			DESCRIPTION
				"default gateway from DHCP server"
			::= { wsDhcpClientSvrInfor 2 }

		
--  1.3.6.1.4.1.388.14.2.3.4.1.1.3
		-- 1.3.6.1.4.1.388.14.2.3.4.1.1.3
		wsDhcpClientNameSvrTable OBJECT-TYPE
			SYNTAX SEQUENCE OF WsDhcpClientNameSvrEntry
			MAX-ACCESS not-accessible
			STATUS current
			DESCRIPTION
				"name server table from DHCP server"
			::= { wsDhcpClientSvrInfor 3 }

		
--  1.3.6.1.4.1.388.14.2.3.4.1.1.3.1
		-- 1.3.6.1.4.1.388.14.2.3.4.1.1.3.1
		wsDhcpClientNameSvrEntry OBJECT-TYPE
			SYNTAX WsDhcpClientNameSvrEntry
			MAX-ACCESS not-accessible
			STATUS current
			DESCRIPTION
				"name servedr table entry"
			INDEX { wsDhcpClientNameSvrIndex }
			::= { wsDhcpClientNameSvrTable 1 }

		
		WsDhcpClientNameSvrEntry ::=
			SEQUENCE { 
				wsDhcpClientNameSvrIndex
					INTEGER,
				wsDhcpClientNameSvrIP
					IpAddress
			 }

--  1.3.6.1.4.1.388.14.2.3.4.1.1.3.1.1
		-- 1.3.6.1.4.1.388.14.2.3.4.1.1.3.1.1
		wsDhcpClientNameSvrIndex OBJECT-TYPE
			SYNTAX INTEGER (1..8)
			MAX-ACCESS not-accessible
			STATUS current
			DESCRIPTION
				"simple index"
			::= { wsDhcpClientNameSvrEntry 1 }

		
--  1.3.6.1.4.1.388.14.2.3.4.1.1.3.1.2
		-- 1.3.6.1.4.1.388.14.2.3.4.1.1.3.1.2
		wsDhcpClientNameSvrIP OBJECT-TYPE
			SYNTAX IpAddress
			MAX-ACCESS read-only
			STATUS current
			DESCRIPTION
				"name server IP"
			::= { wsDhcpClientNameSvrEntry 2 }

		
--  1.3.6.1.4.1.388.14.2.3.4.1.2
		-- 1.3.6.1.4.1.388.14.2.3.4.1.2
		wsDhcpClientVendorInfor OBJECT IDENTIFIER ::= { wsSWDhcpClient 2 }

		
--  1.3.6.1.4.1.388.14.2.3.4.1.2.3
		-- 1.3.6.1.4.1.388.14.2.3.4.1.2.1
		wsDhcpClientUpgSvrInfo OBJECT-TYPE
			SYNTAX DisplayString
			MAX-ACCESS read-only
			STATUS current
			DESCRIPTION
				"user name from DHCP server"
			::= { wsDhcpClientVendorInfor 1 }

		
--  1.3.6.1.4.1.388.14.2.3.4.1.2.5
		-- 1.3.6.1.4.1.388.14.2.3.4.1.2.2
		wsDhcpClientUpgImgName OBJECT-TYPE
			SYNTAX DisplayString
			MAX-ACCESS read-only
			STATUS current
			DESCRIPTION
				"image name from DHCP server, including path"
			::= { wsDhcpClientVendorInfor 2 }

		
--  1.3.6.1.4.1.388.14.2.3.4.1.2.6
		-- 1.3.6.1.4.1.388.14.2.3.4.1.2.3
		wsDhcpClientUpgCfgName OBJECT-TYPE
			SYNTAX DisplayString
			MAX-ACCESS read-only
			STATUS current
			DESCRIPTION
				"config name from DHCP server, including path"
			::= { wsDhcpClientVendorInfor 3 }

		
		-- 1.3.6.1.4.1.388.14.2.3.4.1.2.4
		wsDhcpClientUpgClusterCfgName OBJECT-TYPE
			SYNTAX DisplayString
			MAX-ACCESS read-only
			STATUS current
			DESCRIPTION
				"Description."
			::= { wsDhcpClientVendorInfor 4 }

		
--  1.3.6.1.4.1.388.14.2.3.4.100
		-- 1.3.6.1.4.1.388.14.2.3.4.100
		wsSwDhcpConformance OBJECT IDENTIFIER ::= { wsSWDhcpModule 100 }

		
--  1.3.6.1.4.1.388.14.2.3.4.100.1
		-- 1.3.6.1.4.1.388.14.2.3.4.100.1
		wsDhcpCompliances OBJECT IDENTIFIER ::= { wsSwDhcpConformance 1 }

		
--  1.3.6.1.4.1.388.14.2.3.4.100.1.1
-- this module
		-- 1.3.6.1.4.1.388.14.2.3.4.100.1.1
		wsDhcpCompliance MODULE-COMPLIANCE
			STATUS current
			DESCRIPTION 
				"DHCP MIB compiance"
			MODULE -- this module
				MANDATORY-GROUPS { wsSwDhcpClientGroup }
			::= { wsDhcpCompliances 1 }

		
--  1.3.6.1.4.1.388.14.2.3.4.100.2
		-- 1.3.6.1.4.1.388.14.2.3.4.100.2
		wsSwDhcpGroups OBJECT IDENTIFIER ::= { wsSwDhcpConformance 2 }

		
--  1.3.6.1.4.1.388.14.2.3.4.100.2.1
		-- 1.3.6.1.4.1.388.14.2.3.4.100.2.1
		wsSwDhcpClientGroup OBJECT-GROUP
			OBJECTS { wsDhcpClientDomainName, wsDhcpClientDefaultGateway, wsDhcpClientNameSvrIP, wsDhcpClientUpgImgName, wsDhcpClientUpgCfgName, 
				wsDhcpClientUpgSvrInfo, wsDhcpClientUpgClusterCfgName }
			STATUS current
			DESCRIPTION 
				"DHCP client group"
			::= { wsSwDhcpGroups 1 }

		
	
	END

--
-- WS-SW-DHCP-MIB.my
--
