-- vim: syntax=mib
--
-- WS-SW-GRE-MIB.my
-- MIB generated by MG-SOFT Visual MIB Builder Version 6.0  Build 88
-- Wednesday, May 24, 2006 at 16:58:30
--

	WS-SW-GRE-MIB DEFINITIONS ::= BEGIN

		IMPORTS
			OBJECT-GROUP, MODULE-COMPLIANCE
				FROM SNMPv2-CONF
			IpAddress, Unsigned32, OBJECT-TYPE, MODULE-IDENTITY
				FROM SNMPv2-SMI
			wsIfNumber
				FROM WS-SW-IF-MIB
			wsSwGre
				FROM WS-SW-SMI;


		-- 1.3.6.1.4.1.388.14.2.8.1
		wsSwGreMIB MODULE-IDENTITY
			LAST-UPDATED "200604271534Z"		-- April 27, 2006 at 15:34 GMT
			ORGANIZATION
				"Symbol Technologies"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"Description."
			REVISION "200605241654Z"		-- May 24, 2006 at 16:54 GMT
			DESCRIPTION
				"02a02"
			REVISION "200604271543Z"		-- April 27, 2006 at 15:43 GMT
			DESCRIPTION
				"02a01"
			::= { wsSwGre 1 }



--
-- Node definitions
--

		-- 1.3.6.1.4.1.388.14.2.8.1.1
		wsSwGRETunnelTable OBJECT-TYPE
			SYNTAX SEQUENCE OF WsSwGRETunnelEntry
			MAX-ACCESS not-accessible
			STATUS current
			DESCRIPTION
				"Description."
			::= { wsSwGreMIB 1 }


		-- 1.3.6.1.4.1.388.14.2.8.1.1.1
		wsSwGRETunnelEntry OBJECT-TYPE
			SYNTAX WsSwGRETunnelEntry
			MAX-ACCESS not-accessible
			STATUS current
			DESCRIPTION
				"Description."
			INDEX { wsIfNumber }
			::= { wsSwGRETunnelTable 1 }


		WsSwGRETunnelEntry ::=
			SEQUENCE {
				wsSwGRETunnelLocalIpAddr
					IpAddress,
				wsSwGRETunnelRemoteIpAddr
					IpAddress,
				wsSwGRETunnelTTL
					Unsigned32
			 }

		-- 1.3.6.1.4.1.388.14.2.8.1.1.1.1
		wsSwGRETunnelLocalIpAddr OBJECT-TYPE
			SYNTAX IpAddress
			MAX-ACCESS read-write
			STATUS current
			DESCRIPTION
				"Description."
			::= { wsSwGRETunnelEntry 1 }


		-- 1.3.6.1.4.1.388.14.2.8.1.1.1.2
		wsSwGRETunnelRemoteIpAddr OBJECT-TYPE
			SYNTAX IpAddress
			MAX-ACCESS read-write
			STATUS current
			DESCRIPTION
				"Description."
			::= { wsSwGRETunnelEntry 2 }


		-- 1.3.6.1.4.1.388.14.2.8.1.1.1.3
		wsSwGRETunnelTTL OBJECT-TYPE
			SYNTAX Unsigned32
			MAX-ACCESS read-write
			STATUS current
			DESCRIPTION
				"Description."
			::= { wsSwGRETunnelEntry 3 }


		-- 1.3.6.1.4.1.388.14.2.8.1.100
		wsSwGreMIBConformance OBJECT IDENTIFIER ::= { wsSwGreMIB 100 }


		-- 1.3.6.1.4.1.388.14.2.8.1.100.1
		wsSwGreMIBCompliances OBJECT IDENTIFIER ::= { wsSwGreMIBConformance 1 }


		-- 1.3.6.1.4.1.388.14.2.8.1.100.1.1
		wsSwGreMIBCompliance MODULE-COMPLIANCE
			STATUS current
			DESCRIPTION
				"Description."
			MODULE -- this module
				MANDATORY-GROUPS { wsSwGreMIBGroup }
			::= { wsSwGreMIBCompliances 1 }


		-- 1.3.6.1.4.1.388.14.2.8.1.100.2
		wsSwGreMIBGroups OBJECT IDENTIFIER ::= { wsSwGreMIBConformance 2 }


		-- 1.3.6.1.4.1.388.14.2.8.1.100.2.1
		wsSwGreMIBGroup OBJECT-GROUP
			OBJECTS { wsSwGRETunnelLocalIpAddr, wsSwGRETunnelRemoteIpAddr, wsSwGRETunnelTTL }
			STATUS current
			DESCRIPTION
				"Description."
			::= { wsSwGreMIBGroups 1 }



	END

--
-- WS-SW-GRE-MIB.my
--
