-- **********************************************************
-- Copyright 2008-2012 VMware, Inc.  All rights reserved. 
-- **********************************************************

VMWARE-AGENTCAP-MIB DEFINITIONS ::= BEGIN

IMPORTS
    MODULE-IDENTITY
       FROM SNMPv2-SMI
    vmwareAgentCapabilities
       FROM VMWARE-ROOT-MIB
    AGENT-CAPABILITIES
       FROM  SNMPv2-CONF;
vmwAgentCapabilityMIB MODULE-IDENTITY
   LAST-UPDATED "201210030000Z"
   ORGANIZATION "VMware, Inc"
   CONTACT-INFO
      "VMware, Inc
      3401 Hillview Ave
      Palo Alto, CA 94304
      Tel: 1-877-486-9273 or 650-427-5000
      Fax: 650-427-5001
      Web: http://communities.vmware.com/community/developer/forums/managementapi
      "
   DESCRIPTION
     "This module defines agent capabilities for deployed VMware agents by release. "

   REVISION     "201210030000Z"  
   DESCRIPTION
         "Capabilities for VMware ESX OP agent added."

   REVISION     "201207130000Z"  
   DESCRIPTION
         "Capabilities for VMware ESX 5.1 agent added."

   REVISION     "201010180000Z"  
   DESCRIPTION
         "Capabilities for VMware ESX 5.0 added."
   REVISION     "200810270000Z"  
   DESCRIPTION
         "Capabilities for VMware ESX 4.0 added."
        ::= { vmwareAgentCapabilities 1 }

vmwEsxCapability OBJECT IDENTIFIER ::= {  vmwAgentCapabilityMIB 1 }

--
-- ESX 5.5 and follow up patch releases
--

vmwESX55 AGENT-CAPABILITIES 
  PRODUCT-RELEASE 
     "5.5.x"  
  STATUS  current
  DESCRIPTION
     "Release 5.5 for VMware ESXi supports SNMPv1, SNMPv2c, and SNMPv3 with a stand-alone snmpd process. 

     This release features support for monitoring multiple IP Stacks. The standard IP-MIB, UDP-MIB, and TCP-MIB
     may be used with a context set to the IP Stack Name as found in ENTITY-MIB entLogicalTable 
     or via command: esxcli network ip netstack list
     An example using net-snmp's snmpwalk command:: snmpwalk -v2c -n defaultTcpipStack ip

     No vDR instrumentation is yet available.

     This agent supports read-only protocol operations. This implies that configuring the SNMPv3 Agent 
     can not be done via SET operations. Hence IETF standard SNMPv3 agent configuration mibs are not provided.
     The SNMPv3 protocol is fully supported once configured via the CLI command interface (esxcli system snmp) 
     command set or vCenter Server host profiles. Lastly this SNMP agent provides one read-only view of 
     the entire system to which all SNMPv3 users configured are assigned.
     "
  REFERENCE 
     "http://www.vmware.com/products"

     -- RFC 3418
     SUPPORTS SNMPv2-MIB
     INCLUDES { 
         snmpGroup, 
         systemGroup,
         snmpCommunityGroup,
         snmpBasicNotificationsGroup,
         snmpWarmStartNotificationGroup
         -- groups not supported; snmpSetGroup, snmpNotificationGroup
     }

     VARIATION snmpSetSerialNo
     ACCESS  not-implemented
     DESCRIPTION "Agent provides read-only view of system information."

     VARIATION snmpTrapOID
     ACCESS not-implemented
     DESCRIPTION "Agent does not proxy other agents RFC1157 Trap-PDUs."

     VARIATION  snmpTrapEnterprise
     ACCESS not-implemented
     DESCRIPTION "Agent does not proxy other agents RFC1157 Trap-PDUs."

     VARIATION snmpEnableAuthenTraps
     SYNTAX INTEGER { disabled(2) }
     ACCESS read-only
     DESCRIPTION "Agent does not allow authentication traps. Poll snmpInBadCommunityNames for same info."
     -- the above clause implies this:
     -- VARIATION authenticationFailure
     -- ACCESS not-implemented
     -- DESCRIPTION "Agent does not provide this notification. snmpEnableAuthenTraps will return disabled."

     -- ********************* ************ ************ *************** ***
     -- RFC 3412
     SUPPORTS SNMP-MPD-MIB
     INCLUDES { 
        snmpMPDGroup
     }

     -- ********************* ************ ************ *************** ***
     -- RFC 2863
     SUPPORTS IF-MIB
     INCLUDES { 
         ifGeneralInformationGroup,
         linkUpDownNotificationsGroup
     }

     VARIATION ifAdminStatus
     ACCESS read-only
     DESCRIPTION "Agent provides read-only view of administrative state for each physical interface.
                  ESX virtual switches support changing administrative state 
                  of physical network interfaces (nics) up or down. For example the command:
                  esxcli network nic [up|down] -n vmnic0 
                  Virtual vmware interfaces (ifType 238) also support changing administratie state:
                  network ip interface set --enabled [yes|no] -i vmk0
                 "

     VARIATION ifLinkUpDownTrapEnable
     ACCESS read-only
     DESCRIPTION "Agent provides read-only view of system information."

     VARIATION ifAlias
     ACCESS read-only
     DESCRIPTION "ifIndexes may only change across reboot."

     VARIATION ifInUnknownProtos
     ACCESS not-implemented
     DESCRIPTION "This counter always returns 0."

     -- ifRcvAddressGroup is interface/media specific 
     VARIATION ifRcvAddressStatus
     ACCESS not-implemented
     DESCRIPTION "Required if media specific mib modules are implemented."

     VARIATION ifRcvAddressType 
     ACCESS not-implemented
     DESCRIPTION "Required if media specific mib modules are implemented."

     -- ********************* ************ ************ *************** ***
     -- RFC 4293
     -- supports SNMPv2/3 Contexts for multiple instances
     SUPPORTS IP-MIB
     INCLUDES { 
         ipSystemStatsGroup,   
         ipAddressGroup,
         ipNetToPhysicalGroup, 
         ipDefaultRouterGroup,
         icmpStatsGroup,
         ipSystemStatsHCOctetGroup,
         ipSystemStatsHCPacketGroup,
         ipv4GeneralGroup,
         ipv4IfGroup,
         ipv4SystemStatsGroup,
         ipv4SystemStatsHCPacketGroup,
         ipv6GeneralGroup2,
         ipv6IfGroup,
         ipAddressPrefixGroup,
         ipv6RouterAdvertGroup,
         ipLastChangeGroup
     }
     -- VARIATION ipv6ScopeGroup
     -- ACCESS  not-implemented

     -- ********************* ************ ************ *************** ***
     -- RFC 4292
     -- supports SNMPv2/3 Contexts for multiple instances
     SUPPORTS IP-FORWARD-MIB
     INCLUDES { 
         inetForwardCidrRouteGroup          
     }

     -- ********************* ************ ************ *************** ***
     -- RFC 4113
     -- supports SNMPv2/3 Contexts for multiple instances
     SUPPORTS UDP-MIB
     -- The next two 32 bit counters will be fixed per bug report PR 890894
     -- VARIATION udpInDatagrams
     -- ACCESS not-implemented, use udpHCInDatagrams
     -- VARIATION udpOutDatagrams
     -- ACCESS not-implemented, use udpHCOutDatagrams
     INCLUDES { 
        udpBaseGroup, 
        udpEndpointGroup
     }

     -- ********************* ************ ************ *************** ***
     -- RFC 4022
     -- supports SNMPv2/3 Contexts for multiple instances
     SUPPORTS TCP-MIB
     INCLUDES { 
         tcpBaseGroup, 
         tcpConnectionGroup,
         tcpListenerGroup
     }

     -- RFC 2790
     -- NOTE: For storage larger than Integer32 (Terabyte) this agent will report INT_MAX
     SUPPORTS HOST-RESOURCES-MIB
     INCLUDES { 
            hrSystemGroup,
            hrStorageGroup, -- visorfs "ramdisks" are not reported
            hrDeviceGroup,
            hrSWRunGroup,
            hrSWRunPerfGroup,
            hrSWInstalledGroup  -- updates once an hour
     }

     VARIATION  hrSystemNumUsers 
     ACCESS read-only
     DESCRIPTION "Value reports number of active ESX Shell sessions"

     VARIATION  hrSWRunName
     ACCESS read-only
     DESCRIPTION "Value does not match hrSWInstalledName"

     VARIATION  hrSystemDate
     ACCESS read-only
     DESCRIPTION "agent provides read only access"

     VARIATION hrSystemInitialLoadDevice 
     ACCESS read-only
     DESCRIPTION "agent provides read only access"

     VARIATION hrSystemInitialLoadParameters
     ACCESS read-only
     DESCRIPTION "agent provides read only access"

     VARIATION hrStorageSize 
     ACCESS read-only
     DESCRIPTION "agent provides read only access"

     VARIATION  hrSWRunStatus
     ACCESS read-only
     DESCRIPTION "agent provides read only access"

    -- hrDeviceStatus reports unknown for: cpu. pnic either running/unknown.
    --               disk reports running, warning, down, unknown
    -- device error counters do not account for all failure cases
    
     VARIATION hrSWOSIndex
     ACCESS not-implemented
     DESCRIPTION "No operatingSystem entry exists in hrSWRunGroup hrSWRunTable"

     VARIATION  hrFSLastFullBackupDate
     ACCESS not-implemented
     DESCRIPTION "is not implemented"

     VARIATION  hrFSLastPartialBackupDate
     ACCESS not-implemented
     DESCRIPTION "is not implemented"
         
     VARIATION hrPrinterStatus
     ACCESS not-implemented
     DESCRIPTION "is not implemented"     

     VARIATION hrPrinterDetectedErrorState
     ACCESS not-implemented
     DESCRIPTION "is not implemented"          


     -- ********************* ************ ************ *************** ***
     -- RFC 4133
     SUPPORTS ENTITY-MIB
     INCLUDES { 
        entityPhysicalGroup,
        entityPhysical2Group,
        entityPhysical3Group,
        entityGeneralGroup
     }
     -- VARIATION entityNotificationsGroup  
     -- ACCESS not-implemented
     -- VARIATION entityMappingGroup
     -- ACCESS not-implemented

     -- ********************* ************ ************ *************** ***
     -- REVISION 200810150000Z
     SUPPORTS IEEE8021-BRIDGE-MIB
     INCLUDES { 
        ieee8021BridgeBaseBridgeGroup,
        ieee8021BridgeBasePortGroup,
        ieee8021BridgeTpPortGroup
     }

     -- ********************* ************ ************ *************** ***
     -- REVISION 200810150000Z
     -- virtual switch uplinks (physical ports) do perform do mac learning and will
     -- not report in FDB/forwarding tables
     SUPPORTS IEEE8021-Q-BRIDGE-MIB
     INCLUDES { 
        ieee8021QBridgeBaseGroup,
        ieee8021QBridgeVlanGroup,
        ieee8021QBridgeVlanStaticGroup,
        ieee8021QBridgePortGroup2,
        ieee8021QBridgeFdbUnicastGroup,
        ieee8021QBridgeFdbMulticastGroup,
        ieee8021QBridgeFdbStaticGroup,
        ieee8021QBridgeVlanStatisticsGroup
     }
     -- VARATION ieee8021QBridgeVlanCurrentUntaggedPorts
     -- Reports count of 0 if only untagged vlan access (vid 0) is defined
     
     -- ********************* ************ ************ *************** ***
     -- REVISION 200706200000Z
     -- VDS link aggregations are not reported this release, issue PR 859941
     -- only VSS, traditional vswitch, nic teams are reported entries
     SUPPORTS IEEE8023-LAG-MIB
     INCLUDES { 
        dot3adAggGroup,
        dot3adAggPortGroup,
        dot3adTablesLastChangedGroup,
        dot3adAggPortListGroup
     }

     -- ********************* ************ ************ *************** ***
     -- REVISION 200906080000Z
     SUPPORTS LLDP-V2-MIB
     INCLUDES { 
        lldpV2ConfigGroup,
        lldpV2ConfigTxGroup,
        lldpV2StatsTxGroup,
        lldpV2LocSysGroup,
        lldpV2ConfigRxGroup, 
        lldpV2StatsRxGroup,
        lldpV2RemSysGroup,
        lldpV2NotificationsGroup
     }

     -- ********************* ************ ************ *************** ***
     -- REVISION 201008020000Z 
     SUPPORTS VMWARE-SYSTEM-MIB
     INCLUDES {
         vmwSystemGroup
     }
     -- REVISION 200810150000Z
     SUPPORTS VMWARE-RESOURCES-MIB
     INCLUDES {
         vmwResourceGroup
     }
     -- REVISION 201006220000Z 
     SUPPORTS VMWARE-VMINFO-MIB
     INCLUDES {
         vmwVmInfoGroup,
         vmwVmInfoNotificationGroup
     }
     -- VARIATION vmwVmNetConnType
     -- DESCRIPTION "This object was valid for ESX 2.5 systems only. Only value returned was 'monitor_dev'"
     -- STATUS deprecated

     -- REVISION 201005120000Z
     SUPPORTS VMWARE-ENV-MIB
     INCLUDES {
         vmwEnvAlertGroup,
         vmwESXEnvNotificationGroup2 
     }

     -- REVISION 201008200000Z
     SUPPORTS VMWARE-CIMOM-MIB
     INCLUDES {
        vmwCimOmNotificationGroup
     }
     
   ::= { vmwEsxCapability 5 }

--
-- ESX 5.1 and follow up patch releases
--

vmwESX51x AGENT-CAPABILITIES 
  PRODUCT-RELEASE 
     "5.1.x"  
  STATUS  current
  DESCRIPTION
     "Release 5.1.x for VMware ESXi supports SNMPv1, SNMPv2c, and SNMPv3 with a stand-alone snmpd process. 
      This agent supports read-only protocol operations. This implies that configuring the SNMPv3 Agent 
      can not be done via SET operations. Hence IETF standard SNMPv3 agent configuration mibs are not provided.
      SNMPv3 protocol is fully supported once configured via the CLI command interface (esxcli system snmp) 
      command set or host profiles. Lastly this SNMP agent provides one read-only view of 
      the entire system to which all SNMPv3 users configured are assigned.
     "
  REFERENCE 
     "http://www.vmware.com/products"

     -- RFC 3418
     SUPPORTS SNMPv2-MIB
     INCLUDES { 
         snmpGroup, 
         systemGroup,
         snmpCommunityGroup,
         snmpBasicNotificationsGroup,
         snmpWarmStartNotificationGroup
         -- groups not supported; snmpSetGroup, snmpNotificationGroup
     }

     VARIATION snmpSetSerialNo
     ACCESS  not-implemented
     DESCRIPTION "Agent provides read-only view of system information."

     VARIATION snmpTrapOID
     ACCESS not-implemented
     DESCRIPTION "Agent does not proxy other agents RFC1157 Trap-PDUs."

     VARIATION  snmpTrapEnterprise
     ACCESS not-implemented
     DESCRIPTION "Agent does not proxy other agents RFC1157 Trap-PDUs."

     VARIATION snmpEnableAuthenTraps
     SYNTAX INTEGER { disabled(2) }
     ACCESS read-only
     DESCRIPTION "Agent does not allow authentication traps. Poll snmpInBadCommunityNames for same info."
     -- the above clause implies this:
     -- VARIATION authenticationFailure
     -- ACCESS not-implemented
     -- DESCRIPTION "Agent does not provide this notification. snmpEnableAuthenTraps will return disabled."


     -- ********************* ************ ************ *************** ***
     -- RFC 2863
     SUPPORTS IF-MIB
     INCLUDES { 
         ifGeneralInformationGroup,
         linkUpDownNotificationsGroup
     }

     VARIATION ifAdminStatus
     ACCESS read-only
     DESCRIPTION "Agent provides read-only view of administrative state for each physical interface.
                  ESX virtual switches support changing administrative state 
                  of physical network interfaces (nics) up or down. For example the command:
                  esxcli network nic [up|down] -n vmnic0 
                  Virtual vmware interfaces (ifType 238) also support changing administratie state:
                  network ip interface set --enabled [yes|no] -i vmk0
                 "

     VARIATION ifLinkUpDownTrapEnable
     ACCESS read-only
     DESCRIPTION "Agent provides read-only view of system information."

     VARIATION ifAlias
     ACCESS read-only
     DESCRIPTION "ifIndexes may only change across reboot."

     VARIATION ifInUnknownProtos
     ACCESS not-implemented
     DESCRIPTION "This counter always returns 0."

     -- ifRcvAddressGroup is interface/media specific 
     VARIATION ifRcvAddressStatus
     ACCESS not-implemented
     DESCRIPTION "Required if media specific mib modules are implemented."

     VARIATION ifRcvAddressType 
     ACCESS not-implemented
     DESCRIPTION "Required if media specific mib modules are implemented."

     -- ********************* ************ ************ *************** ***
     -- RFC 4293
     SUPPORTS IP-MIB
     INCLUDES { 
         ipSystemStatsGroup,   
         ipAddressGroup,
         ipNetToPhysicalGroup, 
         ipDefaultRouterGroup,
         icmpStatsGroup,
         ipSystemStatsHCOctetGroup,
         ipSystemStatsHCPacketGroup,
         ipv4GeneralGroup,
         ipv4IfGroup,
         ipv4SystemStatsGroup,
         ipv4SystemStatsHCPacketGroup,
         ipv6GeneralGroup2,
         ipv6IfGroup,
         ipAddressPrefixGroup,
         ipv6RouterAdvertGroup,
         ipLastChangeGroup
     }
     -- VARIATION ipv6ScopeGroup
     -- ACCESS  not-implemented

     -- ********************* ************ ************ *************** ***
     -- RFC 4292
     SUPPORTS IP-FORWARD-MIB
     INCLUDES { 
         inetForwardCidrRouteGroup          
     }

     -- ********************* ************ ************ *************** ***
     -- RFC 4113
     SUPPORTS UDP-MIB
     -- The next two 32 bit counters will be fixed per bug report PR 890894
     -- VARIATION udpInDatagrams
     -- ACCESS not-implemented, use udpHCInDatagrams
     -- VARIATION udpOutDatagrams
     -- ACCESS not-implemented, use udpHCOutDatagrams
     INCLUDES { 
        udpBaseGroup, 
        udpEndpointGroup
     }

     -- ********************* ************ ************ *************** ***
     -- RFC 4022
     SUPPORTS TCP-MIB
     INCLUDES { 
         tcpBaseGroup, 
         tcpConnectionGroup,
         tcpListenerGroup
     }

     -- RFC 2790
     -- NOTE: For storage larger than Integer32 (Terabyte) this agent will report INT_MAX
     SUPPORTS HOST-RESOURCES-MIB
     INCLUDES { 
            hrSystemGroup,
            hrStorageGroup, -- visorfs "ramdisks" are not reported
            hrDeviceGroup,
            hrSWRunGroup,
            hrSWRunPerfGroup,
            hrSWInstalledGroup  -- updates once an hour
     }

     VARIATION  hrSystemNumUsers 
     ACCESS read-only
     DESCRIPTION "Value reports number of active ESX Shell sessions"

     VARIATION  hrSWRunName
     ACCESS read-only
     DESCRIPTION "Value does not match hrSWInstalledName"

     VARIATION  hrSystemDate
     ACCESS read-only
     DESCRIPTION "agent provides read only access"

     VARIATION hrSystemInitialLoadDevice 
     ACCESS read-only
     DESCRIPTION "agent provides read only access"

     VARIATION hrSystemInitialLoadParameters
     ACCESS read-only
     DESCRIPTION "agent provides read only access"

     VARIATION hrStorageSize 
     ACCESS read-only
     DESCRIPTION "agent provides read only access"

     VARIATION  hrSWRunStatus
     ACCESS read-only
     DESCRIPTION "agent provides read only access"

    -- hrDeviceStatus reports unknown for: cpu. pnic either running/unknown.
    --               disk reports running, warning, down, unknown
    -- device error counters do not account for all failure cases
    
     VARIATION hrSWOSIndex
     ACCESS not-implemented
     DESCRIPTION "No operatingSystem entry exists in hrSWRunGroup hrSWRunTable"

     VARIATION  hrFSLastFullBackupDate
     ACCESS not-implemented
     DESCRIPTION "is not implemented"

     VARIATION  hrFSLastPartialBackupDate
     ACCESS not-implemented
     DESCRIPTION "is not implemented"
         
     VARIATION hrPrinterStatus
     ACCESS not-implemented
     DESCRIPTION "is not implemented"     

     VARIATION hrPrinterDetectedErrorState
     ACCESS not-implemented
     DESCRIPTION "is not implemented"          


     -- ********************* ************ ************ *************** ***
     -- RFC 4133
     SUPPORTS ENTITY-MIB
     INCLUDES { 
        entityPhysicalGroup,
        entityPhysical2Group,
        entityPhysical3Group,
        entityGeneralGroup
     }
     -- VARIATION entityNotificationsGroup  
     -- ACCESS not-implemented
     -- VARIATION entityMappingGroup
     -- ACCESS not-implemented

     -- ********************* ************ ************ *************** ***
     -- REVISION 200810150000Z
     SUPPORTS IEEE8021-BRIDGE-MIB
     INCLUDES { 
        ieee8021BridgeBaseBridgeGroup,
        ieee8021BridgeBasePortGroup,
        ieee8021BridgeTpPortGroup
     }

     -- ********************* ************ ************ *************** ***
     -- REVISION 200810150000Z
     -- virtual switch uplinks (physical ports) do perform do mac learning and will
     -- not report in FDB/forwarding tables
     SUPPORTS IEEE8021-Q-BRIDGE-MIB
     INCLUDES { 
        ieee8021QBridgeBaseGroup,
        ieee8021QBridgeVlanGroup,
        ieee8021QBridgeVlanStaticGroup,
        ieee8021QBridgePortGroup2,
        ieee8021QBridgeFdbUnicastGroup,
        ieee8021QBridgeFdbMulticastGroup,
        ieee8021QBridgeFdbStaticGroup,
        ieee8021QBridgeVlanStatisticsGroup
     }
     -- VARATION ieee8021QBridgeVlanCurrentUntaggedPorts
     -- Reports count of 0 if only untagged vlan access (vid 0) is defined
     
     -- ********************* ************ ************ *************** ***
     -- REVISION 200706200000Z
     -- VDS link aggregations are not reported this release, issue PR 859941
     -- only VSS, traditional vswitch, nic teams are reported entries
     SUPPORTS IEEE8023-LAG-MIB
     INCLUDES { 
        dot3adAggGroup,
        dot3adAggPortGroup,
        dot3adTablesLastChangedGroup,
        dot3adAggPortListGroup
     }

     -- ********************* ************ ************ *************** ***
     -- REVISION 200906080000Z
     SUPPORTS LLDP-V2-MIB
     INCLUDES { 
        lldpV2ConfigGroup,
        lldpV2ConfigTxGroup,
        lldpV2StatsTxGroup,
        lldpV2LocSysGroup,
        lldpV2ConfigRxGroup, 
        lldpV2StatsRxGroup,
        lldpV2RemSysGroup,
        lldpV2NotificationsGroup
     }

     -- ********************* ************ ************ *************** ***
     -- REVISION 201008020000Z 
     SUPPORTS VMWARE-SYSTEM-MIB
     INCLUDES {
         vmwSystemGroup
     }
     -- REVISION 200810150000Z
     SUPPORTS VMWARE-RESOURCES-MIB
     INCLUDES {
         vmwResourceGroup
     }
     -- REVISION 201006220000Z 
     SUPPORTS VMWARE-VMINFO-MIB
     INCLUDES {
         vmwVmInfoGroup,
         vmwVmInfoNotificationGroup
     }
     -- VARIATION vmwVmNetConnType
     -- DESCRIPTION "This object was valid for ESX 2.5 systems only. Only value returned was 'monitor_dev'"
     -- STATUS deprecated

     -- REVISION 201005120000Z
     SUPPORTS VMWARE-ENV-MIB
     INCLUDES {
         vmwEnvAlertGroup,
         vmwESXEnvNotificationGroup2 
     }

     -- REVISION 201008200000Z
     SUPPORTS VMWARE-CIMOM-MIB
     INCLUDES {
        vmwCimOmNotificationGroup
     }
     
   ::= { vmwEsxCapability 4 }


vmwESX50x AGENT-CAPABILITIES 
  PRODUCT-RELEASE 
     "5.0.x"
  STATUS  current
  DESCRIPTION
     "Release 5.0.x for VMware ESXi. The SNMPv1/v2c agent is a subsystem in the hostd process"
  REFERENCE 
     "http://www.vmware.com/products"

     -- RFC 3418
     SUPPORTS SNMPv2-MIB
     INCLUDES { 
         snmpGroup, 
         systemGroup,
         snmpCommunityGroup,
         snmpBasicNotificationsGroup,
         snmpWarmStartNotificationGroup
         -- groups not supported; snmpSetGroup, snmpNotificationGroup
     }

     VARIATION snmpSetSerialNo
     ACCESS  not-implemented
     DESCRIPTION "Agent provides read-only view of system information."

     VARIATION snmpTrapOID
     ACCESS not-implemented
     DESCRIPTION "Agent does not proxy other agents RFC1157 Trap-PDUs."

     VARIATION  snmpTrapEnterprise
     ACCESS not-implemented
     DESCRIPTION "Agent does not proxy other agents RFC1157 Trap-PDUs."

     VARIATION snmpEnableAuthenTraps
     SYNTAX INTEGER { disabled(2) }
     ACCESS read-only
     DESCRIPTION "Agent does not allow authentication traps. Poll snmpInBadCommunityNames for same info."
     -- the above implies this:
     -- VARIATION authenticationFailure
     -- ACCESS not-implemented
     -- DESCRIPTION "Agent does not provide this notification. snmpEnableAuthenTraps will return disabled."


     -- ********************* ************ ************ *************** ***
     -- RFC 2863
     SUPPORTS IF-MIB
     INCLUDES { 
         ifGeneralInformationGroup,
         linkUpDownNotificationsGroup
     }

     VARIATION ifAdminStatus
     ACCESS read-only
     DESCRIPTION "Agent provides read-only view of administrative state for each physical interface.
                  Note: ESX virtual switches now may support changing administrative state 
                  of physical network interfaces (nics) up or down."

     VARIATION ifLinkUpDownTrapEnable
     ACCESS read-only
     DESCRIPTION "Agent provides read-only view of system information."

     VARIATION ifAlias
     ACCESS read-only
     DESCRIPTION "ifIndexes may only change across reboot."

     VARIATION ifInUnknownProtos
     ACCESS not-implemented
     DESCRIPTION "This counter always returns 0."

     -- ifRcvAddressGroup is interface/media specific 
     VARIATION ifRcvAddressStatus
     ACCESS not-implemented
     DESCRIPTION "Required if media specific mib modules are implemented."

     VARIATION ifRcvAddressType 
     ACCESS not-implemented
     DESCRIPTION "Required if media specific mib modules are implemented."

     -- RFC 2790
     SUPPORTS HOST-RESOURCES-MIB
     INCLUDES { 
            hrSystemGroup,
            hrStorageGroup, -- visorfs "ramdisks" are not reported
            hrDeviceGroup,
            hrSWRunGroup,
            hrSWRunPerfGroup,
            hrSWInstalledGroup  -- updates once an hour
     }

     VARIATION  hrSystemNumUsers 
     ACCESS read-only
     DESCRIPTION "Value reports number of active login sessions in host agent (hostd)"

     VARIATION  hrSWRunName
     ACCESS read-only
     DESCRIPTION "Value does not match hrSWInstalledName"

     VARIATION hrDeviceErrors
     ACCESS not-implemented
     DESCRIPTION "ESXi pcpu, network interface cards, do not provide error stats"

    -- hrDeviceStatus reports unknown for: cpu. pnic either running/unknown.
    --               disk reports running, warning, down, unknown
    -- device error counters do not account for all failure cases
    
     VARIATION hrSWOSIndex
     ACCESS not-implemented
     DESCRIPTION "No operatingSystem entry exists in hrSWRunGroup hrSWRunTable"

     VARIATION  hrFSLastFullBackupDate
     ACCESS not-implemented
     DESCRIPTION "is not implemented"

     VARIATION  hrFSLastPartialBackupDate
     ACCESS not-implemented
     DESCRIPTION "is not implemented"
         
     VARIATION hrPrinterStatus
     ACCESS not-implemented
     DESCRIPTION "is not implemented"     

     VARIATION hrPrinterDetectedErrorState
     ACCESS not-implemented
     DESCRIPTION "is not implemented"          

     VARIATION  hrSystemDate
     ACCESS read-only
     DESCRIPTION "agent provides read only access"

     VARIATION hrSystemInitialLoadDevice 
     ACCESS read-only
     DESCRIPTION "agent provides read only access"

     VARIATION hrSystemInitialLoadParameters
     ACCESS read-only
     DESCRIPTION "agent provides read only access"

     VARIATION hrStorageSize 
     ACCESS read-only
     DESCRIPTION "agent provides read only access"

     VARIATION  hrSWRunStatus
     ACCESS read-only
     DESCRIPTION "agent provides read only access"
               
     -- ********************* ************ ************ *************** ***

     -- REVISION 201008020000Z 
     SUPPORTS VMWARE-SYSTEM-MIB
     INCLUDES {
         vmwSystemGroup
     }
     -- REVISION 200810150000Z
     SUPPORTS VMWARE-RESOURCES-MIB
     INCLUDES {
         vmwResourceGroup
     }
     -- REVISION 201006220000Z 
     SUPPORTS VMWARE-VMINFO-MIB
     INCLUDES {
         vmwVmInfoGroup,
         vmwVmInfoNotificationGroup
     }
     -- VARIATION vmwVmNetConnType
     -- DESCRIPTION "This object was valid for ESX 2.5 systems only. Only value returned was 'monitor_dev'"
     -- STATUS deprecated

     -- REVISION 201005120000Z
     SUPPORTS VMWARE-ENV-MIB
     INCLUDES {
         vmwEnvNotificationGroup
     }

   ::= { vmwEsxCapability 3 }


-- 
--
--

vmwESX41x AGENT-CAPABILITIES 
  PRODUCT-RELEASE 
     "4.1.x"
  STATUS  current
  DESCRIPTION
     "Release 4.1.x for VMware ESX, the SNMP agent is now a subsystem in the hostd process on ESXi."
  REFERENCE 
     "http://www.vmware.com/products"

     -- RFC 3418
     SUPPORTS SNMPv2-MIB
     INCLUDES { 
         snmpGroup, 
         systemGroup,
         snmpCommunityGroup,
         snmpBasicNotificationsGroup,
         snmpWarmStartNotificationGroup
         -- groups not supported; snmpSetGroup, snmpNotificationGroup
     }

     VARIATION snmpSetSerialNo
     ACCESS  not-implemented
     DESCRIPTION "Agent provides read-only view of system information."

     VARIATION snmpTrapOID
     ACCESS not-implemented
     DESCRIPTION "Agent does not proxy other agents RFC1157 Trap-PDUs."

     VARIATION  snmpTrapEnterprise
     ACCESS not-implemented
     DESCRIPTION "Agent does not proxy other agents RFC1157 Trap-PDUs."

     VARIATION snmpEnableAuthenTraps
     SYNTAX INTEGER { disabled(2) }
     ACCESS read-only
     DESCRIPTION "Agent does not allow authentication traps. Poll snmpInBadCommunityNames for same info."
     -- the above implies this:
     -- VARIATION authenticationFailure
     -- ACCESS not-implemented
     -- DESCRIPTION "Agent does not provide this notification. snmpEnableAuthenTraps will return disabled."


     -- ********************* ************ ************ *************** ***
     -- RFC 2863
     SUPPORTS IF-MIB
     INCLUDES { 
         ifGeneralInformationGroup,
         linkUpDownNotificationsGroup
     }

     VARIATION ifAdminStatus
     ACCESS read-only
     DESCRIPTION "Agent provides read-only view of administrative state for each interface.
                  ESX virtual layer 2 switches may support changing administrative state 
                  of physical network interfaces (nics)."

     VARIATION ifLinkUpDownTrapEnable
     ACCESS read-only
     DESCRIPTION "Agent provides read-only view of system information."

     VARIATION ifAlias
     ACCESS read-only
     DESCRIPTION "ifIndexes may only change across reboot."

     VARIATION ifInUnknownProtos
     ACCESS not-implemented
     DESCRIPTION "This counter always returns 0."

     -- ifRcvAddressGroup is interface/media specific 
     VARIATION ifRcvAddressStatus
     ACCESS not-implemented
     DESCRIPTION "Required if media specific mib modules are implemented."

     VARIATION ifRcvAddressType 
     ACCESS not-implemented
     DESCRIPTION "Required if media specific mib modules are implemented."

     -- ********************* ************ ************ *************** ***

     -- REVISION 200712270000Z
     SUPPORTS VMWARE-SYSTEM-MIB
     INCLUDES {
         vmwSystemGroup
     }
     -- REVISION 200810150000Z
     SUPPORTS VMWARE-RESOURCES-MIB
     INCLUDES {
         vmwResourceGroup
     }
     -- REVISION 200810230000Z
     SUPPORTS VMWARE-VMINFO-MIB
     INCLUDES {
         vmwVmInfoGroup,
         vmwVmInfoNotificationGroup
     }
     -- VARIATION vmwVmNetConnType
     -- DESCRIPTION "This object was valid for ESX 2.5 systems only. Only value returned was 'monitor_dev'"
     -- STATUS deprecated

     -- REVISION 200712270000Z
     SUPPORTS VMWARE-ENV-MIB
     INCLUDES {
         vmwEnvNotificationGroup
     }

   ::= { vmwEsxCapability 2 }

-- 
--
--

vmwESX40x AGENT-CAPABILITIES 
  PRODUCT-RELEASE 
     "4.0.x"
  STATUS  current
  DESCRIPTION
     "Release 4.0.x for VMware ESX. The SNMP agent is now part of the hostd process"
  REFERENCE 
     "http://www.vmware.com/products"

     -- RFC 3418
     SUPPORTS SNMPv2-MIB
     INCLUDES { 
         snmpGroup, 
         systemGroup,
         snmpCommunityGroup,
         snmpBasicNotificationsGroup,
         snmpWarmStartNotificationGroup
         -- groups not supported; snmpSetGroup, snmpNotificationGroup
     }

     VARIATION snmpSetSerialNo
     ACCESS  not-implemented
     DESCRIPTION "Agent provides read-only view of system information."

     VARIATION snmpTrapOID
     ACCESS not-implemented
     DESCRIPTION "Agent does not proxy other agents RFC1157 Trap-PDUs."

     VARIATION  snmpTrapEnterprise
     ACCESS not-implemented
     DESCRIPTION "Agent does not proxy other agents RFC1157 Trap-PDUs."

     VARIATION snmpEnableAuthenTraps
     SYNTAX INTEGER { disabled(2) }
     ACCESS read-only
     DESCRIPTION "Agent does not allow authentication traps. Poll snmpInBadCommunityNames for same info."
     -- the above implies this:
     -- VARIATION authenticationFailure
     -- ACCESS not-implemented
     -- DESCRIPTION "Agent does not provide this notification. snmpEnableAuthenTraps will return disabled."


     -- ********************* ************ ************ *************** ***
     -- RFC 2863
     SUPPORTS IF-MIB
     INCLUDES { 
         ifGeneralInformationGroup,
         linkUpDownNotificationsGroup
     }

     VARIATION ifAdminStatus
     SYNTAX INTEGER { up(1) }
     ACCESS read-only
     DESCRIPTION "Agent provides read-only view of system information and
                  does not support changing operational state."

     VARIATION ifLinkUpDownTrapEnable
     ACCESS read-only
     DESCRIPTION "Agent provides read-only view of system information."

     -- ifXTable not implemented
     VARIATION ifTableLastChange
     ACCESS not-implemented
     DESCRIPTION "post RFC 1213 managed objects not implemented."

     VARIATION ifConnectorPresent
     ACCESS not-implemented
     DESCRIPTION "ifXTable not implemented."

     VARIATION ifHighSpeed
     ACCESS not-implemented
     DESCRIPTION "ifXTable not implemented."

     VARIATION ifName
     ACCESS not-implemented
     DESCRIPTION "ifXTable not implemented."

     VARIATION ifAlias
     ACCESS not-implemented
     DESCRIPTION "ifXTable not implemented."

     -- ifFixedLengthGroup
     VARIATION ifAlias
     ACCESS not-implemented
     DESCRIPTION "Performance counters not implemented."

     VARIATION ifHCInOctets
     ACCESS not-implemented
     DESCRIPTION "Performance counters not implemented."

     VARIATION ifHCOutOctets
     ACCESS not-implemented
     DESCRIPTION "Performance counters not implemented."

     VARIATION ifInOctets
     ACCESS not-implemented
     DESCRIPTION "Performance counters not implemented."

     VARIATION ifOutOctets
     ACCESS not-implemented
     DESCRIPTION "Performance counters not implemented."

     VARIATION ifInUnknownProtos
     ACCESS not-implemented
     DESCRIPTION "Performance counters not implemented."

     VARIATION ifInErrors
     ACCESS not-implemented
     DESCRIPTION "Performance counters not implemented."

     VARIATION ifOutErrors
     ACCESS not-implemented
     DESCRIPTION "Performance counters not implemented."

     -- ifHCFixedLengthGroup
     VARIATION ifHCInOctets
     ACCESS not-implemented
     DESCRIPTION "Performance counters not implemented."

     VARIATION ifHCOutOctets
     ACCESS not-implemented
     DESCRIPTION "Performance counters not implemented."

     VARIATION ifInOctets
     ACCESS not-implemented
     DESCRIPTION "Performance counters not implemented."

     VARIATION ifOutOctets
     ACCESS not-implemented
     DESCRIPTION "Performance counters not implemented."

     VARIATION ifInUnknownProtos
     ACCESS not-implemented
     DESCRIPTION "Performance counters not implemented."

     VARIATION ifInErrors
     ACCESS not-implemented
     DESCRIPTION "Performance counters not implemented."

     VARIATION ifOutErrors
     ACCESS not-implemented
     DESCRIPTION "Performance counters not implemented."

     -- ifPacketGroup
     VARIATION ifInOctets
     ACCESS not-implemented
     DESCRIPTION "Performance counters not implemented."

     VARIATION ifOutOctets
     ACCESS not-implemented
     DESCRIPTION "Performance counters not implemented."

     VARIATION ifInUnknownProtos
     ACCESS not-implemented
     DESCRIPTION "Performance counters not implemented."

     VARIATION ifInErrors
     ACCESS not-implemented
     DESCRIPTION "Performance counters not implemented."

     VARIATION ifOutErrors
     ACCESS not-implemented
     DESCRIPTION "Performance counters not implemented."

     VARIATION ifMtu
     ACCESS not-implemented
     DESCRIPTION "Performance counters not implemented."

     VARIATION ifInUcastPkts
     ACCESS not-implemented
     DESCRIPTION "Performance counters not implemented."

     VARIATION ifInMulticastPkts
     ACCESS not-implemented
     DESCRIPTION "Performance counters not implemented."

     VARIATION ifInBroadcastPkts
     ACCESS not-implemented
     DESCRIPTION "Performance counters not implemented."

     VARIATION ifInDiscards
     ACCESS not-implemented
     DESCRIPTION "Performance counters not implemented."

     VARIATION ifOutUcastPkts
     ACCESS not-implemented
     DESCRIPTION "Performance counters not implemented."

     VARIATION ifOutMulticastPkts
     ACCESS not-implemented
     DESCRIPTION "Performance counters not implemented."

     VARIATION ifOutBroadcastPkts
     ACCESS not-implemented
     DESCRIPTION "Performance counters not implemented."

     VARIATION ifOutDiscards
     ACCESS not-implemented
     DESCRIPTION "Performance counters not implemented."

     VARIATION ifPromiscuousMode 
     ACCESS not-implemented
     DESCRIPTION "Performance counters not implemented."


     -- ifHCPacketGroup
     VARIATION ifInOctets
     ACCESS not-implemented
     DESCRIPTION "Performance counters not implemented."

     VARIATION ifOutOctets
     ACCESS not-implemented
     DESCRIPTION "Performance counters not implemented."

     VARIATION ifInUnknownProtos
     ACCESS not-implemented
     DESCRIPTION "Performance counters not implemented."

     VARIATION ifInErrors
     ACCESS not-implemented
     DESCRIPTION "Performance counters not implemented."

     VARIATION ifOutErrors
     ACCESS not-implemented
     DESCRIPTION "Performance counters not implemented."

     VARIATION ifMtu
     ACCESS not-implemented
     DESCRIPTION "Performance counters not implemented."

     VARIATION ifInUcastPkts
     ACCESS not-implemented
     DESCRIPTION "Performance counters not implemented."

     VARIATION ifInMulticastPkts
     ACCESS not-implemented
     DESCRIPTION "Performance counters not implemented."

     VARIATION ifInBroadcastPkts
     ACCESS not-implemented
     DESCRIPTION "Performance counters not implemented."

     VARIATION ifInDiscards
     ACCESS not-implemented
     DESCRIPTION "Performance counters not implemented."

     VARIATION ifOutUcastPkts
     ACCESS not-implemented
     DESCRIPTION "Performance counters not implemented."

     VARIATION ifOutMulticastPkts
     ACCESS not-implemented
     DESCRIPTION "Performance counters not implemented."

     VARIATION ifOutBroadcastPkts
     ACCESS not-implemented
     DESCRIPTION "Performance counters not implemented."

     VARIATION ifOutDiscards
     ACCESS not-implemented
     DESCRIPTION "Performance counters not implemented."

     VARIATION ifPromiscuousMode
     ACCESS not-implemented
     DESCRIPTION "Performance counters not implemented."

     -- ifVHCPacketGroup
     VARIATION ifHCInUcastPkts
     ACCESS not-implemented
     DESCRIPTION "Performance counters not implemented."

     VARIATION ifHCInMulticastPkts
     ACCESS not-implemented
     DESCRIPTION "Performance counters not implemented."

     VARIATION ifHCInBroadcastPkts
     ACCESS not-implemented
     DESCRIPTION "Performance counters not implemented."

     VARIATION ifHCOutUcastPkts
     ACCESS not-implemented
     DESCRIPTION "Performance counters not implemented."

     VARIATION ifHCOutMulticastPkts
     ACCESS not-implemented
     DESCRIPTION "Performance counters not implemented."

     VARIATION ifHCOutBroadcastPkts
     ACCESS not-implemented
     DESCRIPTION "Performance counters not implemented."

     VARIATION ifHCInOctets
     ACCESS not-implemented
     DESCRIPTION "Performance counters not implemented."

     VARIATION ifHCOutOctets
     ACCESS not-implemented
     DESCRIPTION "Performance counters not implemented."

     VARIATION ifInOctets
     ACCESS not-implemented
     DESCRIPTION "Performance counters not implemented."

     VARIATION ifOutOctets
     ACCESS not-implemented
     DESCRIPTION "Performance counters not implemented."

     VARIATION ifInUnknownProtos
     ACCESS not-implemented
     DESCRIPTION "Performance counters not implemented."

     VARIATION ifInErrors
     ACCESS not-implemented
     DESCRIPTION "Performance counters not implemented."

     VARIATION ifOutErrors
     ACCESS not-implemented
     DESCRIPTION "Performance counters not implemented."

     VARIATION ifMtu
     ACCESS not-implemented
     DESCRIPTION "Performance counters not implemented."

     VARIATION ifInUcastPkts
     ACCESS not-implemented
     DESCRIPTION "Performance counters not implemented."

     VARIATION ifInMulticastPkts
     ACCESS not-implemented
     DESCRIPTION "Performance counters not implemented."

     VARIATION ifInBroadcastPkts
     ACCESS not-implemented
     DESCRIPTION "Performance counters not implemented."

     VARIATION ifInDiscards
     ACCESS not-implemented
     DESCRIPTION "Performance counters not implemented."

     VARIATION ifOutUcastPkts
     ACCESS not-implemented
     DESCRIPTION "Performance counters not implemented."

     VARIATION ifOutMulticastPkts
     ACCESS not-implemented
     DESCRIPTION "Performance counters not implemented."

     VARIATION ifOutBroadcastPkts
     ACCESS not-implemented
     DESCRIPTION "Performance counters not implemented."

     VARIATION ifOutDiscards
     ACCESS not-implemented
     DESCRIPTION "Performance counters not implemented."

     VARIATION ifPromiscuousMode
     ACCESS not-implemented
     DESCRIPTION "Performance counters not implemented."

     -- ifCounterDiscontinuityGroup
     VARIATION ifCounterDiscontinuityTime
     ACCESS not-implemented
     DESCRIPTION "Required if Performance counters are implemented."

     -- ifRcvAddressGroup is interface/media specific 
     VARIATION ifRcvAddressStatus
     ACCESS not-implemented
     DESCRIPTION "Required if media specific mib modules are implemented."

     VARIATION ifRcvAddressType 
     ACCESS not-implemented
     DESCRIPTION "Required if media specific mib modules are implemented."


     -- ********************* ************ ************ *************** ***

     -- REVISION 200712270000Z
     SUPPORTS VMWARE-SYSTEM-MIB
     INCLUDES {
         vmwSystemGroup
     }
     -- REVISION 200810150000Z
     SUPPORTS VMWARE-RESOURCES-MIB
     INCLUDES {
         vmwResourceGroup
     }
     -- REVISION 200810230000Z
     SUPPORTS VMWARE-VMINFO-MIB
     INCLUDES {
         vmwVmInfoGroup,
         vmwVmInfoNotificationGroup
     }
     -- VARIATION vmwVmNetConnType
     -- DESCRIPTION "This object was valid for ESX 2.5 systems only. Only value returned was 'monitor_dev'"
     -- STATUS deprecated

     -- REVISION 200712270000Z
     SUPPORTS VMWARE-ENV-MIB
     INCLUDES {
         vmwEnvNotificationGroup
     }

   ::= { vmwEsxCapability 1 }

END
