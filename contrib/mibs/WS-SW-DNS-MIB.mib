-- vim: syntax=mib
--
-- WS-SW-DNS-MIB.my
-- MIB generated by MG-SOFT Visual MIB Builder Version 6.0  Build 88
-- Wednesday, May 24, 2006 at 16:52:00
--

	WS-SW-DNS-MIB DEFINITIONS ::= BEGIN

		IMPORTS
			OBJECT-GROUP, MODULE-COMPLIANCE
				FROM SNMPv2-CONF
			IpAddress, OBJECT-TYPE, MODULE-IDENTITY
				FROM SNMPv2-SMI
			DisplayString, TruthValue, RowStatus
				FROM SNMPv2-TC
			wsSwDNS
				FROM WS-SW-SMI;


		-- 1.3.6.1.4.1.388.14.2.2.1
		wsSwDNSModule MODULE-IDENTITY
			LAST-UPDATED "200505051121Z"		-- May 05, 2005 at 11:21 GMT
			ORGANIZATION
				"Symbol Technologies"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"ws switchin DNS module"
			REVISION "200605241651Z"		-- May 24, 2006 at 16:51 GMT
			DESCRIPTION
				"01a08"
			REVISION "200601131109Z"		-- January 13, 2006 at 11:09 GMT
			DESCRIPTION
				"01a07"
			REVISION "200509221402Z"		-- September 22, 2005 at 14:02 GMT
			DESCRIPTION
				"01a06"
			REVISION "200505191442Z"		-- May 19, 2005 at 14:42 GMT
			DESCRIPTION
				"01a05"
			REVISION "200505181426Z"		-- May 18, 2005 at 14:26 GMT
			DESCRIPTION
				"01a04"
			REVISION "200505111033Z"		-- May 11, 2005 at 10:33 GMT
			DESCRIPTION
				"01a03"
			REVISION "200505101552Z"		-- May 10, 2005 at 15:52 GMT
			DESCRIPTION
				"01a02"
			REVISION "200505051207Z"		-- May 05, 2005 at 12:07 GMT
			DESCRIPTION
				"01a01"
			::= { wsSwDNS 1 }




--
-- Node definitions
--

		-- 1.3.6.1.4.1.388.14.2.2.1.1
		wsSwDNSDomainName OBJECT IDENTIFIER ::= { wsSwDNSModule 1 }


		-- 1.3.6.1.4.1.388.14.2.2.1.1.1
		wsSwDNSDomainNameStatic OBJECT-TYPE
			SYNTAX DisplayString (SIZE (0..80))
			MAX-ACCESS read-write
			STATUS current
			DESCRIPTION
				"static domain name"
			::= { wsSwDNSDomainName 1 }


		-- 1.3.6.1.4.1.388.14.2.2.1.1.2
		wsSwDNSDomainNameLookup OBJECT-TYPE
			SYNTAX TruthValue
			MAX-ACCESS read-write
			STATUS current
			DESCRIPTION
				"enable/disable domain name lookup"
			::= { wsSwDNSDomainName 2 }


		-- 1.3.6.1.4.1.388.14.2.2.1.2
		wsSwDNSNameSvrTable OBJECT-TYPE
			SYNTAX SEQUENCE OF WsSwDNSNameSvrEntry
			MAX-ACCESS not-accessible
			STATUS current
			DESCRIPTION
				"static DNS table"
			::= { wsSwDNSModule 2 }


		-- 1.3.6.1.4.1.388.14.2.2.1.2.1
		wsSwDNSNameSvrEntry OBJECT-TYPE
			SYNTAX WsSwDNSNameSvrEntry
			MAX-ACCESS not-accessible
			STATUS current
			DESCRIPTION
				"static DNS table entry"
			INDEX { wsSwDNSNameSvrIP, wsSwDNSNameSvrType }
			::= { wsSwDNSNameSvrTable 1 }


		WsSwDNSNameSvrEntry ::=
			SEQUENCE {
				wsSwDNSNameSvrIP
					IpAddress,
				wsSwDNSNameSvrPriority
					INTEGER,
				wsSwDNSNameSvrType
					INTEGER,
				wsSwDNSNameSvrRowStatus
					RowStatus
			 }

		-- 1.3.6.1.4.1.388.14.2.2.1.2.1.1
		wsSwDNSNameSvrIP OBJECT-TYPE
			SYNTAX IpAddress
			MAX-ACCESS read-only
			STATUS current
			DESCRIPTION
				"DNS IP Address"
			::= { wsSwDNSNameSvrEntry 1 }


		-- 1.3.6.1.4.1.388.14.2.2.1.2.1.2
		wsSwDNSNameSvrPriority OBJECT-TYPE
			SYNTAX INTEGER (1..6)
			MAX-ACCESS read-only
			STATUS current
			DESCRIPTION
				"Description."
			::= { wsSwDNSNameSvrEntry 2 }


		-- 1.3.6.1.4.1.388.14.2.2.1.2.1.3
		wsSwDNSNameSvrType OBJECT-TYPE
			SYNTAX INTEGER
				{
				static(1),
				dynamic(2)
				}
			MAX-ACCESS read-only
			STATUS current
			DESCRIPTION
				"Description."
			::= { wsSwDNSNameSvrEntry 3 }


		-- 1.3.6.1.4.1.388.14.2.2.1.2.1.4
		wsSwDNSNameSvrRowStatus OBJECT-TYPE
			SYNTAX RowStatus
			MAX-ACCESS read-create
			STATUS current
			DESCRIPTION
				"static DNS row status"
			::= { wsSwDNSNameSvrEntry 4 }


		-- 1.3.6.1.4.1.388.14.2.2.1.100
		wsSwDNSComformance OBJECT IDENTIFIER ::= { wsSwDNSModule 100 }


		-- 1.3.6.1.4.1.388.14.2.2.1.100.1
		wsSwDNSCompliances OBJECT IDENTIFIER ::= { wsSwDNSComformance 1 }


		-- 1.3.6.1.4.1.388.14.2.2.1.100.1.1
		wsSwDNSCompliance MODULE-COMPLIANCE
			STATUS current
			DESCRIPTION
				"Description."
			MODULE -- this module
				MANDATORY-GROUPS { wsSwDNSGroup }
			::= { wsSwDNSCompliances 1 }


		-- 1.3.6.1.4.1.388.14.2.2.1.100.3
		wsSwDNSGroups OBJECT IDENTIFIER ::= { wsSwDNSComformance 3 }


		-- 1.3.6.1.4.1.388.14.2.2.1.100.3.1
		wsSwDNSGroup OBJECT-GROUP
			OBJECTS { wsSwDNSDomainNameStatic, wsSwDNSDomainNameLookup, wsSwDNSNameSvrPriority, wsSwDNSNameSvrType, wsSwDNSNameSvrRowStatus,
				wsSwDNSNameSvrIP }
			STATUS current
			DESCRIPTION
				"Description."
			::= { wsSwDNSGroups 1 }



	END

--
-- WS-SW-DNS-MIB.my
--
