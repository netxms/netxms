-- vim: syntax=mib
--
-- WS-CC-SMI.my
-- MIB generated by MG-SOFT Visual MIB Builder Version 6.0  Build 88
-- Wednesday, May 24, 2006 at 16:09:29
--

	WS-CC-SMI DEFINITIONS ::= BEGIN
 
		IMPORTS
			MODULE-IDENTITY			
				FROM SNMPv2-SMI			
			wsCc			
				FROM WS-SMI;
	
	
		-- 1.3.6.1.4.1.388.14.3.1
		wsCcMIB MODULE-IDENTITY 
			LAST-UPDATED "200505171117Z"		-- May 17, 2005 at 11:17 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200605241609Z"		-- May 24, 2006 at 16:09 GMT
			DESCRIPTION 
				"01a03"
			REVISION "200507071353Z"		-- July 07, 2005 at 13:53 GMT
			DESCRIPTION 
				"01a02"
			REVISION "200505171146Z"		-- May 17, 2005 at 11:46 GMT
			DESCRIPTION 
				"01a01"
			::= { wsCc 1 }

		
	
--
-- Node definitions
--
	
		-- 1.3.6.1.4.1.388.14.3.2
		wsCcRf OBJECT IDENTIFIER ::= { wsCc 2 }

		
		-- 1.3.6.1.4.1.388.14.3.3
		wsCcStats OBJECT IDENTIFIER ::= { wsCc 3 }

		
	
	END

--
-- WS-CC-SMI.my
--
