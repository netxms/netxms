-- vim: syntax=mib
--
-- WS-SW-ACL-MIB.my
-- MIB generated by MG-SOFT Visual MIB Builder Version 6.0  Build 88
-- Thursday, May 10, 2007 at 14:32:20
--

	WS-SW-ACL-MIB DEFINITIONS ::= BEGIN
 
		IMPORTS
			OBJECT-GROUP			
				FROM SNMPv2-CONF			
			IpAddress, Integer32, Counter32, Counter64, OBJECT-TYPE, 
			MODULE-IDENTITY			
				FROM SNMPv2-SMI			
			DisplayString, RowStatus, PhysAddress, TruthValue			
				FROM SNMPv2-TC			
			wsSwAcl			
				FROM WS-SW-SMI			
			AbbrevRowStatus, DoActionNow			
				FROM WS-TYPE-MIB;
	
	
		-- 1.3.6.1.4.1.388.14.2.11.1
		wsSwAclMibModule MODULE-IDENTITY 
			LAST-UPDATED "200705101422Z"		-- May 10, 2007 at 14:22 GMT
			ORGANIZATION 
				"Symbol Technologies, Inc."
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"MIB for Access-Control List (ACL) and NAT configuration."
			REVISION "200705101422Z"		-- May 10, 2007 at 14:22 GMT
			DESCRIPTION 
				"The following objects have been deprecated
				
				wsSwAclStdIpAclWlanIndex
				
				wsSwAclExtIpAclWlanIndex
				
				wsSwAclExtMacAclWlanIndex"
			REVISION "200702271729Z"		-- February 27, 2007 at 17:29 GMT
			DESCRIPTION 
				"01a14"
			REVISION "200701051313Z"		-- January 05, 2007 at 13:13 GMT
			DESCRIPTION 
				"01a13"
			REVISION "200612121256Z"		-- December 12, 2006 at 12:56 GMT
			DESCRIPTION 
				"01a12"
			REVISION "200612081237Z"		-- December 08, 2006 at 12:37 GMT
			DESCRIPTION 
				"01a11"
			REVISION "200609282150Z"		-- September 28, 2006 at 21:50 GMT
			DESCRIPTION 
				"01a10"
			REVISION "200609131420Z"		-- September 13, 2006 at 14:20 GMT
			DESCRIPTION 
				"01a09"
			REVISION "200609051615Z"		-- September 05, 2006 at 16:15 GMT
			DESCRIPTION 
				"01a08"
			REVISION "200609011755Z"		-- September 01, 2006 at 17:55 GMT
			DESCRIPTION 
				"01a07"
			REVISION "200608281820Z"		-- August 28, 2006 at 18:20 GMT
			DESCRIPTION 
				"01a06"
			REVISION "200608231314Z"		-- August 23, 2006 at 13:14 GMT
			DESCRIPTION 
				"01a05"
			REVISION "200608221409Z"		-- August 22, 2006 at 14:09 GMT
			DESCRIPTION 
				"01a04"
			REVISION "200608030927Z"		-- August 03, 2006 at 09:27 GMT
			DESCRIPTION 
				"01a03"
			REVISION "200606191736Z"		-- June 19, 2006 at 17:36 GMT
			DESCRIPTION 
				"01a02"
			REVISION "200606081127Z"		-- June 08, 2006 at 11:27 GMT
			DESCRIPTION 
				"01a01"
			::= { wsSwAcl 1 }

		
	
	
	
--
-- Node definitions
--
	
		-- 1.3.6.1.4.1.388.14.2.11.1.2
		wsSwAclMIB OBJECT IDENTIFIER ::= { wsSwAclMibModule 2 }

		
		-- 1.3.6.1.4.1.388.14.2.11.1.2.1
		wsSwAclTable OBJECT-TYPE
			SYNTAX SEQUENCE OF WsSwAclEntry
			MAX-ACCESS not-accessible
			STATUS current
			DESCRIPTION
				"Table for listing the ACLs configured on the switch."
			::= { wsSwAclMIB 1 }

		
		-- 1.3.6.1.4.1.388.14.2.11.1.2.1.1
		wsSwAclEntry OBJECT-TYPE
			SYNTAX WsSwAclEntry
			MAX-ACCESS not-accessible
			STATUS current
			DESCRIPTION
				"An entry in the ACL Table."
			INDEX { wsSwAclId }
			::= { wsSwAclTable 1 }

		
		WsSwAclEntry ::=
			SEQUENCE { 
				wsSwAclId
					DisplayString,
				wsSwAclType
					INTEGER,
				wsSwAclRowStatus
					AbbrevRowStatus
			 }

		-- 1.3.6.1.4.1.388.14.2.11.1.2.1.1.1
		wsSwAclId OBJECT-TYPE
			SYNTAX DisplayString
			MAX-ACCESS read-write
			STATUS current
			DESCRIPTION
				"The identifier string for the ACL, usually a number."
			::= { wsSwAclEntry 1 }

		
		-- 1.3.6.1.4.1.388.14.2.11.1.2.1.1.2
		wsSwAclType OBJECT-TYPE
			SYNTAX INTEGER
				{
				standardIp(1),
				extendedIp(2),
				extendedMac(3)
				}
			MAX-ACCESS read-create
			STATUS current
			DESCRIPTION
				"The ACL type, whether standard IP or extended IP or extended MAC."
			::= { wsSwAclEntry 2 }

		
		-- 1.3.6.1.4.1.388.14.2.11.1.2.1.1.3
		wsSwAclRowStatus OBJECT-TYPE
			SYNTAX AbbrevRowStatus
			MAX-ACCESS read-create
			STATUS current
			DESCRIPTION
				"Row status for the ACL entry."
			::= { wsSwAclEntry 3 }

		
		-- 1.3.6.1.4.1.388.14.2.11.1.2.2
		wsSwAclClearAllAcls OBJECT-TYPE
			SYNTAX DoActionNow
			MAX-ACCESS read-write
			STATUS current
			DESCRIPTION
				"A scalar used to clear all the ACLs in the ACL table."
			::= { wsSwAclMIB 2 }

		
		-- 1.3.6.1.4.1.388.14.2.11.1.2.3
		wsSwAclStdIpAclTable OBJECT-TYPE
			SYNTAX SEQUENCE OF WsSwAclStdIpAclEntry
			MAX-ACCESS not-accessible
			STATUS current
			DESCRIPTION
				"Table for standard IP ACLs."
			::= { wsSwAclMIB 3 }

		
		-- 1.3.6.1.4.1.388.14.2.11.1.2.3.1
		wsSwAclStdIpAclEntry OBJECT-TYPE
			SYNTAX WsSwAclStdIpAclEntry
			MAX-ACCESS not-accessible
			STATUS current
			DESCRIPTION
				"An entry in the standard IP ACL Table."
			INDEX { wsSwAclId, wsSwAclStdIpAclPrecedence }
			::= { wsSwAclStdIpAclTable 1 }

		
		WsSwAclStdIpAclEntry ::=
			SEQUENCE { 
				wsSwAclStdIpAclPrecedence
					INTEGER,
				wsSwAclStdIpAclOpType
					INTEGER,
				wsSwAclStdIpAclSrcIp
					IpAddress,
				wsSwAclStdIpAclSrcIpMask
					INTEGER,
				wsSwAclStdIpAclMark8021p
					INTEGER,
				wsSwAclStdIpAclTos
					INTEGER,
				wsSwAclStdIpAclWlanIndex
					INTEGER,
				wsSwAclStdIpAclRowStatus
					AbbrevRowStatus,
				wsSwAclStdIpAclLog
					TruthValue
			 }

		-- 1.3.6.1.4.1.388.14.2.11.1.2.3.1.1
		wsSwAclStdIpAclPrecedence OBJECT-TYPE
			SYNTAX INTEGER (1..5000)
			MAX-ACCESS read-create
			STATUS current
			DESCRIPTION
				"The precedence number for the Access Control Entry 
				(ACE). 1 is the highest precedence rule and 5000 is 
				 the lowest precedence rule."
			::= { wsSwAclStdIpAclEntry 1 }

		
		-- 1.3.6.1.4.1.388.14.2.11.1.2.3.1.2
		wsSwAclStdIpAclOpType OBJECT-TYPE
			SYNTAX INTEGER
				{
				deny(1),
				permit(2),
				mark(3)
				}
			MAX-ACCESS read-create
			STATUS current
			DESCRIPTION
				"The operation type (permit or deny) for this ACE."
			::= { wsSwAclStdIpAclEntry 2 }

		
		-- 1.3.6.1.4.1.388.14.2.11.1.2.3.1.3
		wsSwAclStdIpAclSrcIp OBJECT-TYPE
			SYNTAX IpAddress
			MAX-ACCESS read-create
			STATUS current
			DESCRIPTION
				"The source IP address for this ACE."
			::= { wsSwAclStdIpAclEntry 3 }

		
		-- 1.3.6.1.4.1.388.14.2.11.1.2.3.1.4
		wsSwAclStdIpAclSrcIpMask OBJECT-TYPE
			SYNTAX INTEGER (1..32)
			MAX-ACCESS read-create
			STATUS current
			DESCRIPTION
				"The source IP address mask for this ACE."
			DEFVAL { 0 }
			::= { wsSwAclStdIpAclEntry 4 }

		
		-- 1.3.6.1.4.1.388.14.2.11.1.2.3.1.5
		wsSwAclStdIpAclMark8021p OBJECT-TYPE
			SYNTAX INTEGER (0..7)
			MAX-ACCESS read-create
			STATUS current
			DESCRIPTION
				"The 802.1p VLAN user priority (to be used with -mark- action)"
			DEFVAL { -1 }
			::= { wsSwAclStdIpAclEntry 5 }

		
		-- 1.3.6.1.4.1.388.14.2.11.1.2.3.1.6
		wsSwAclStdIpAclTos OBJECT-TYPE
			SYNTAX INTEGER (0..255)
			MAX-ACCESS read-create
			STATUS current
			DESCRIPTION
				"The TOS bits in the IP header (to be used with -mark- action)"
			DEFVAL { -1 }
			::= { wsSwAclStdIpAclEntry 6 }

		
		-- 1.3.6.1.4.1.388.14.2.11.1.2.3.1.7
		wsSwAclStdIpAclWlanIndex OBJECT-TYPE
			SYNTAX INTEGER (1..32)
			MAX-ACCESS read-create
			STATUS deprecated
			DESCRIPTION
				"The WLAN index to be used with this standard IP ACL.
				
				Note: Use the wsSwAclWlanAclTable to set ACLs on WLANs."
			DEFVAL { 0 }
			::= { wsSwAclStdIpAclEntry 7 }

		
		-- 1.3.6.1.4.1.388.14.2.11.1.2.3.1.8
		wsSwAclStdIpAclRowStatus OBJECT-TYPE
			SYNTAX AbbrevRowStatus
			MAX-ACCESS read-create
			STATUS current
			DESCRIPTION
				"The row status for this ACE."
			::= { wsSwAclStdIpAclEntry 8 }

		
		-- 1.3.6.1.4.1.388.14.2.11.1.2.3.1.9
		wsSwAclStdIpAclLog OBJECT-TYPE
			SYNTAX TruthValue
			MAX-ACCESS read-create
			STATUS current
			DESCRIPTION
				"Log a match to this entry."
			DEFVAL { false }
			::= { wsSwAclStdIpAclEntry 9 }

		
		-- 1.3.6.1.4.1.388.14.2.11.1.2.4
		wsSwAclExtIpAclTable OBJECT-TYPE
			SYNTAX SEQUENCE OF WsSwAclExtIpAclEntry
			MAX-ACCESS not-accessible
			STATUS current
			DESCRIPTION
				"Table for extended IP ACLs."
			::= { wsSwAclMIB 4 }

		
		-- 1.3.6.1.4.1.388.14.2.11.1.2.4.1
		wsSwAclExtIpAclEntry OBJECT-TYPE
			SYNTAX WsSwAclExtIpAclEntry
			MAX-ACCESS not-accessible
			STATUS current
			DESCRIPTION
				"An entry in the extended IP ACL Table."
			INDEX { wsSwAclId, wsSwAclExtIpAclPrecedence }
			::= { wsSwAclExtIpAclTable 1 }

		
		WsSwAclExtIpAclEntry ::=
			SEQUENCE { 
				wsSwAclExtIpAclPrecedence
					INTEGER,
				wsSwAclExtIpAclOpType
					INTEGER,
				wsSwAclExtIpAclSrcIp
					IpAddress,
				wsSwAclExtIpAclSrcIpMask
					INTEGER,
				wsSwAclExtIpAclDestIp
					IpAddress,
				wsSwAclExtIpAclDestIpMask
					INTEGER,
				wsSwAclExtIpAclProtocolType
					INTEGER,
				wsSwAclExtIpAclMark8021p
					INTEGER,
				wsSwAclExtIpAclTos
					INTEGER,
				wsSwAclExtIpAclWlanIndex
					INTEGER,
				wsSwAclExtIpAclRowStatus
					AbbrevRowStatus,
				wsSwAclExtIpAclLog
					TruthValue
			 }

		-- 1.3.6.1.4.1.388.14.2.11.1.2.4.1.1
		wsSwAclExtIpAclPrecedence OBJECT-TYPE
			SYNTAX INTEGER (1..5000)
			MAX-ACCESS read-create
			STATUS current
			DESCRIPTION
				"The precedence number for the Access Control Entry 
				(ACE). 1 is the highest precedence rule and 5000 is 
				 the lowest precedence rule."
			::= { wsSwAclExtIpAclEntry 1 }

		
		-- 1.3.6.1.4.1.388.14.2.11.1.2.4.1.2
		wsSwAclExtIpAclOpType OBJECT-TYPE
			SYNTAX INTEGER
				{
				deny(1),
				permit(2),
				mark(3)
				}
			MAX-ACCESS read-create
			STATUS current
			DESCRIPTION
				"The operation type (permit or deny) for this ACE."
			::= { wsSwAclExtIpAclEntry 2 }

		
		-- 1.3.6.1.4.1.388.14.2.11.1.2.4.1.3
		wsSwAclExtIpAclSrcIp OBJECT-TYPE
			SYNTAX IpAddress
			MAX-ACCESS read-create
			STATUS current
			DESCRIPTION
				"The source IP address for this ACE."
			::= { wsSwAclExtIpAclEntry 3 }

		
		-- 1.3.6.1.4.1.388.14.2.11.1.2.4.1.4
		wsSwAclExtIpAclSrcIpMask OBJECT-TYPE
			SYNTAX INTEGER (1..32)
			MAX-ACCESS read-create
			STATUS current
			DESCRIPTION
				"The source IP address mask for this ACE."
			::= { wsSwAclExtIpAclEntry 4 }

		
		-- 1.3.6.1.4.1.388.14.2.11.1.2.4.1.5
		wsSwAclExtIpAclDestIp OBJECT-TYPE
			SYNTAX IpAddress
			MAX-ACCESS read-create
			STATUS current
			DESCRIPTION
				"The destination IP address for this ACE."
			::= { wsSwAclExtIpAclEntry 5 }

		
		-- 1.3.6.1.4.1.388.14.2.11.1.2.4.1.6
		wsSwAclExtIpAclDestIpMask OBJECT-TYPE
			SYNTAX INTEGER (1..32)
			MAX-ACCESS read-create
			STATUS current
			DESCRIPTION
				"The destination IP address mask for this ACE."
			::= { wsSwAclExtIpAclEntry 6 }

		
		-- 1.3.6.1.4.1.388.14.2.11.1.2.4.1.7
		wsSwAclExtIpAclProtocolType OBJECT-TYPE
			SYNTAX INTEGER
				{
				icmp(1),
				ip(2),
				tcp(3),
				udp(4)
				}
			MAX-ACCESS read-create
			STATUS current
			DESCRIPTION
				"The protocol type (ICMP/IP/TCP/UDP) for this ACE."
			::= { wsSwAclExtIpAclEntry 7 }

		
		-- 1.3.6.1.4.1.388.14.2.11.1.2.4.1.8
		wsSwAclExtIpAclMark8021p OBJECT-TYPE
			SYNTAX INTEGER (0..7)
			MAX-ACCESS read-create
			STATUS current
			DESCRIPTION
				"The 802.1p VLAN user priority (to be used with -mark- action)"
			DEFVAL { -1 }
			::= { wsSwAclExtIpAclEntry 8 }

		
		-- 1.3.6.1.4.1.388.14.2.11.1.2.4.1.9
		wsSwAclExtIpAclTos OBJECT-TYPE
			SYNTAX INTEGER (0..255)
			MAX-ACCESS read-create
			STATUS current
			DESCRIPTION
				"The TOS bits in the IP header (to be used with -mark- action)"
			DEFVAL { -1 }
			::= { wsSwAclExtIpAclEntry 9 }

		
		-- 1.3.6.1.4.1.388.14.2.11.1.2.4.1.10
		wsSwAclExtIpAclWlanIndex OBJECT-TYPE
			SYNTAX INTEGER (1..32)
			MAX-ACCESS read-create
			STATUS deprecated
			DESCRIPTION
				"The WLAN index to be used with this extended IP ACL. 
				
				Note: Use the wsSwAclWlanAclTable to set ACLs on WLANs."
			DEFVAL { 0 }
			::= { wsSwAclExtIpAclEntry 10 }

		
		-- 1.3.6.1.4.1.388.14.2.11.1.2.4.1.11
		wsSwAclExtIpAclRowStatus OBJECT-TYPE
			SYNTAX AbbrevRowStatus
			MAX-ACCESS read-create
			STATUS current
			DESCRIPTION
				"The row status for this ACE."
			::= { wsSwAclExtIpAclEntry 11 }

		
		-- 1.3.6.1.4.1.388.14.2.11.1.2.4.1.12
		wsSwAclExtIpAclLog OBJECT-TYPE
			SYNTAX TruthValue
			MAX-ACCESS read-create
			STATUS current
			DESCRIPTION
				"Log a match to this entry."
			DEFVAL { false }
			::= { wsSwAclExtIpAclEntry 12 }

		
		-- 1.3.6.1.4.1.388.14.2.11.1.2.5
		wsSwAclExtIpAclIcmpTable OBJECT-TYPE
			SYNTAX SEQUENCE OF WsSwAclExtIpAclIcmpEntry
			MAX-ACCESS not-accessible
			STATUS current
			DESCRIPTION
				"A table for Extended IP Acls ICMP Protocol 
				Parameters configuration"
			::= { wsSwAclMIB 5 }

		
		-- 1.3.6.1.4.1.388.14.2.11.1.2.5.1
		wsSwAclExtIpAclIcmpEntry OBJECT-TYPE
			SYNTAX WsSwAclExtIpAclIcmpEntry
			MAX-ACCESS not-accessible
			STATUS current
			DESCRIPTION
				"An entry in the table for Extended IP Acls ICMP 
				Protocol Parameters configuration"
			INDEX { wsSwAclId, wsSwAclExtIpAclPrecedence }
			::= { wsSwAclExtIpAclIcmpTable 1 }

		
		WsSwAclExtIpAclIcmpEntry ::=
			SEQUENCE { 
				wsSwAclExtIpAclIcmpType
					INTEGER,
				wsSwAclExtIpAclIcmpCode
					INTEGER,
				wsSwAclExtIpAclIcmpRowStatus
					AbbrevRowStatus
			 }

		-- 1.3.6.1.4.1.388.14.2.11.1.2.5.1.1
		wsSwAclExtIpAclIcmpType OBJECT-TYPE
			SYNTAX INTEGER (0..255)
			MAX-ACCESS read-create
			STATUS current
			DESCRIPTION
				"The type of the ICMP message."
			DEFVAL { -1 }
			::= { wsSwAclExtIpAclIcmpEntry 1 }

		
		-- 1.3.6.1.4.1.388.14.2.11.1.2.5.1.2
		wsSwAclExtIpAclIcmpCode OBJECT-TYPE
			SYNTAX INTEGER (0..255)
			MAX-ACCESS read-create
			STATUS current
			DESCRIPTION
				"The code within the ICMP message."
			DEFVAL { -1 }
			::= { wsSwAclExtIpAclIcmpEntry 2 }

		
		-- 1.3.6.1.4.1.388.14.2.11.1.2.5.1.3
		wsSwAclExtIpAclIcmpRowStatus OBJECT-TYPE
			SYNTAX AbbrevRowStatus
			MAX-ACCESS read-create
			STATUS current
			DESCRIPTION
				"The row status for this entry in the wsSwAclExtIpAclIcmpTable."
			::= { wsSwAclExtIpAclIcmpEntry 3 }

		
		-- 1.3.6.1.4.1.388.14.2.11.1.2.6
		wsSwAclExtIpAclTcpUdpTable OBJECT-TYPE
			SYNTAX SEQUENCE OF WsSwAclExtIpAclTcpUdpEntry
			MAX-ACCESS not-accessible
			STATUS current
			DESCRIPTION
				"A table for Extended IP Acls TCP/UDP Protocol 
				Parameters configuration"
			::= { wsSwAclMIB 6 }

		
		-- 1.3.6.1.4.1.388.14.2.11.1.2.6.1
		wsSwAclExtIpAclTcpUdpEntry OBJECT-TYPE
			SYNTAX WsSwAclExtIpAclTcpUdpEntry
			MAX-ACCESS not-accessible
			STATUS current
			DESCRIPTION
				"An entry in the table for Extended IP Acls TCP/UDP 
				Protocol Parameters configuration"
			INDEX { wsSwAclId, wsSwAclExtIpAclPrecedence }
			::= { wsSwAclExtIpAclTcpUdpTable 1 }

		
		WsSwAclExtIpAclTcpUdpEntry ::=
			SEQUENCE { 
				wsSwAclExtIpAclTcpUdpSrcPortLow
					INTEGER,
				wsSwAclExtIpAclTcpUdpSrcPortHigh
					INTEGER,
				wsSwAclExtIpAclTcpUdpDestPortLow
					INTEGER,
				wsSwAclExtIpAclTcpUdpDestPortHigh
					INTEGER,
				wsSwAclExtIpAclTcpUdpRowStatus
					AbbrevRowStatus
			 }

		-- 1.3.6.1.4.1.388.14.2.11.1.2.6.1.1
		wsSwAclExtIpAclTcpUdpSrcPortLow OBJECT-TYPE
			SYNTAX INTEGER (1..65535)
			MAX-ACCESS read-create
			STATUS current
			DESCRIPTION
				"The low value in the range of TCP/UDP source port 
				numbers permitted or denied for an ACE rule."
			DEFVAL { 0 }
			::= { wsSwAclExtIpAclTcpUdpEntry 1 }

		
		-- 1.3.6.1.4.1.388.14.2.11.1.2.6.1.2
		wsSwAclExtIpAclTcpUdpSrcPortHigh OBJECT-TYPE
			SYNTAX INTEGER (1..65535)
			MAX-ACCESS read-create
			STATUS current
			DESCRIPTION
				"The high value in the range of TCP/UDP source port 
				numbers permitted or denied for an ACE rule."
			DEFVAL { 0 }
			::= { wsSwAclExtIpAclTcpUdpEntry 2 }

		
		-- 1.3.6.1.4.1.388.14.2.11.1.2.6.1.3
		wsSwAclExtIpAclTcpUdpDestPortLow OBJECT-TYPE
			SYNTAX INTEGER (1..65535)
			MAX-ACCESS read-create
			STATUS current
			DESCRIPTION
				"The low value in the range of TCP/UDP destination port 
				numbers permitted or denied for an ACE rule."
			DEFVAL { 0 }
			::= { wsSwAclExtIpAclTcpUdpEntry 3 }

		
		-- 1.3.6.1.4.1.388.14.2.11.1.2.6.1.4
		wsSwAclExtIpAclTcpUdpDestPortHigh OBJECT-TYPE
			SYNTAX INTEGER (1..65535)
			MAX-ACCESS read-create
			STATUS current
			DESCRIPTION
				"The high value in the range of TCP/UDP destination port 
				numbers permitted or denied for an ACE rule."
			DEFVAL { 0 }
			::= { wsSwAclExtIpAclTcpUdpEntry 4 }

		
		-- 1.3.6.1.4.1.388.14.2.11.1.2.6.1.5
		wsSwAclExtIpAclTcpUdpRowStatus OBJECT-TYPE
			SYNTAX AbbrevRowStatus
			MAX-ACCESS read-create
			STATUS current
			DESCRIPTION
				"The row status for this entry in the wsSwAclExtIpAclTcpUdpTable."
			::= { wsSwAclExtIpAclTcpUdpEntry 5 }

		
		-- 1.3.6.1.4.1.388.14.2.11.1.2.7
		wsSwAclExtMacAclTable OBJECT-TYPE
			SYNTAX SEQUENCE OF WsSwAclExtMacAclEntry
			MAX-ACCESS not-accessible
			STATUS current
			DESCRIPTION
				"A table for Extended MAC ACLs."
			::= { wsSwAclMIB 7 }

		
		-- 1.3.6.1.4.1.388.14.2.11.1.2.7.1
		wsSwAclExtMacAclEntry OBJECT-TYPE
			SYNTAX WsSwAclExtMacAclEntry
			MAX-ACCESS not-accessible
			STATUS current
			DESCRIPTION
				"A entry in the Extended MAC ACLs table."
			INDEX { wsSwAclId, wsSwAclExtMacAclPrecedence }
			::= { wsSwAclExtMacAclTable 1 }

		
		WsSwAclExtMacAclEntry ::=
			SEQUENCE { 
				wsSwAclExtMacAclPrecedence
					INTEGER,
				wsSwAclExtMacAclOpType
					INTEGER,
				wsSwAclExtMacAclSrcMac
					PhysAddress,
				wsSwAclExtMacAclSrcMacMask
					PhysAddress,
				wsSwAclExtMacAclDestMac
					PhysAddress,
				wsSwAclExtMacAclDestMacMask
					PhysAddress,
				wsSwAclExtMacAclVlanId
					INTEGER,
				wsSwAclExtMacAclVlanUserPriority
					INTEGER,
				wsSwAclExtMacAclEtherType
					INTEGER,
				wsSwAclExtMacAclMark8021p
					INTEGER,
				wsSwAclExtMacAclTos
					INTEGER,
				wsSwAclExtMacAclWlanIndex
					INTEGER,
				wsSwAclExtMacAclRowStatus
					AbbrevRowStatus
			 }

		-- 1.3.6.1.4.1.388.14.2.11.1.2.7.1.1
		wsSwAclExtMacAclPrecedence OBJECT-TYPE
			SYNTAX INTEGER (1..5000)
			MAX-ACCESS read-create
			STATUS current
			DESCRIPTION
				"The precedence number for the Access Control Entry 
				(ACE). 1 is the highest precedence rule and 5000 is 
				 the lowest precedence rule."
			::= { wsSwAclExtMacAclEntry 1 }

		
		-- 1.3.6.1.4.1.388.14.2.11.1.2.7.1.2
		wsSwAclExtMacAclOpType OBJECT-TYPE
			SYNTAX INTEGER
				{
				deny(1),
				permit(2),
				mark(3)
				}
			MAX-ACCESS read-create
			STATUS current
			DESCRIPTION
				"The operation type (permit or deny) for this ACE."
			::= { wsSwAclExtMacAclEntry 2 }

		
		-- 1.3.6.1.4.1.388.14.2.11.1.2.7.1.3
		wsSwAclExtMacAclSrcMac OBJECT-TYPE
			SYNTAX PhysAddress
			MAX-ACCESS read-create
			STATUS current
			DESCRIPTION
				"The source MAC address for this ACE."
			::= { wsSwAclExtMacAclEntry 3 }

		
		-- 1.3.6.1.4.1.388.14.2.11.1.2.7.1.4
		wsSwAclExtMacAclSrcMacMask OBJECT-TYPE
			SYNTAX PhysAddress
			MAX-ACCESS read-create
			STATUS current
			DESCRIPTION
				"The source MAC address mask for this ACE."
			::= { wsSwAclExtMacAclEntry 4 }

		
		-- 1.3.6.1.4.1.388.14.2.11.1.2.7.1.5
		wsSwAclExtMacAclDestMac OBJECT-TYPE
			SYNTAX PhysAddress
			MAX-ACCESS read-create
			STATUS current
			DESCRIPTION
				"The destination MAC address for this ACE."
			::= { wsSwAclExtMacAclEntry 5 }

		
		-- 1.3.6.1.4.1.388.14.2.11.1.2.7.1.6
		wsSwAclExtMacAclDestMacMask OBJECT-TYPE
			SYNTAX PhysAddress
			MAX-ACCESS read-create
			STATUS current
			DESCRIPTION
				"The destination MAC address mask for this ACE."
			::= { wsSwAclExtMacAclEntry 6 }

		
		-- 1.3.6.1.4.1.388.14.2.11.1.2.7.1.7
		wsSwAclExtMacAclVlanId OBJECT-TYPE
			SYNTAX INTEGER (1..4096)
			MAX-ACCESS read-create
			STATUS current
			DESCRIPTION
				"The VLAN identifier for this ACE."
			DEFVAL { 0 }
			::= { wsSwAclExtMacAclEntry 7 }

		
		-- 1.3.6.1.4.1.388.14.2.11.1.2.7.1.8
		wsSwAclExtMacAclVlanUserPriority OBJECT-TYPE
			SYNTAX INTEGER (0..7)
			MAX-ACCESS read-create
			STATUS current
			DESCRIPTION
				"The VLAN user priority for this ACE."
			DEFVAL { -1 }
			::= { wsSwAclExtMacAclEntry 8 }

		
		-- 1.3.6.1.4.1.388.14.2.11.1.2.7.1.9
		wsSwAclExtMacAclEtherType OBJECT-TYPE
			SYNTAX INTEGER (1..65535)
			MAX-ACCESS read-create
			STATUS current
			DESCRIPTION
				"The ether type for this ACE."
			DEFVAL { 0 }
			::= { wsSwAclExtMacAclEntry 9 }

		
		-- 1.3.6.1.4.1.388.14.2.11.1.2.7.1.10
		wsSwAclExtMacAclMark8021p OBJECT-TYPE
			SYNTAX INTEGER (0..7)
			MAX-ACCESS read-create
			STATUS current
			DESCRIPTION
				"The 802.1p VLAN user priority (to be used with -mark- action)"
			DEFVAL { -1 }
			::= { wsSwAclExtMacAclEntry 10 }

		
		-- 1.3.6.1.4.1.388.14.2.11.1.2.7.1.11
		wsSwAclExtMacAclTos OBJECT-TYPE
			SYNTAX INTEGER (0..255)
			MAX-ACCESS read-create
			STATUS current
			DESCRIPTION
				"The TOS bits in the IP header (to be used with -mark- action)"
			DEFVAL { -1 }
			::= { wsSwAclExtMacAclEntry 11 }

		
		-- 1.3.6.1.4.1.388.14.2.11.1.2.7.1.12
		wsSwAclExtMacAclWlanIndex OBJECT-TYPE
			SYNTAX INTEGER (1..32)
			MAX-ACCESS read-create
			STATUS deprecated
			DESCRIPTION
				"The WLAN index to be used with this extended MAC ACL.
				
				Note: Use the wsSwAclWlanAclTable to set ACLs on WLANs in dataplane platforms."
			DEFVAL { 0 }
			::= { wsSwAclExtMacAclEntry 12 }

		
		-- 1.3.6.1.4.1.388.14.2.11.1.2.7.1.13
		wsSwAclExtMacAclRowStatus OBJECT-TYPE
			SYNTAX AbbrevRowStatus
			MAX-ACCESS read-create
			STATUS current
			DESCRIPTION
				"The row status for this ACE."
			::= { wsSwAclExtMacAclEntry 13 }

		
		-- 1.3.6.1.4.1.388.14.2.11.1.2.8
		wsSwAclInterfaceAclTable OBJECT-TYPE
			SYNTAX SEQUENCE OF WsSwAclInterfaceAclEntry
			MAX-ACCESS not-accessible
			STATUS current
			DESCRIPTION
				"A table for applying ACLs to an interface."
			::= { wsSwAclMIB 8 }

		
		-- 1.3.6.1.4.1.388.14.2.11.1.2.8.1
		wsSwAclInterfaceAclEntry OBJECT-TYPE
			SYNTAX WsSwAclInterfaceAclEntry
			MAX-ACCESS not-accessible
			STATUS current
			DESCRIPTION
				"An entry in the wsSwAclInterfaceAclTable."
			INDEX { wsSwAclInterfaceAclIfName }
			::= { wsSwAclInterfaceAclTable 1 }

		
		WsSwAclInterfaceAclEntry ::=
			SEQUENCE { 
				wsSwAclInterfaceAclIfName
					DisplayString,
				wsSwAclInterfaceAclInboundIpAclId
					DisplayString,
				wsSwAclInterfaceAclInboundMacAclId
					DisplayString,
				wsSwAclInterfaceAclRowStatus
					AbbrevRowStatus
			 }

		-- 1.3.6.1.4.1.388.14.2.11.1.2.8.1.1
		wsSwAclInterfaceAclIfName OBJECT-TYPE
			SYNTAX DisplayString
			MAX-ACCESS read-create
			STATUS current
			DESCRIPTION
				"The name of the interface to which ACL is applied."
			::= { wsSwAclInterfaceAclEntry 1 }

		
		-- 1.3.6.1.4.1.388.14.2.11.1.2.8.1.2
		wsSwAclInterfaceAclInboundIpAclId OBJECT-TYPE
			SYNTAX DisplayString
			MAX-ACCESS read-create
			STATUS current
			DESCRIPTION
				"The identifier of the inbound IP ACL applied to 
				the interface."
			::= { wsSwAclInterfaceAclEntry 2 }

		
		-- 1.3.6.1.4.1.388.14.2.11.1.2.8.1.3
		wsSwAclInterfaceAclInboundMacAclId OBJECT-TYPE
			SYNTAX DisplayString
			MAX-ACCESS read-create
			STATUS current
			DESCRIPTION
				"The identifier of the inbound MAC ACL applied to 
				the interface."
			::= { wsSwAclInterfaceAclEntry 3 }

		
		-- 1.3.6.1.4.1.388.14.2.11.1.2.8.1.4
		wsSwAclInterfaceAclRowStatus OBJECT-TYPE
			SYNTAX AbbrevRowStatus
			MAX-ACCESS read-create
			STATUS current
			DESCRIPTION
				"The row status for this entry in the 
				wsSwAclInterfaceAclTable."
			::= { wsSwAclInterfaceAclEntry 4 }

		
		-- 1.3.6.1.4.1.388.14.2.11.1.2.9
		wsSwAclCountAllAcls OBJECT-TYPE
			SYNTAX INTEGER (0..500)
			MAX-ACCESS read-only
			STATUS current
			DESCRIPTION
				"Count of all the ACLs present in the wireless switch."
			::= { wsSwAclMIB 9 }

		
		-- 1.3.6.1.4.1.388.14.2.11.1.2.10
		wsSwAclNatIfTable OBJECT-TYPE
			SYNTAX SEQUENCE OF WsSwAclNatIfEntry
			MAX-ACCESS not-accessible
			STATUS current
			DESCRIPTION
				"A table for configuring the type of an interface 
				for NAT."
			::= { wsSwAclMIB 10 }

		
		-- 1.3.6.1.4.1.388.14.2.11.1.2.10.1
		wsSwAclNatIfEntry OBJECT-TYPE
			SYNTAX WsSwAclNatIfEntry
			MAX-ACCESS not-accessible
			STATUS current
			DESCRIPTION
				"An entry in the wsSwAclNatIfTable."
			INDEX { wsSwAclNatIfName }
			::= { wsSwAclNatIfTable 1 }

		
		WsSwAclNatIfEntry ::=
			SEQUENCE { 
				wsSwAclNatIfName
					DisplayString,
				wsSwAclNatIfType
					INTEGER,
				wsSwAclNatIfRowStatus
					AbbrevRowStatus
			 }

		-- 1.3.6.1.4.1.388.14.2.11.1.2.10.1.1
		wsSwAclNatIfName OBJECT-TYPE
			SYNTAX DisplayString
			MAX-ACCESS read-create
			STATUS current
			DESCRIPTION
				"The name of the interface to be NATed."
			::= { wsSwAclNatIfEntry 1 }

		
		-- 1.3.6.1.4.1.388.14.2.11.1.2.10.1.2
		wsSwAclNatIfType OBJECT-TYPE
			SYNTAX INTEGER
				{
				inside(1),
				outside(2)
				}
			MAX-ACCESS read-create
			STATUS current
			DESCRIPTION
				"The interface type which is to be NAT'ed."
			::= { wsSwAclNatIfEntry 2 }

		
		-- 1.3.6.1.4.1.388.14.2.11.1.2.10.1.3
		wsSwAclNatIfRowStatus OBJECT-TYPE
			SYNTAX AbbrevRowStatus
			MAX-ACCESS read-create
			STATUS current
			DESCRIPTION
				"The row status for this entry in the wsSwAclNatIfTable."
			::= { wsSwAclNatIfEntry 3 }

		
		-- 1.3.6.1.4.1.388.14.2.11.1.2.11
		wsSwAclStaticNatTable OBJECT-TYPE
			SYNTAX SEQUENCE OF WsSwAclStaticNatEntry
			MAX-ACCESS not-accessible
			STATUS current
			DESCRIPTION
				"A table for configuring static NAT entries."
			::= { wsSwAclMIB 11 }

		
		-- 1.3.6.1.4.1.388.14.2.11.1.2.11.1
		wsSwAclStaticNatEntry OBJECT-TYPE
			SYNTAX WsSwAclStaticNatEntry
			MAX-ACCESS not-accessible
			STATUS current
			DESCRIPTION
				"An entry in the static NAT table."
			INDEX { wsSwAclStaticNatIndex }
			::= { wsSwAclStaticNatTable 1 }

		
		WsSwAclStaticNatEntry ::=
			SEQUENCE { 
				wsSwAclStaticNatIndex
					Integer32,
				wsSwAclStaticNatLocalAddr
					IpAddress,
				wsSwAclStaticNatGlobalAddr
					IpAddress,
				wsSwAclStaticNatIfType
					INTEGER,
				wsSwAclStaticNatDirection
					INTEGER,
				wsSwAclStaticNatLocalPort
					Integer32,
				wsSwAclStaticNatGlobalPort
					Integer32,
				wsSwAclStaticNatLocalProtocol
					INTEGER,
				wsSwAclStaticNatRowStatus
					AbbrevRowStatus
			 }

		-- 1.3.6.1.4.1.388.14.2.11.1.2.11.1.1
		wsSwAclStaticNatIndex OBJECT-TYPE
			SYNTAX Integer32 (1..500)
			MAX-ACCESS read-create
			STATUS current
			DESCRIPTION
				"The integer index for this entry in wsSwAclStaticNatTable."
			::= { wsSwAclStaticNatEntry 1 }

		
		-- 1.3.6.1.4.1.388.14.2.11.1.2.11.1.2
		wsSwAclStaticNatLocalAddr OBJECT-TYPE
			SYNTAX IpAddress
			MAX-ACCESS read-create
			STATUS current
			DESCRIPTION
				"The local IP address for this static NAT entry."
			::= { wsSwAclStaticNatEntry 2 }

		
		-- 1.3.6.1.4.1.388.14.2.11.1.2.11.1.3
		wsSwAclStaticNatGlobalAddr OBJECT-TYPE
			SYNTAX IpAddress
			MAX-ACCESS read-create
			STATUS current
			DESCRIPTION
				"The global IP address for this static NAT entry."
			::= { wsSwAclStaticNatEntry 3 }

		
		-- 1.3.6.1.4.1.388.14.2.11.1.2.11.1.4
		wsSwAclStaticNatIfType OBJECT-TYPE
			SYNTAX INTEGER
				{
				inside(1),
				outside(2)
				}
			MAX-ACCESS read-create
			STATUS current
			DESCRIPTION
				"The type (inside/outside) of the interface to be NAT'ed for this static NAT entry."
			::= { wsSwAclStaticNatEntry 4 }

		
		-- 1.3.6.1.4.1.388.14.2.11.1.2.11.1.5
		wsSwAclStaticNatDirection OBJECT-TYPE
			SYNTAX INTEGER
				{
				source(1),
				destination(2)
				}
			MAX-ACCESS read-create
			STATUS current
			DESCRIPTION
				"The direction of the interface (source or destination) in which NAT is to be applied for this static NAT mapping."
			::= { wsSwAclStaticNatEntry 5 }

		
		-- 1.3.6.1.4.1.388.14.2.11.1.2.11.1.6
		wsSwAclStaticNatLocalPort OBJECT-TYPE
			SYNTAX Integer32 (1..65535)
			MAX-ACCESS read-create
			STATUS current
			DESCRIPTION
				"The local NAT port used for this entry."
			::= { wsSwAclStaticNatEntry 6 }

		
		-- 1.3.6.1.4.1.388.14.2.11.1.2.11.1.7
		wsSwAclStaticNatGlobalPort OBJECT-TYPE
			SYNTAX Integer32 (1..65535)
			MAX-ACCESS read-create
			STATUS current
			DESCRIPTION
				"The global NAT port used for this entry."
			::= { wsSwAclStaticNatEntry 7 }

		
		-- 1.3.6.1.4.1.388.14.2.11.1.2.11.1.8
		wsSwAclStaticNatLocalProtocol OBJECT-TYPE
			SYNTAX INTEGER
				{
				tcp(1),
				udp(2)
				}
			MAX-ACCESS read-create
			STATUS current
			DESCRIPTION
				"The local protocol for this static NAT entry."
			::= { wsSwAclStaticNatEntry 8 }

		
		-- 1.3.6.1.4.1.388.14.2.11.1.2.11.1.9
		wsSwAclStaticNatRowStatus OBJECT-TYPE
			SYNTAX AbbrevRowStatus
			MAX-ACCESS read-create
			STATUS current
			DESCRIPTION
				"The row status for this entry in the 
				wsSwAclStaticNatTable."
			::= { wsSwAclStaticNatEntry 9 }

		
		-- 1.3.6.1.4.1.388.14.2.11.1.2.12
		wsSwAclDynamicNatTable OBJECT-TYPE
			SYNTAX SEQUENCE OF WsSwAclDynamicNatEntry
			MAX-ACCESS not-accessible
			STATUS current
			DESCRIPTION
				"A table for configuring dynamic NAT entries in the switch."
			::= { wsSwAclMIB 12 }

		
		-- 1.3.6.1.4.1.388.14.2.11.1.2.12.1
		wsSwAclDynamicNatEntry OBJECT-TYPE
			SYNTAX WsSwAclDynamicNatEntry
			MAX-ACCESS not-accessible
			STATUS current
			DESCRIPTION
				"An entry in the wsSwAclDynamicNatTable."
			INDEX { wsSwAclDynamicNatIndex }
			::= { wsSwAclDynamicNatTable 1 }

		
		WsSwAclDynamicNatEntry ::=
			SEQUENCE { 
				wsSwAclDynamicNatIndex
					INTEGER,
				wsSwAclDynamicNatIfType
					INTEGER,
				wsSwAclDynamicNatDirection
					INTEGER,
				wsSwAclDynamicNatAclId
					DisplayString,
				wsSwAclDynamicNatIfName
					DisplayString,
				wsSwAclDynamicNatRowStatus
					AbbrevRowStatus
			 }

		-- 1.3.6.1.4.1.388.14.2.11.1.2.12.1.1
		wsSwAclDynamicNatIndex OBJECT-TYPE
			SYNTAX INTEGER (1..4)
			MAX-ACCESS read-create
			STATUS current
			DESCRIPTION
				"The simple integer index for the wsSwAclDynamicNatTable."
			::= { wsSwAclDynamicNatEntry 1 }

		
		-- 1.3.6.1.4.1.388.14.2.11.1.2.12.1.2
		wsSwAclDynamicNatIfType OBJECT-TYPE
			SYNTAX INTEGER
				{
				inside(1),
				outside(2)
				}
			MAX-ACCESS read-create
			STATUS current
			DESCRIPTION
				"The type of the interface to be NAT'ed for this dynamic NAT entry."
			::= { wsSwAclDynamicNatEntry 2 }

		
		-- 1.3.6.1.4.1.388.14.2.11.1.2.12.1.3
		wsSwAclDynamicNatDirection OBJECT-TYPE
			SYNTAX INTEGER
				{
				source(1),
				destination(2)
				}
			MAX-ACCESS read-create
			STATUS current
			DESCRIPTION
				"The direction of the interface (source or destination) in which NAT is to be applied."
			::= { wsSwAclDynamicNatEntry 3 }

		
		-- 1.3.6.1.4.1.388.14.2.11.1.2.12.1.4
		wsSwAclDynamicNatAclId OBJECT-TYPE
			SYNTAX DisplayString
			MAX-ACCESS read-create
			STATUS current
			DESCRIPTION
				"The ACL identifier to be used in configuring this dynamic NAT entry."
			::= { wsSwAclDynamicNatEntry 4 }

		
		-- 1.3.6.1.4.1.388.14.2.11.1.2.12.1.5
		wsSwAclDynamicNatIfName OBJECT-TYPE
			SYNTAX DisplayString
			MAX-ACCESS read-create
			STATUS current
			DESCRIPTION
				"The name of the interface to which this dynamic NAT rule is applied."
			::= { wsSwAclDynamicNatEntry 5 }

		
		-- 1.3.6.1.4.1.388.14.2.11.1.2.12.1.6
		wsSwAclDynamicNatRowStatus OBJECT-TYPE
			SYNTAX AbbrevRowStatus
			MAX-ACCESS read-create
			STATUS current
			DESCRIPTION
				"The row status for this entry in the wsSwAclDynamicNatTable."
			::= { wsSwAclDynamicNatEntry 6 }

		
		-- 1.3.6.1.4.1.388.14.2.11.1.2.13
		wsSwAclNatTable OBJECT-TYPE
			SYNTAX SEQUENCE OF WsSwAclNatEntry
			MAX-ACCESS not-accessible
			STATUS current
			DESCRIPTION
				"A table for showing the status of Network Address Translation entries."
			::= { wsSwAclMIB 13 }

		
		-- 1.3.6.1.4.1.388.14.2.11.1.2.13.1
		wsSwAclNatEntry OBJECT-TYPE
			SYNTAX WsSwAclNatEntry
			MAX-ACCESS not-accessible
			STATUS current
			DESCRIPTION
				"An entry in the wsSwAclNatTable, indexed by a simple integer, wsSwAclNatIndex."
			INDEX { wsSwAclNatIndex }
			::= { wsSwAclNatTable 1 }

		
		WsSwAclNatEntry ::=
			SEQUENCE { 
				wsSwAclNatIndex
					Integer32,
				wsSwAclNatInsideLocalAddress
					IpAddress,
				wsSwAclNatInsideLocalPort
					INTEGER,
				wsSwAclNatInsideGlobalAddress
					IpAddress,
				wsSwAclNatInsideGlobalPort
					INTEGER,
				wsSwAclNatOutsideLocalAddress
					IpAddress,
				wsSwAclNatOutsideLocalPort
					INTEGER,
				wsSwAclNatOutsideGlobalAddress
					DisplayString,
				wsSwAclNatOutsideGlobalPort
					INTEGER
			 }

		-- 1.3.6.1.4.1.388.14.2.11.1.2.13.1.1
		wsSwAclNatIndex OBJECT-TYPE
			SYNTAX Integer32 (1..500)
			MAX-ACCESS read-only
			STATUS current
			DESCRIPTION
				"The integer index (NAT flow id) for this entry in wsSwAclNatTable."
			::= { wsSwAclNatEntry 1 }

		
		-- 1.3.6.1.4.1.388.14.2.11.1.2.13.1.2
		wsSwAclNatInsideLocalAddress OBJECT-TYPE
			SYNTAX IpAddress
			MAX-ACCESS read-only
			STATUS current
			DESCRIPTION
				"The inside local IP address for this entry in wsSwAclNatTable."
			::= { wsSwAclNatEntry 2 }

		
		-- 1.3.6.1.4.1.388.14.2.11.1.2.13.1.3
		wsSwAclNatInsideLocalPort OBJECT-TYPE
			SYNTAX INTEGER (1..65535)
			MAX-ACCESS read-only
			STATUS current
			DESCRIPTION
				"The inside local port for this entry in the wsSwAclNatTable."
			::= { wsSwAclNatEntry 3 }

		
		-- 1.3.6.1.4.1.388.14.2.11.1.2.13.1.4
		wsSwAclNatInsideGlobalAddress OBJECT-TYPE
			SYNTAX IpAddress
			MAX-ACCESS read-only
			STATUS current
			DESCRIPTION
				"The inside global IP address for this entry in wsSwAclNatTable."
			::= { wsSwAclNatEntry 4 }

		
		-- 1.3.6.1.4.1.388.14.2.11.1.2.13.1.5
		wsSwAclNatInsideGlobalPort OBJECT-TYPE
			SYNTAX INTEGER (1..65535)
			MAX-ACCESS read-only
			STATUS current
			DESCRIPTION
				"The inside global port for this entry in the wsSwAclNatTable."
			::= { wsSwAclNatEntry 5 }

		
		-- 1.3.6.1.4.1.388.14.2.11.1.2.13.1.6
		wsSwAclNatOutsideLocalAddress OBJECT-TYPE
			SYNTAX IpAddress
			MAX-ACCESS read-only
			STATUS current
			DESCRIPTION
				"The outside local IP address for this entry in wsSwAclNatTable."
			::= { wsSwAclNatEntry 6 }

		
		-- 1.3.6.1.4.1.388.14.2.11.1.2.13.1.7
		wsSwAclNatOutsideLocalPort OBJECT-TYPE
			SYNTAX INTEGER (1..65535)
			MAX-ACCESS read-only
			STATUS current
			DESCRIPTION
				"The outside local port for this entry in the wsSwAclNatTable."
			::= { wsSwAclNatEntry 7 }

		
		-- 1.3.6.1.4.1.388.14.2.11.1.2.13.1.8
		wsSwAclNatOutsideGlobalAddress OBJECT-TYPE
			SYNTAX DisplayString
			MAX-ACCESS read-only
			STATUS current
			DESCRIPTION
				"The outside global IP address for this entry in wsSwAclNatTable."
			::= { wsSwAclNatEntry 8 }

		
		-- 1.3.6.1.4.1.388.14.2.11.1.2.13.1.9
		wsSwAclNatOutsideGlobalPort OBJECT-TYPE
			SYNTAX INTEGER (1..65535)
			MAX-ACCESS read-only
			STATUS current
			DESCRIPTION
				"The outside global port for this entry in the wsSwAclNatTable."
			::= { wsSwAclNatEntry 9 }

		
		-- 1.3.6.1.4.1.388.14.2.11.1.2.14
		wsSwAclStatsTable OBJECT-TYPE
			SYNTAX SEQUENCE OF WsSwAclStatsEntry
			MAX-ACCESS not-accessible
			STATUS current
			DESCRIPTION
				"A table containing statistics per ACL rule/flow."
			::= { wsSwAclMIB 14 }

		
		-- 1.3.6.1.4.1.388.14.2.11.1.2.14.1
		wsSwAclStatsEntry OBJECT-TYPE
			SYNTAX WsSwAclStatsEntry
			MAX-ACCESS not-accessible
			STATUS current
			DESCRIPTION
				"An entry containing the statistics for an ACL rule/flow."
			INDEX { wsSwAclStatsRuleId }
			::= { wsSwAclStatsTable 1 }

		
		WsSwAclStatsEntry ::=
			SEQUENCE { 
				wsSwAclStatsRuleId
					Integer32,
				wsSwAclStatsAction
					INTEGER,
				wsSwAclStatsIfName
					DisplayString,
				wsSwAclStatsPrecedence
					INTEGER,
				wsSwAclStatsProtocol
					INTEGER,
				wsSwAclStatsSrcIpLow
					IpAddress,
				wsSwAclStatsSrcIpHigh
					IpAddress,
				wsSwAclStatsSrcPortLow
					INTEGER,
				wsSwAclStatsSrcPortHigh
					INTEGER,
				wsSwAclStatsDestIpLow
					IpAddress,
				wsSwAclStatsDestIpHigh
					IpAddress,
				wsSwAclStatsDestPortLow
					INTEGER,
				wsSwAclStatsDestPortHigh
					INTEGER,
				wsSwAclStatsTimesUsed
					Counter32,
				wsSwAclStatsNumFlowsActive
					Counter32,
				wsSwAclStatsNumFlowsTotal
					Counter32,
				wsSwAclStatsTotalInPkts
					Counter64,
				wsSwAclStatsTotalOutPkts
					Counter64
			 }

		-- 1.3.6.1.4.1.388.14.2.11.1.2.14.1.1
		wsSwAclStatsRuleId OBJECT-TYPE
			SYNTAX Integer32 (1..65535)
			MAX-ACCESS read-only
			STATUS current
			DESCRIPTION
				"The rule identifier for this ACL rule."
			::= { wsSwAclStatsEntry 1 }

		
		-- 1.3.6.1.4.1.388.14.2.11.1.2.14.1.2
		wsSwAclStatsAction OBJECT-TYPE
			SYNTAX INTEGER (1..6)
			MAX-ACCESS read-only
			STATUS current
			DESCRIPTION
				"The action for this ACL rule."
			::= { wsSwAclStatsEntry 2 }

		
		-- 1.3.6.1.4.1.388.14.2.11.1.2.14.1.3
		wsSwAclStatsIfName OBJECT-TYPE
			SYNTAX DisplayString
			MAX-ACCESS read-only
			STATUS current
			DESCRIPTION
				"The interface name to which this ACL rule is applied."
			::= { wsSwAclStatsEntry 3 }

		
		-- 1.3.6.1.4.1.388.14.2.11.1.2.14.1.4
		wsSwAclStatsPrecedence OBJECT-TYPE
			SYNTAX INTEGER (1..5000)
			MAX-ACCESS read-only
			STATUS current
			DESCRIPTION
				"The rule precedence for this ACL rule."
			::= { wsSwAclStatsEntry 4 }

		
		-- 1.3.6.1.4.1.388.14.2.11.1.2.14.1.5
		wsSwAclStatsProtocol OBJECT-TYPE
			SYNTAX INTEGER (1..255)
			MAX-ACCESS read-only
			STATUS current
			DESCRIPTION
				"The protocol (IP/ICMP/TCP/UDCP) for this ACL rule."
			::= { wsSwAclStatsEntry 5 }

		
		-- 1.3.6.1.4.1.388.14.2.11.1.2.14.1.6
		wsSwAclStatsSrcIpLow OBJECT-TYPE
			SYNTAX IpAddress
			MAX-ACCESS read-only
			STATUS current
			DESCRIPTION
				"The low end of the range of source IP addresses for this ACL rule."
			::= { wsSwAclStatsEntry 6 }

		
		-- 1.3.6.1.4.1.388.14.2.11.1.2.14.1.7
		wsSwAclStatsSrcIpHigh OBJECT-TYPE
			SYNTAX IpAddress
			MAX-ACCESS read-only
			STATUS current
			DESCRIPTION
				"The high end of the range of source IP addresses for this ACL rule."
			::= { wsSwAclStatsEntry 7 }

		
		-- 1.3.6.1.4.1.388.14.2.11.1.2.14.1.8
		wsSwAclStatsSrcPortLow OBJECT-TYPE
			SYNTAX INTEGER (1..65535)
			MAX-ACCESS read-only
			STATUS current
			DESCRIPTION
				"The low end of the range of source port values for this ACL rule."
			::= { wsSwAclStatsEntry 8 }

		
		-- 1.3.6.1.4.1.388.14.2.11.1.2.14.1.9
		wsSwAclStatsSrcPortHigh OBJECT-TYPE
			SYNTAX INTEGER (1..65535)
			MAX-ACCESS read-only
			STATUS current
			DESCRIPTION
				"The high end of the range of source port values for this ACL rule."
			::= { wsSwAclStatsEntry 9 }

		
		-- 1.3.6.1.4.1.388.14.2.11.1.2.14.1.10
		wsSwAclStatsDestIpLow OBJECT-TYPE
			SYNTAX IpAddress
			MAX-ACCESS read-only
			STATUS current
			DESCRIPTION
				"The low end of the range of destination IP addresses for this ACL rule."
			::= { wsSwAclStatsEntry 10 }

		
		-- 1.3.6.1.4.1.388.14.2.11.1.2.14.1.11
		wsSwAclStatsDestIpHigh OBJECT-TYPE
			SYNTAX IpAddress
			MAX-ACCESS read-only
			STATUS current
			DESCRIPTION
				"The high end of the range of destination IP addresses for this ACL rule."
			::= { wsSwAclStatsEntry 11 }

		
		-- 1.3.6.1.4.1.388.14.2.11.1.2.14.1.12
		wsSwAclStatsDestPortLow OBJECT-TYPE
			SYNTAX INTEGER (1..65535)
			MAX-ACCESS read-only
			STATUS current
			DESCRIPTION
				"The low end of the range of destination port values for this ACL rule."
			::= { wsSwAclStatsEntry 12 }

		
		-- 1.3.6.1.4.1.388.14.2.11.1.2.14.1.13
		wsSwAclStatsDestPortHigh OBJECT-TYPE
			SYNTAX INTEGER (1..65535)
			MAX-ACCESS read-only
			STATUS current
			DESCRIPTION
				"The high end of the range of destination port values for this ACL rule."
			::= { wsSwAclStatsEntry 13 }

		
		-- 1.3.6.1.4.1.388.14.2.11.1.2.14.1.14
		wsSwAclStatsTimesUsed OBJECT-TYPE
			SYNTAX Counter32
			MAX-ACCESS read-only
			STATUS current
			DESCRIPTION
				"Number of times this flow rule has been used (either hits or drops)."
			::= { wsSwAclStatsEntry 14 }

		
		-- 1.3.6.1.4.1.388.14.2.11.1.2.14.1.15
		wsSwAclStatsNumFlowsActive OBJECT-TYPE
			SYNTAX Counter32
			MAX-ACCESS read-only
			STATUS current
			DESCRIPTION
				"The total number of active flows for this ACL rule."
			::= { wsSwAclStatsEntry 15 }

		
		-- 1.3.6.1.4.1.388.14.2.11.1.2.14.1.16
		wsSwAclStatsNumFlowsTotal OBJECT-TYPE
			SYNTAX Counter32
			MAX-ACCESS read-only
			STATUS current
			DESCRIPTION
				"The total number of flows for this ACL rule."
			::= { wsSwAclStatsEntry 16 }

		
		-- 1.3.6.1.4.1.388.14.2.11.1.2.14.1.17
		wsSwAclStatsTotalInPkts OBJECT-TYPE
			SYNTAX Counter64
			MAX-ACCESS read-only
			STATUS current
			DESCRIPTION
				"The total number of incoming packets for this ACL rule."
			::= { wsSwAclStatsEntry 17 }

		
		-- 1.3.6.1.4.1.388.14.2.11.1.2.14.1.18
		wsSwAclStatsTotalOutPkts OBJECT-TYPE
			SYNTAX Counter64
			MAX-ACCESS read-only
			STATUS current
			DESCRIPTION
				"The total number of outgoing packets for this ACL rule."
			::= { wsSwAclStatsEntry 18 }

		
		-- 1.3.6.1.4.1.388.14.2.11.1.2.15
		wsSwAclSetErrorA OBJECT-TYPE
			SYNTAX DisplayString
			MAX-ACCESS read-only
			STATUS current
			DESCRIPTION
				"The error message, if any, from the last set request to
				any of the following tablular or scalar objects:
				wsSwAclTable, 
				wsSwAclClearAllAcls, 
				wsSwAclStdIpAclTable,
				wsSwAclExtIpAclTable, 
				wsSwAclExtIpAclIcmpTable,
				wsSwAclExtIpAclTcpUdpTable,
				wsSwAclExtMacAclTable.
				
				"
			::= { wsSwAclMIB 15 }

		
		-- 1.3.6.1.4.1.388.14.2.11.1.2.16
		wsSwAclSetErrorB OBJECT-TYPE
			SYNTAX DisplayString
			MAX-ACCESS read-only
			STATUS current
			DESCRIPTION
				"The error message, if any, from the last set request to
				any of the following tablular or scalar objects:
				wsSwAclInterfaceAclTable.
				"
			::= { wsSwAclMIB 16 }

		
		-- 1.3.6.1.4.1.388.14.2.11.1.2.17
		wsSwAclNatSetError OBJECT-TYPE
			SYNTAX DisplayString
			MAX-ACCESS read-only
			STATUS current
			DESCRIPTION
				"The error message, if any, from the last set request to
				any of the following tablular or scalar objects:
				wsSwAclNatIfTable,
				wsSwAclStaticNatTable,
				wsSwAclDynamicNatTable."
			::= { wsSwAclMIB 17 }

		
		-- 1.3.6.1.4.1.388.14.2.11.1.2.18
		wsSwAclWlanAclTable OBJECT-TYPE
			SYNTAX SEQUENCE OF WsSwAclWlanAclEntry
			MAX-ACCESS not-accessible
			STATUS current
			DESCRIPTION
				"This table allows the user to configure the L2 ACLs on a per-WLAN basis 
				rather than on the physical interfaces."
			::= { wsSwAclMIB 18 }

		
		-- 1.3.6.1.4.1.388.14.2.11.1.2.18.1
		wsSwAclWlanAclEntry OBJECT-TYPE
			SYNTAX WsSwAclWlanAclEntry
			MAX-ACCESS not-accessible
			STATUS current
			DESCRIPTION
				"An entry in the wsSwAclWlanAclTable."
			INDEX { wsSwAclWlanIndex, wsSwAclWlanAclDirection }
			::= { wsSwAclWlanAclTable 1 }

		
		WsSwAclWlanAclEntry ::=
			SEQUENCE { 
				wsSwAclWlanIndex
					INTEGER,
				wsSwAclWlanAclDirection
					INTEGER,
				wsSwAclWlanMacAclId
					DisplayString,
				wsSwAclWlanIpAclId
					DisplayString,
				wsSwAclWlanAclRowStatus
					AbbrevRowStatus
			 }

		-- 1.3.6.1.4.1.388.14.2.11.1.2.18.1.1
		wsSwAclWlanIndex OBJECT-TYPE
			SYNTAX INTEGER (1..256)
			MAX-ACCESS read-create
			STATUS current
			DESCRIPTION
				"The index of the WLAN which uniquely denotes a WLAN.
				This ranges from 1 to 256."
			::= { wsSwAclWlanAclEntry 1 }

		
		-- 1.3.6.1.4.1.388.14.2.11.1.2.18.1.2
		wsSwAclWlanAclDirection OBJECT-TYPE
			SYNTAX INTEGER
				{
				inbound(1),
				outbound(2)
				}
			MAX-ACCESS read-create
			STATUS current
			DESCRIPTION
				"The direction in which the ACL to be applied on this WLAN port."
			::= { wsSwAclWlanAclEntry 2 }

		
		-- 1.3.6.1.4.1.388.14.2.11.1.2.18.1.3
		wsSwAclWlanMacAclId OBJECT-TYPE
			SYNTAX DisplayString
			MAX-ACCESS read-create
			STATUS current
			DESCRIPTION
				"The name or number of the MAC ACL, which uniquely denotes the particular MAC ACL
				 being applied on this WLAN."
			::= { wsSwAclWlanAclEntry 3 }

		
		-- 1.3.6.1.4.1.388.14.2.11.1.2.18.1.4
		wsSwAclWlanIpAclId OBJECT-TYPE
			SYNTAX DisplayString
			MAX-ACCESS read-create
			STATUS current
			DESCRIPTION
				"The name or number of the IP ACL, which uniquely denotes the particular IP ACL
				 being applied on this WLAN."
			::= { wsSwAclWlanAclEntry 4 }

		
		-- 1.3.6.1.4.1.388.14.2.11.1.2.18.1.5
		wsSwAclWlanAclRowStatus OBJECT-TYPE
			SYNTAX AbbrevRowStatus
			MAX-ACCESS read-create
			STATUS current
			DESCRIPTION
				"SNMP row status to create/configure this entry."
			::= { wsSwAclWlanAclEntry 5 }

		
		-- 1.3.6.1.4.1.388.14.2.11.1.2.100
		wsSwAclConformance OBJECT IDENTIFIER ::= { wsSwAclMIB 100 }

		
		-- 1.3.6.1.4.1.388.14.2.11.1.2.100.1
		wsSwAclGroups OBJECT IDENTIFIER ::= { wsSwAclConformance 1 }

		
		-- 1.3.6.1.4.1.388.14.2.11.1.2.100.1.1
		wsSwAclGroup OBJECT-GROUP
			OBJECTS { wsSwAclId, wsSwAclType, wsSwAclRowStatus, wsSwAclClearAllAcls, wsSwAclStdIpAclPrecedence, 
				wsSwAclExtIpAclPrecedence, wsSwAclExtIpAclIcmpType, wsSwAclExtIpAclTcpUdpSrcPortLow, wsSwAclExtMacAclPrecedence, wsSwAclInterfaceAclIfName, 
				wsSwAclExtIpAclOpType, wsSwAclExtIpAclSrcIp, wsSwAclExtIpAclSrcIpMask, wsSwAclExtIpAclDestIp, wsSwAclExtIpAclDestIpMask, 
				wsSwAclExtIpAclProtocolType, wsSwAclExtIpAclRowStatus, wsSwAclExtIpAclIcmpCode, wsSwAclExtIpAclTcpUdpDestPortHigh, wsSwAclExtIpAclTcpUdpDestPortLow, 
				wsSwAclExtIpAclTcpUdpSrcPortHigh, wsSwAclExtMacAclOpType, wsSwAclExtMacAclSrcMac, wsSwAclExtMacAclSrcMacMask, wsSwAclExtMacAclDestMac, 
				wsSwAclExtMacAclDestMacMask, wsSwAclExtMacAclVlanId, wsSwAclExtMacAclVlanUserPriority, wsSwAclExtMacAclEtherType, wsSwAclExtMacAclRowStatus, 
				wsSwAclInterfaceAclRowStatus, wsSwAclInterfaceAclInboundMacAclId, wsSwAclInterfaceAclInboundIpAclId, wsSwAclNatIfRowStatus, wsSwAclCountAllAcls, 
				wsSwAclExtIpAclTcpUdpRowStatus, wsSwAclExtIpAclIcmpRowStatus, wsSwAclNatIndex, wsSwAclNatInsideGlobalAddress, wsSwAclNatInsideLocalAddress, 
				wsSwAclNatOutsideGlobalAddress, wsSwAclNatOutsideLocalAddress, wsSwAclDynamicNatIfName, wsSwAclStdIpAclTos, wsSwAclExtIpAclTos, 
				wsSwAclExtMacAclTos, wsSwAclExtIpAclMark8021p, wsSwAclExtMacAclMark8021p, wsSwAclStdIpAclOpType, wsSwAclStdIpAclSrcIp, 
				wsSwAclStdIpAclSrcIpMask, wsSwAclStdIpAclRowStatus, wsSwAclNatIfName, wsSwAclNatIfType, wsSwAclStaticNatIndex, 
				wsSwAclStaticNatLocalAddr, wsSwAclStaticNatGlobalAddr, wsSwAclStaticNatIfType, wsSwAclStaticNatDirection, wsSwAclDynamicNatIndex, 
				wsSwAclDynamicNatIfType, wsSwAclDynamicNatDirection, wsSwAclDynamicNatAclId, wsSwAclStatsRuleId, wsSwAclStatsAction, 
				wsSwAclStatsIfName, wsSwAclStatsPrecedence, wsSwAclStatsProtocol, wsSwAclStatsSrcIpLow, wsSwAclStatsSrcIpHigh, 
				wsSwAclStatsSrcPortLow, wsSwAclStatsSrcPortHigh, wsSwAclStatsDestIpLow, wsSwAclStatsDestIpHigh, wsSwAclStatsDestPortLow, 
				wsSwAclStatsDestPortHigh, wsSwAclStatsNumFlowsActive, wsSwAclStatsNumFlowsTotal, wsSwAclStatsTotalInPkts, wsSwAclStatsTotalOutPkts, 
				wsSwAclStatsTimesUsed, wsSwAclDynamicNatRowStatus, wsSwAclStdIpAclMark8021p, wsSwAclNatInsideLocalPort, wsSwAclNatInsideGlobalPort, 
				wsSwAclNatOutsideLocalPort, wsSwAclNatOutsideGlobalPort, wsSwAclStaticNatGlobalPort, wsSwAclStaticNatLocalPort, wsSwAclNatSetError, 
				wsSwAclStaticNatRowStatus, wsSwAclStaticNatLocalProtocol, wsSwAclSetErrorB, wsSwAclWlanIndex, wsSwAclWlanMacAclId, 
				wsSwAclWlanIpAclId, wsSwAclWlanAclDirection, wsSwAclWlanAclRowStatus, wsSwAclSetErrorA, wsSwAclStdIpAclLog, 
				wsSwAclExtIpAclLog }
			STATUS current
			DESCRIPTION 
				"Group of ACL and NAT objects"
			::= { wsSwAclGroups 1 }

		
		-- 1.3.6.1.4.1.388.14.2.11.1.2.100.1.2
		wsSwAclDeprecatedGroup OBJECT-GROUP
			OBJECTS { wsSwAclStdIpAclWlanIndex, wsSwAclExtIpAclWlanIndex, wsSwAclExtMacAclWlanIndex }
			STATUS deprecated
			DESCRIPTION 
				"Group of deprecated objects."
			::= { wsSwAclGroups 2 }

		
		-- 1.3.6.1.4.1.388.14.2.11.1.2.100.2
		wsSwAclCompls OBJECT IDENTIFIER ::= { wsSwAclConformance 2 }

		
	
	END

--
-- WS-SW-ACL-MIB.my
--
