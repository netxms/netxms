-- SECTION 1: Top Level Definitions

S5-ETHERNET-TRAP-MIB DEFINITIONS ::= BEGIN

-- 5000 Ethernet Trap MIB Release 1.1.3
-- Revision 09/22/98
-- 5000 Ethernet Trap MIB Release 1.1.2
-- Revision 05/19/98
-- 5000 Ethernet Trap MIB Release 1.1.1
-- Revision 03/23/94

-- Copyright 1993-98 SynOptics Communications, Inc.
-- All rights reserved.
-- This SynOptics SNMP Management Information Base Specification
-- (Specification) embodies SynOptics' confidential and
-- proprietary intellectual property. SynOptics retains all
-- title and ownership in the Specification, including any
-- revisions.

-- This Specification is supplied "AS IS," and SynOptics makes
-- no warranty, either express or implied, as to the use,
-- operation, condition, or performance of the Specification.


-- Imports

IMPORTS
	TRAP-TYPE	FROM RFC-1215
	s5EnPortPartStatus, s5EnPortJabberStatus,
	s5EnPortLinkStatus
			FROM S5-ETHERNET-COMMON-MIB
	s5EnRedPortCompanionBrdNum, s5EnRedPortCompanionPortNum,
	s5EnRedPortRemoteOperStatus, s5EnRedPortRedundMode,
	s5EnRedPortOperStatus
			FROM S5-ETH-REDUNDANT-LINKS-MIB
	s5EthTrap	FROM S5-ROOT-MIB

	s5SbsViolationStatusBrdIndx,
	s5SbsViolationStatusPortIndx,
	s5SbsViolationStatusMACAddress,
	s5SbsMgmViolationType,
	s5SbsMgmViolationIpAddress
			FROM S5-SWITCH-BAYSECURE-MIB;


-- SECTION 2: SynOptics 5000 Ethernet Trap Definitions

-- All ethernet traps are numbered uniquely with ENTERPRISE
-- field value of s5EthTrap.

s5EtrPortAutoPart TRAP-TYPE
	ENTERPRISE	s5EthTrap
	VARIABLES	{ s5EnPortPartStatus,
			  s5EnPortJabberStatus }
--	STATUS		mandatory
	DESCRIPTION
		"A port was auto partitioned (wrapped). This
		trap is sent only once when the condition is
		first detected. The following values are
		returned:
		  s5EnPortPartStatus.....the partition status
		    of the port, with the instance identifying
		    the board and the port.
		  s5EnPortJabberStatus...the jabber status of
		    the DTE(s) connected to the port, with the
		    instance identifying the board and the port."
	::= 1	-- 0x01

s5EtrPortDteJabbering TRAP-TYPE
	ENTERPRISE	s5EthTrap
	VARIABLES	{ s5EnPortJabberStatus }
--	STATUS		mandatory
	DESCRIPTION
		"An ethernet DTE started jabbering.  This trap
		is sent only once when the condition is first
		detected. The following values are returned:
		  s5EnPortJabberStatus...the jabber status of
		    the DTE(s) connected to the port, with the
		    instance identifying the board and the port."
	::= 2	-- 0x02

s5EtrRedPortFailure TRAP-TYPE
	ENTERPRISE	s5EthTrap
	VARIABLES	{ s5EnRedPortOperStatus,
			  s5EnRedPortCompanionBrdNum,
			  s5EnRedPortCompanionPortNum,
			  s5EnPortPartStatus,
			  s5EnPortLinkStatus,
			  s5EnPortJabberStatus }
--	STATUS		mandatory
	DESCRIPTION
		"A port that is in a redundant pair developed a fault.
		This trap is sent once when the condition is
		first detected. For all objects returned in the trap,
		the instance identifies the board and the port index.
		The following values are returned:
		  s5EnRedPortOperStatus.........The status of the port.
		              The value will distinguish between a
		              local fault, a remote fault, and a
		              missing board.
		  s5EnRedPortCompanionBrdNum....The index of the slot
		              containing the board of the other port
		              in the redundant pair.
		  s5EnRedPortCompanionPortNum...The index of the other
		              port in the redundant pair.
		  s5EnPortPartStatus, s5EnPortLinkStatus and
		  s5EnPortJabberStatus..........These values may help
		              determine the cause of the local fault."  
	::= 3	-- 0x03

s5EtrRedBadRemCfgDetected TRAP-TYPE
	ENTERPRISE	s5EthTrap
	VARIABLES	{ s5EnRedPortRemoteOperStatus,
			  s5EnRedPortRedundMode}
--	STATUS		mandatory
	DESCRIPTION
		"This trap is sent periodically when the NMM detects a
		remoteOperStatus of invalid on a port set for
		redundancy. The instance identifies the board and port
		index. The following values are returned:
		  s5EnRedPortRemoteOperStatus.....The value of the
		              received signal from the remote port.
		  s5EnRedPortRedundMode...the redundancy mode of the port."
	::= 4	-- 0x04

s5EtrSbsMacAccessViolation TRAP-TYPE
	ENTERPRISE	s5EthTrap
	VARIABLES	{ s5SbsViolationStatusBrdIndx,
			  s5SbsViolationStatusPortIndx,
			  s5SbsViolationStatusMACAddress}
--	STATUS		mandatory
	DESCRIPTION
		"This trap is sent when the switch device detects a
		Mac_address based security violation on a port set by
		s5SbsSecurityAction defined in s5sbs100.mib. This trap
		is sent only once when the condition is first detected. 
		The following values are returned:
		s5SbsViolationStatusBrdIndx...the Board number on which a security violation was seen.
		s5SbsViolationStatusPortIndx...the Port number on which a security violation was seen.
		s5SbsViolationStatusMACIndx...the mac address trigers this violation"
	::= 5	-- 0x05

s5EtrMgmAccessViolation TRAP-TYPE
	ENTERPRISE	s5EthTrap
	VARIABLES	{ s5SbsMgmViolationType,
			  s5SbsMgmViolationIpAddress}
--	STATUS		mandatory
	DESCRIPTION
		"This trap is sent when the switch device detects a
		management access violation on the switch. This trap
		is sent only once when the condition is first detected. 
		The following values are returned:
		s5SbsMgmViolationType.....WEB access violation or telnet 
					access violation or SNMP access violation.
		s5SbsMgmViolationIpAddress...the invalid IP address."
	::= 6	-- 0x06

s5EtrPortManualPart TRAP-TYPE
	ENTERPRISE	s5EthTrap
	VARIABLES	{ s5EnPortPartStatus,
			  s5EnPortJabberStatus }
--	STATUS		mandatory
	DESCRIPTION
		"A port was manually partitioned (wrapped). This
		trap is sent once when the port is initially 
		partitioned. The following values are
		returned:
		  s5EnPortPartStatus.....the partition status
		    of the port, with the instance identifying
		    the board and the port.
		  s5EnPortJabberStatus...the jabber status of
		    the DTE(s) connected to the port, with the
		    instance identifying the board and the port."
	::= 7	-- 0x07

END
