-- **********************************************************
-- Copyright 2007-2013 VMware, Inc.  All rights reserved.
-- **********************************************************

VMWARE-PRODUCTS-MIB DEFINITIONS ::= BEGIN

IMPORTS
   MODULE-IDENTITY
        FROM SNMPv2-SMI
    vmwOID, vmwProductSpecific
        FROM VMWARE-ROOT-MIB;

vmwProducts MODULE-IDENTITY
       LAST-UPDATED "201301260000Z"
       ORGANIZATION "VMware, Inc"
       CONTACT-INFO
               "VMware, Inc
                3401 Hillview Ave
                Palo Alto, CA 94304
                Tel: 1-877-486-9273 or 650-427-5000
                Fax: 650-427-5001
                Web: http://communities.vmware.com/community/developer/forums/managementapi
                "
       DESCRIPTION
               "This MIB module provides the OID identifiers
                which are returned from SNMPv2-MIB sysObjectId for
                agents in specific VMware products.
               "
       REVISION      "201301260000Z"
       DESCRIPTION
               "Add vmwVCM - VMware Cloud VM - snmp agent's sysObjectId value."
       REVISION      "201109290000Z"
       DESCRIPTION
               "Add vmwVCOps snmp agent's sysObjectId value."
       REVISION      "200707300000Z"
       DESCRIPTION
               "The initial revision."
       ::= { vmwProductSpecific 11 }

vmwESX OBJECT IDENTIFIER
    ::= { vmwProductSpecific 1 }

vmwDVS OBJECT IDENTIFIER
    ::= { vmwProductSpecific 2 }

vmwVC OBJECT IDENTIFIER
    ::= { vmwProductSpecific 3 }

vmwServer OBJECT IDENTIFIER
    ::= { vmwProductSpecific 4 }

vmwVCOps OBJECT IDENTIFIER
    ::= { vmwProductSpecific 5 }

vmwCVM OBJECT IDENTIFIER
    ::= { vmwProductSpecific 6 }

oidESX OBJECT IDENTIFIER
    ::= { vmwOID 1 }

END -- end of module VMWARE-PRODUCTS-MIB.
