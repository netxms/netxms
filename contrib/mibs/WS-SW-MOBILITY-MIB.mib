-- vim: syntax=mib
--
-- WS-SW-MOBILITY-MIB.my
-- MIB generated by MG-SOFT Visual MIB Builder Version 6.0  Build 88
-- Tuesday, October 03, 2006 at 12:05:30
--

	WS-SW-MOBILITY-MIB DEFINITIONS ::= BEGIN

		IMPORTS
			OBJECT-GROUP, MODULE-COMPLIANCE
				FROM SNMPv2-CONF
			IpAddress, Unsigned32, OBJECT-TYPE, MODULE-IDENTITY
				FROM SNMPv2-SMI
			RowStatus, MacAddress, TruthValue
				FROM SNMPv2-TC
			wsSwMobility
				FROM WS-SW-SMI;


		-- 1.3.6.1.4.1.388.14.2.9.1
		wsSwMobilityMib MODULE-IDENTITY
			LAST-UPDATED "200610031204Z"		-- October 03, 2006 at 12:04 GMT
			ORGANIZATION
				"Symbol Technologies"
			CONTACT-INFO
				"Symbol Technologies, Inc.
				Customer Service
				Postal:
				One Symbol Plaza
				Holtsville, NY 11742-1300
				USA
				Tel: +1. 631.738.6213
				E-mail: support@symbol.com
				Web: http://www.symbol.com/support"
			DESCRIPTION
				"Description."
			REVISION "200610031204Z"		-- October 03, 2006 at 12:04 GMT
			DESCRIPTION
				"02a06"
			REVISION "200608101550Z"		-- August 10, 2006 at 15:50 GMT
			DESCRIPTION
				"02a05"
			REVISION "200606281022Z"		-- June 28, 2006 at 10:22 GMT
			DESCRIPTION
				"02a04"
			REVISION "200605241709Z"		-- May 24, 2006 at 17:09 GMT
			DESCRIPTION
				"02a03"
			REVISION "200605101139Z"		-- May 10, 2006 at 11:39 GMT
			DESCRIPTION
				"02a02"
			REVISION "200605091429Z"		-- May 09, 2006 at 14:29 GMT
			DESCRIPTION
				"02a01"
			::= { wsSwMobility 1 }




--
-- Node definitions
--

		-- 1.3.6.1.4.1.388.14.2.9.1.1
		wsSwMobilityPeerTable OBJECT-TYPE
			SYNTAX SEQUENCE OF WsSwMobilityPeerEntry
			MAX-ACCESS not-accessible
			STATUS current
			DESCRIPTION
				"Description."
			::= { wsSwMobilityMib 1 }


		-- 1.3.6.1.4.1.388.14.2.9.1.1.1
		wsSwMobilityPeerEntry OBJECT-TYPE
			SYNTAX WsSwMobilityPeerEntry
			MAX-ACCESS not-accessible
			STATUS current
			DESCRIPTION
				"Description."
			INDEX { wsSwMobilityPeerIp }
			::= { wsSwMobilityPeerTable 1 }


		WsSwMobilityPeerEntry ::=
			SEQUENCE {
				wsSwMobilityPeerIp
					IpAddress,
				wsSwMobilityPeerJOINSent
					Unsigned32,
				wsSwMobilityPeerJOINRecvd
					Unsigned32,
				wsSwMobilityPeerLEAVESent
					Unsigned32,
				wsSwMobilityPeerLEAVERecvd
					Unsigned32,
				wsSwMobilityPeerL2ROAMSent
					Unsigned32,
				wsSwMobilityPeerL2ROAMRecvd
					Unsigned32,
				wsSwMobilityPeerL3ROAMSent
					Unsigned32,
				wsSwMobilityPeerL3ROAMRecvd
					Unsigned32,
				wsSwMobilityPeerSessionState
					INTEGER,
				wsSwMobilityPeerClearStatistics
					INTEGER,
				wsSwMobilityPeerRowStatus
					RowStatus
			 }

		-- 1.3.6.1.4.1.388.14.2.9.1.1.1.1
		wsSwMobilityPeerIp OBJECT-TYPE
			SYNTAX IpAddress
			MAX-ACCESS read-only
			STATUS current
			DESCRIPTION
				"Description."
			::= { wsSwMobilityPeerEntry 1 }


		-- 1.3.6.1.4.1.388.14.2.9.1.1.1.2
		wsSwMobilityPeerJOINSent OBJECT-TYPE
			SYNTAX Unsigned32
			MAX-ACCESS read-only
			STATUS current
			DESCRIPTION
				"Description."
			::= { wsSwMobilityPeerEntry 2 }


		-- 1.3.6.1.4.1.388.14.2.9.1.1.1.3
		wsSwMobilityPeerJOINRecvd OBJECT-TYPE
			SYNTAX Unsigned32
			MAX-ACCESS read-only
			STATUS current
			DESCRIPTION
				"Description."
			::= { wsSwMobilityPeerEntry 3 }


		-- 1.3.6.1.4.1.388.14.2.9.1.1.1.4
		wsSwMobilityPeerLEAVESent OBJECT-TYPE
			SYNTAX Unsigned32
			MAX-ACCESS read-only
			STATUS current
			DESCRIPTION
				"Description."
			::= { wsSwMobilityPeerEntry 4 }


		-- 1.3.6.1.4.1.388.14.2.9.1.1.1.5
		wsSwMobilityPeerLEAVERecvd OBJECT-TYPE
			SYNTAX Unsigned32
			MAX-ACCESS read-only
			STATUS current
			DESCRIPTION
				"Description."
			::= { wsSwMobilityPeerEntry 5 }


		-- 1.3.6.1.4.1.388.14.2.9.1.1.1.6
		wsSwMobilityPeerL2ROAMSent OBJECT-TYPE
			SYNTAX Unsigned32
			MAX-ACCESS read-only
			STATUS current
			DESCRIPTION
				"Description."
			::= { wsSwMobilityPeerEntry 6 }


		-- 1.3.6.1.4.1.388.14.2.9.1.1.1.7
		wsSwMobilityPeerL2ROAMRecvd OBJECT-TYPE
			SYNTAX Unsigned32
			MAX-ACCESS read-only
			STATUS current
			DESCRIPTION
				"Description."
			::= { wsSwMobilityPeerEntry 7 }


		-- 1.3.6.1.4.1.388.14.2.9.1.1.1.8
		wsSwMobilityPeerL3ROAMSent OBJECT-TYPE
			SYNTAX Unsigned32
			MAX-ACCESS read-only
			STATUS current
			DESCRIPTION
				"Description."
			::= { wsSwMobilityPeerEntry 8 }


		-- 1.3.6.1.4.1.388.14.2.9.1.1.1.9
		wsSwMobilityPeerL3ROAMRecvd OBJECT-TYPE
			SYNTAX Unsigned32
			MAX-ACCESS read-only
			STATUS current
			DESCRIPTION
				"Description."
			::= { wsSwMobilityPeerEntry 9 }


		-- 1.3.6.1.4.1.388.14.2.9.1.1.1.10
		wsSwMobilityPeerSessionState OBJECT-TYPE
			SYNTAX INTEGER
				{
				idle(1),
				active(2),
				passive(3),
				connect(4),
				established(5)
				}
			MAX-ACCESS read-only
			STATUS current
			DESCRIPTION
				"Description."
			::= { wsSwMobilityPeerEntry 10 }


		-- 1.3.6.1.4.1.388.14.2.9.1.1.1.11
		wsSwMobilityPeerClearStatistics OBJECT-TYPE
			SYNTAX INTEGER
				{
				clear(1),
				idle(2)
				}
			MAX-ACCESS read-create
			STATUS current
			DESCRIPTION
				"Description."
			::= { wsSwMobilityPeerEntry 11 }


		-- 1.3.6.1.4.1.388.14.2.9.1.1.1.12
		wsSwMobilityPeerRowStatus OBJECT-TYPE
			SYNTAX RowStatus
			MAX-ACCESS read-create
			STATUS current
			DESCRIPTION
				"Description."
			::= { wsSwMobilityPeerEntry 12 }


		-- 1.3.6.1.4.1.388.14.2.9.1.2
		wsSwMobilityMUTable OBJECT-TYPE
			SYNTAX SEQUENCE OF WsSwMobilityMUEntry
			MAX-ACCESS not-accessible
			STATUS current
			DESCRIPTION
				"Description."
			::= { wsSwMobilityMib 2 }


		-- 1.3.6.1.4.1.388.14.2.9.1.2.1
		wsSwMobilityMUEntry OBJECT-TYPE
			SYNTAX WsSwMobilityMUEntry
			MAX-ACCESS not-accessible
			STATUS current
			DESCRIPTION
				"Description."
			INDEX { wsSwMobilityMUMACAddr }
			::= { wsSwMobilityMUTable 1 }


		WsSwMobilityMUEntry ::=
			SEQUENCE {
				wsSwMobilityMUMACAddr
					MacAddress,
				wsSwMobilityMUIPAddress
					IpAddress,
				wsSwMobilityMUHSIPAddr
					IpAddress,
				wsSwMobilityMUCSIPAddr
					IpAddress,
				wsSwMobilityMUHSVLAN
					Unsigned32
			 }

		-- 1.3.6.1.4.1.388.14.2.9.1.2.1.1
		wsSwMobilityMUMACAddr OBJECT-TYPE
			SYNTAX MacAddress
			MAX-ACCESS read-only
			STATUS current
			DESCRIPTION
				"Description."
			::= { wsSwMobilityMUEntry 1 }


		-- 1.3.6.1.4.1.388.14.2.9.1.2.1.2
		wsSwMobilityMUIPAddress OBJECT-TYPE
			SYNTAX IpAddress
			MAX-ACCESS read-only
			STATUS current
			DESCRIPTION
				"Description."
			::= { wsSwMobilityMUEntry 2 }


		-- 1.3.6.1.4.1.388.14.2.9.1.2.1.3
		wsSwMobilityMUHSIPAddr OBJECT-TYPE
			SYNTAX IpAddress
			MAX-ACCESS read-only
			STATUS current
			DESCRIPTION
				"Description."
			::= { wsSwMobilityMUEntry 3 }


		-- 1.3.6.1.4.1.388.14.2.9.1.2.1.4
		wsSwMobilityMUCSIPAddr OBJECT-TYPE
			SYNTAX IpAddress
			MAX-ACCESS read-only
			STATUS current
			DESCRIPTION
				"Description."
			::= { wsSwMobilityMUEntry 4 }


		-- 1.3.6.1.4.1.388.14.2.9.1.2.1.5
		wsSwMobilityMUHSVLAN OBJECT-TYPE
			SYNTAX Unsigned32
			MAX-ACCESS read-only
			STATUS current
			DESCRIPTION
				"Description."
			::= { wsSwMobilityMUEntry 5 }


		-- 1.3.6.1.4.1.388.14.2.9.1.3
		wsSwMobilityLocalAddr OBJECT-TYPE
			SYNTAX IpAddress
			MAX-ACCESS read-write
			STATUS current
			DESCRIPTION
				"Set local addr"
			::= { wsSwMobilityMib 3 }


		-- 1.3.6.1.4.1.388.14.2.9.1.4
		wsSwMobilityEnable OBJECT-TYPE
			SYNTAX TruthValue
			MAX-ACCESS read-write
			STATUS current
			DESCRIPTION
				"Enable/disable mobility"
			::= { wsSwMobilityMib 4 }


		-- 1.3.6.1.4.1.388.14.2.9.1.5
		wsSwMobilityRoamPeriod OBJECT-TYPE
			SYNTAX Unsigned32 (1..300)
			MAX-ACCESS read-write
			STATUS current
			DESCRIPTION
				"set roam period"
			::= { wsSwMobilityMib 5 }


		-- 1.3.6.1.4.1.388.14.2.9.1.100
		wsSwMobilityMibConformance OBJECT IDENTIFIER ::= { wsSwMobilityMib 100 }


		-- 1.3.6.1.4.1.388.14.2.9.1.100.1
		wsSwMobilityMibCompliances OBJECT IDENTIFIER ::= { wsSwMobilityMibConformance 1 }


		-- 1.3.6.1.4.1.388.14.2.9.1.100.1.1
		wsSwMobilityMibCompliance MODULE-COMPLIANCE
			STATUS current
			DESCRIPTION
				"Description."
			MODULE -- this module
				MANDATORY-GROUPS { wsSwMobilityGroup }
			::= { wsSwMobilityMibCompliances 1 }


		-- 1.3.6.1.4.1.388.14.2.9.1.100.2
		wsSwMobilityGroups OBJECT IDENTIFIER ::= { wsSwMobilityMibConformance 2 }


		-- 1.3.6.1.4.1.388.14.2.9.1.100.2.1
		wsSwMobilityGroup OBJECT-GROUP
			OBJECTS { wsSwMobilityPeerIp, wsSwMobilityPeerJOINSent, wsSwMobilityPeerJOINRecvd, wsSwMobilityPeerLEAVESent, wsSwMobilityPeerLEAVERecvd,
				wsSwMobilityPeerL2ROAMSent, wsSwMobilityPeerL3ROAMSent, wsSwMobilityPeerSessionState, wsSwMobilityPeerClearStatistics, wsSwMobilityPeerRowStatus,
				wsSwMobilityMUMACAddr, wsSwMobilityMUIPAddress, wsSwMobilityMUHSIPAddr, wsSwMobilityMUCSIPAddr, wsSwMobilityMUHSVLAN,
				wsSwMobilityLocalAddr, wsSwMobilityEnable, wsSwMobilityRoamPeriod, wsSwMobilityPeerL2ROAMRecvd, wsSwMobilityPeerL3ROAMRecvd
				 }
			STATUS current
			DESCRIPTION
				"Description."
			::= { wsSwMobilityGroups 1 }



	END

--
-- WS-SW-MOBILITY-MIB.my
--
