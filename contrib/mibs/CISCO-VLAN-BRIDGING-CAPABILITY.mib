-- *****************************************************************
-- CISCO-VLAN-BRIDGING-CAPABILITY.my:
-- Cisco CISCO-VLAN-BRIDGING-MIB AGENT-CAPABILITIES
--
-- Sept 2003, Jayakumar Kadirvelu
--            Seth Wang
--
-- Copyright (c) 2004 by Cisco Systems, Inc.
-- All rights reserved.
-- *****************************************************************

CISCO-VLAN-BRIDGING-CAPABILITY DEFINITIONS ::= BEGIN

IMPORTS
        MODULE-IDENTITY
                FROM SNMPv2-SMI
        AGENT-CAPABILITIES
                FROM SNMPv2-CONF
        ciscoAgentCapability
                FROM CISCO-SMI;

ciscoVlanBridgingCapability MODULE-IDENTITY
        LAST-UPDATED    "200406110000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com
                        cs-vlans@cisco.com"
        DESCRIPTION
                "The agent capabilities description of
                 CISCO-VLAN-BRIDGING-MIB."

        REVISION        "200406110000Z"
        DESCRIPTION
                "Initial version of this MIB module."
        ::= { ciscoAgentCapability 339 }

cVlanBridgingCapCatOSV08R0101 AGENT-CAPABILITIES
    PRODUCT-RELEASE     "Cisco CatOS 8.1(1)."
    STATUS              current
    DESCRIPTION         "CISCO-VLAN-BRIDGING-MIB capabilities."

    SUPPORTS            CISCO-VLAN-BRIDGING-MIB
        INCLUDES        { ciscoVlanBridgingMIBGroup }

    ::= { ciscoVlanBridgingCapability 1 }

cVlanBridgingCapCatOSV08R0201 AGENT-CAPABILITIES
    PRODUCT-RELEASE     "Cisco CatOS 8.2(1)."
    STATUS              current
    DESCRIPTION         "CISCO-VLAN-BRIDGING-MIB capabilities."

    SUPPORTS            CISCO-VLAN-BRIDGING-MIB
        INCLUDES        { ciscoVlanBridgingMIBGroup,
                          ciscoVlanBridgingMIBGroup2 }

    ::= { ciscoVlanBridgingCapability 2 }

END
