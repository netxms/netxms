-- vim: syntax=mib
--
-- WS-USER-MGMT-MIB.my
-- MIB generated by MG-SOFT Visual MIB Builder Version 6.0  Build 88
-- Friday, June 23, 2006 at 15:28:36
--

	WS-USER-MGMT-MIB DEFINITIONS ::= BEGIN
 
		IMPORTS
			OBJECT-GROUP, MODULE-COMPLIANCE			
				FROM SNMPv2-CONF			
			IpAddress, OBJECT-TYPE, MODULE-IDENTITY			
				FROM SNMPv2-SMI			
			PhysAddress, DisplayString, TruthValue			
				FROM SNMPv2-TC			
			wsMgmt			
				FROM WS-SMI;
	
	
		-- 1.3.6.1.4.1.388.14.4.2
		wsUserMgmtMib MODULE-IDENTITY 
			LAST-UPDATED "200606131844Z"		-- June 13, 2006 at 18:44 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200606131425Z"		-- June 13, 2006 at 14:25 GMT
			DESCRIPTION 
				"01a01"
			::= { wsMgmt 2 }

		
	
--
-- Type definitions
--
	
		AbbrRowStatus ::= INTEGER
			{
			active(1),
			createAndGo(4),
			destroy(6)
			}

	
	
--
-- Node definitions
--
	
		-- 1.3.6.1.4.1.388.14.4.2.1
		wsUserMgmtUserTable OBJECT-TYPE
			SYNTAX SEQUENCE OF WsUserMgmtUserEntry
			MAX-ACCESS not-accessible
			STATUS current
			DESCRIPTION
				"Description."
			::= { wsUserMgmtMib 1 }

		
		-- 1.3.6.1.4.1.388.14.4.2.1.1
		wsUserMgmtUserEntry OBJECT-TYPE
			SYNTAX WsUserMgmtUserEntry
			MAX-ACCESS not-accessible
			STATUS current
			DESCRIPTION
				"Description."
			INDEX { wsUserMgmtUserName }
			::= { wsUserMgmtUserTable 1 }

		
		WsUserMgmtUserEntry ::=
			SEQUENCE { 
				wsUserMgmtUserName
					DisplayString,
				wsUserMgmtUserPassword
					DisplayString,
				wsUserMgmtUserRole
					BITS,
				wsUserMgmtUserAccessMode
					BITS,
				wsUserMgmtUserRowStatus
					AbbrRowStatus
			 }

		-- 1.3.6.1.4.1.388.14.4.2.1.1.1
		wsUserMgmtUserName OBJECT-TYPE
			SYNTAX DisplayString (SIZE (1..28))
			MAX-ACCESS read-only
			STATUS current
			DESCRIPTION
				"User Name"
			::= { wsUserMgmtUserEntry 1 }

		
		-- 1.3.6.1.4.1.388.14.4.2.1.1.2
		wsUserMgmtUserPassword OBJECT-TYPE
			SYNTAX DisplayString (SIZE (8..32))
			MAX-ACCESS read-write
			STATUS current
			DESCRIPTION
				"User pasword.  This object will display null string when being read"
			::= { wsUserMgmtUserEntry 2 }

		
		-- 1.3.6.1.4.1.388.14.4.2.1.1.3
		wsUserMgmtUserRole OBJECT-TYPE
			SYNTAX BITS
				{
				monitor(0),
				helpDesk(1),
				networkAdmin(2),
				systemAdmin(3),
				webUserAdmin(4),
				superUser(5)
				}
			MAX-ACCESS read-write
			STATUS current
			DESCRIPTION
				"User previlege"
			::= { wsUserMgmtUserEntry 3 }

		
		-- 1.3.6.1.4.1.388.14.4.2.1.1.4
		wsUserMgmtUserAccessMode OBJECT-TYPE
			SYNTAX BITS
				{
				console(0),
				telnet(1),
				ssh(2),
				snmp(3)
				}
			MAX-ACCESS read-write
			STATUS current
			DESCRIPTION
				"Login source for the user"
			::= { wsUserMgmtUserEntry 4 }

		
		-- 1.3.6.1.4.1.388.14.4.2.1.1.5
		wsUserMgmtUserRowStatus OBJECT-TYPE
			SYNTAX AbbrRowStatus
			MAX-ACCESS read-write
			STATUS current
			DESCRIPTION
				"Description."
			::= { wsUserMgmtUserEntry 5 }

		
		-- 1.3.6.1.4.1.388.14.4.2.2
		wsUserMgmtRadiusSvrTable OBJECT-TYPE
			SYNTAX SEQUENCE OF WsUserMgmtRadiusSvrEntry
			MAX-ACCESS not-accessible
			STATUS current
			DESCRIPTION
				"Description."
			::= { wsUserMgmtMib 2 }

		
		-- 1.3.6.1.4.1.388.14.4.2.2.1
		wsUserMgmtRadiusSvrEntry OBJECT-TYPE
			SYNTAX WsUserMgmtRadiusSvrEntry
			MAX-ACCESS not-accessible
			STATUS current
			DESCRIPTION
				"Description."
			INDEX { wsUserMgmtRadiusSvrIdx }
			::= { wsUserMgmtRadiusSvrTable 1 }

		
		WsUserMgmtRadiusSvrEntry ::=
			SEQUENCE { 
				wsUserMgmtRadiusSvrIdx
					INTEGER,
				wsUserMgmtRadiusSvrIPAddr
					IpAddress,
				wsUserMgmtRadiusSvrPort
					INTEGER,
				wsUserMgmtRadiusSvrNumRetries
					INTEGER,
				wsUserMgmtRadiusSvrTimeOut
					INTEGER,
				wsUserMgmtRadiusSvrSecret
					DisplayString,
				wsUserMgmtRadiusSvrRowStatus
					AbbrRowStatus
			 }

		-- 1.3.6.1.4.1.388.14.4.2.2.1.1
		wsUserMgmtRadiusSvrIdx OBJECT-TYPE
			SYNTAX INTEGER (1..32)
			MAX-ACCESS read-only
			STATUS current
			DESCRIPTION
				"Description."
			::= { wsUserMgmtRadiusSvrEntry 1 }

		
		-- 1.3.6.1.4.1.388.14.4.2.2.1.2
		wsUserMgmtRadiusSvrIPAddr OBJECT-TYPE
			SYNTAX IpAddress
			MAX-ACCESS read-write
			STATUS current
			DESCRIPTION
				"Radius server IP address"
			::= { wsUserMgmtRadiusSvrEntry 2 }

		
		-- 1.3.6.1.4.1.388.14.4.2.2.1.3
		wsUserMgmtRadiusSvrPort OBJECT-TYPE
			SYNTAX INTEGER (0..65535)
			MAX-ACCESS read-write
			STATUS current
			DESCRIPTION
				"Radius server port"
			::= { wsUserMgmtRadiusSvrEntry 3 }

		
		-- 1.3.6.1.4.1.388.14.4.2.2.1.4
		wsUserMgmtRadiusSvrNumRetries OBJECT-TYPE
			SYNTAX INTEGER (0..100)
			MAX-ACCESS read-write
			STATUS current
			DESCRIPTION
				"Number of retries to communicate with active radius server"
			::= { wsUserMgmtRadiusSvrEntry 4 }

		
		-- 1.3.6.1.4.1.388.14.4.2.2.1.5
		wsUserMgmtRadiusSvrTimeOut OBJECT-TYPE
			SYNTAX INTEGER (1..1000)
			UNITS "seconds"
			MAX-ACCESS read-write
			STATUS current
			DESCRIPTION
				"Time to wait for radius to reply"
			::= { wsUserMgmtRadiusSvrEntry 5 }

		
		-- 1.3.6.1.4.1.388.14.4.2.2.1.6
		wsUserMgmtRadiusSvrSecret OBJECT-TYPE
			SYNTAX DisplayString
			MAX-ACCESS read-write
			STATUS current
			DESCRIPTION
				"Encription key shared with the radius server"
			::= { wsUserMgmtRadiusSvrEntry 6 }

		
		-- 1.3.6.1.4.1.388.14.4.2.2.1.7
		wsUserMgmtRadiusSvrRowStatus OBJECT-TYPE
			SYNTAX AbbrRowStatus
			MAX-ACCESS read-write
			STATUS current
			DESCRIPTION
				"Description."
			::= { wsUserMgmtRadiusSvrEntry 7 }

		
		-- 1.3.6.1.4.1.388.14.4.2.3
		wsUserMgmtAuthMethods OBJECT IDENTIFIER ::= { wsUserMgmtMib 3 }

		
		-- 1.3.6.1.4.1.388.14.4.2.3.1
		wsUserMgmtAuthMethod1 OBJECT-TYPE
			SYNTAX INTEGER
				{
				invalid(0),
				none(1),
				local(2),
				radius(3)
				}
			MAX-ACCESS read-write
			STATUS current
			DESCRIPTION
				"First authentication method to ues"
			::= { wsUserMgmtAuthMethods 1 }

		
		-- 1.3.6.1.4.1.388.14.4.2.3.2
		wsUserMgmtAuthMethod2 OBJECT-TYPE
			SYNTAX INTEGER
				{
				invalid(0),
				none(1),
				local(2),
				radius(3)
				}
			MAX-ACCESS read-write
			STATUS current
			DESCRIPTION
				"Second authentication method to use if first methond returns erro"
			::= { wsUserMgmtAuthMethods 2 }

		
		-- 1.3.6.1.4.1.388.14.4.2.3.3
		wsUserMgmtAuthMethod3 OBJECT-TYPE
			SYNTAX TruthValue
			MAX-ACCESS read-write
			STATUS current
			DESCRIPTION
				"Indicates if 'none' authentication method is set or not"
			::= { wsUserMgmtAuthMethods 3 }

		
		-- 1.3.6.1.4.1.388.14.4.2.4
		wsUserMgmtPasswdChange OBJECT IDENTIFIER ::= { wsUserMgmtMib 4 }

		
		-- 1.3.6.1.4.1.388.14.4.2.4.1
		wsUserMgmtPasswdUser OBJECT-TYPE
			SYNTAX DisplayString (SIZE (1..28))
			MAX-ACCESS read-write
			STATUS current
			DESCRIPTION
				"Description."
			::= { wsUserMgmtPasswdChange 1 }

		
		-- 1.3.6.1.4.1.388.14.4.2.4.2
		wsUserMgmtPasswdOld OBJECT-TYPE
			SYNTAX DisplayString (SIZE (8..32))
			MAX-ACCESS read-write
			STATUS current
			DESCRIPTION
				"User must enter the old password in order to change it.  
				Password is null string when read."
			::= { wsUserMgmtPasswdChange 2 }

		
		-- 1.3.6.1.4.1.388.14.4.2.4.3
		wsUserMgmtPasswdNew OBJECT-TYPE
			SYNTAX DisplayString (SIZE (8..32))
			MAX-ACCESS read-write
			STATUS current
			DESCRIPTION
				"The new user password to be used. 
				Password is null string when read."
			::= { wsUserMgmtPasswdChange 3 }

		
		-- 1.3.6.1.4.1.388.14.4.2.4.4
		wsUserMgmtPasswdAction OBJECT-TYPE
			SYNTAX INTEGER
				{
				none(0),
				changePassword(1)
				}
			MAX-ACCESS read-write
			STATUS current
			DESCRIPTION
				"Initiate password change. All objects under wsUserMgmtPasswdChange 
				should be sent within a single set request to assure data consistancy.
				The value of is none(0) when read."
			::= { wsUserMgmtPasswdChange 4 }

		
		-- 1.3.6.1.4.1.388.14.4.2.100
		wsUserMgmtConformance OBJECT IDENTIFIER ::= { wsUserMgmtMib 100 }

		
		-- 1.3.6.1.4.1.388.14.4.2.100.1
		wsUserMgmtCompliances OBJECT IDENTIFIER ::= { wsUserMgmtConformance 1 }

		
		-- 1.3.6.1.4.1.388.14.4.2.100.1.1
		wsMgmtCompliance MODULE-COMPLIANCE
			STATUS current
			DESCRIPTION 
				"Description."
			MODULE -- this module
				MANDATORY-GROUPS { wsUserMgmtGroup }
			::= { wsUserMgmtCompliances 1 }

		
		-- 1.3.6.1.4.1.388.14.4.2.100.2
		wsUserMgmtGroups OBJECT IDENTIFIER ::= { wsUserMgmtConformance 2 }

		
		-- 1.3.6.1.4.1.388.14.4.2.100.2.2
		wsUserMgmtGroup OBJECT-GROUP
			OBJECTS { wsUserMgmtUserPassword, wsUserMgmtUserRole, wsUserMgmtUserAccessMode, wsUserMgmtUserRowStatus, wsUserMgmtRadiusSvrPort, 
				wsUserMgmtRadiusSvrNumRetries, wsUserMgmtRadiusSvrTimeOut, wsUserMgmtRadiusSvrSecret, wsUserMgmtRadiusSvrRowStatus, wsUserMgmtAuthMethod1, 
				wsUserMgmtAuthMethod2, wsUserMgmtRadiusSvrIdx, wsUserMgmtUserName, wsUserMgmtPasswdAction, wsUserMgmtPasswdNew, 
				wsUserMgmtPasswdOld, wsUserMgmtPasswdUser, wsUserMgmtAuthMethod3, wsUserMgmtRadiusSvrIPAddr }
			STATUS current
			DESCRIPTION 
				"Description."
			::= { wsUserMgmtGroups 2 }

		
	
	END

--
-- WS-USER-MGMT-MIB.my
--
